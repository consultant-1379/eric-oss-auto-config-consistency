module ericsson-enm-ResPowerSupply {
  yang-version 1.1;
  namespace urn:rdns:com:ericsson:ericsson-enm-ResPowerSupply;
  prefix erienmnrmrespowersupply;
  yexte:ecim-name ResPowerSupply;
  revision 2351-11-28 {
    yexte:version 4;
    yexte:release 2;
    yexte:correction 2;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ResEquipmentSupportFunction {
    prefix erienmnrmresequipmentsupportfunction;
  }
  typedef enum-OperState {
    description "Operational states of a resource.";
    type enumeration {
      enum DISABLED {
        description "The resource is  totally inoperable.";
        value 0;
      }
      enum ENABLED {
        description "The resource is partially or fully operable.";
        value 1;
      }
    }
  }
  typedef enum-AvailStatus {
    description "The availability status is used to qualify the operational state.
\n It indicates why the operational state has changed its value. ";
    type enumeration {
      enum IN_TEST {
        description "The resource is undergoing a test procedure. 
\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.
\nThe semantics are defined in CCITT Rec. X.735 | ISO/IEC 10164-6. ";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef ddt-ResPowerSupply_PowerSupply_multiplePowerSystem {
    type boolean;
  }
  typedef ddt-ResPowerSupply_SmartLoadSharingConfig_lowLoadLevelTreshold {
    type int32 {
      range 10..40;
    }
  }
  typedef ddt-ResPowerSupply_PowerSupply_systemUndervoltageAlarmLevel {
    type int32 {
      range -480..-380;
    }
  }
  typedef ddt-ResPowerSupply_PowerSupply_systemUndervoltageAlarmCeaseOffset {
    type int32 {
      range 0..50;
    }
  }
  typedef ddt-ResPowerSupply_SmartLoadSharingConfig_highLoadLevelTreshold {
    type int32 {
      range 55..85;
    }
  }
  typedef ddt-ResPowerSupply_PowerSupply_systemOvervoltageAlarmCeaseOffset {
    type int32 {
      range 0..50;
    }
  }
  typedef ddt-ResPowerSupply_PowerSupply_systemOvervoltageAlarmLevel {
    type int32 {
      range -600..-530;
    }
  }
  typedef ddt-ResPowerSupply_SmartLoadSharingConfig_highLoadLevelThreshold {
    type int32 {
      range 55..85;
    }
  }
  typedef ddt-ResPowerSupply_PowerSupply_nominalVoltage {
    type int32 {
      range -570..-480;
    }
  }
  typedef ddt-ResPowerSupply_SmartLoadSharingConfig_lowLoadLevelThreshold {
    type int32 {
      range 10..40;
    }
  }
  typedef ddt-ResPowerSupply_PowerSupply_userLabel {
    type string {
      length 1..128;
    }
  }
  typedef ddt-ResPowerSupply_PowerSupply_systemVoltage {
    type int32 {
      range -600..-380;
    }
  }
  grouping struct-SmartLoadSharingConfig {
    description "Configuration structure defining PSU Loads which trigger switching.";
    leaf highLoadLevelThreshold {
      description "PSU load level. When reached, switches another PSU to active mode.";
      yexte:dependencies "highLoadLevelThreshold >= lowLoadLevelThreshold*2+5";
      type erienmnrmrespowersupply:ddt-ResPowerSupply_SmartLoadSharingConfig_highLoadLevelThreshold;
      default 70;
    }
    leaf lowLoadLevelTreshold {
      status deprecated {
        yexte:status-information "Since 18.Q2. Replaced by lowLoadLevelThreshold";
      }
      description "PSU load level. When reached, switches PSU to standby mode.";
      yexte:dependencies "highLoadLevelTreshold >= lowLoadLevelTreshold*2+5";
      type erienmnrmrespowersupply:ddt-ResPowerSupply_SmartLoadSharingConfig_lowLoadLevelTreshold;
      default 30;
    }
    leaf highLoadLevelTreshold {
      status deprecated {
        yexte:status-information "Since 18.Q2. Replaced by highLoadLevelThreshold";
      }
      description "PSU load level. When reached, switches another PSU to active mode.";
      yexte:dependencies "highLoadLevelTreshold >= lowLoadLevelTreshold*2+5";
      type erienmnrmrespowersupply:ddt-ResPowerSupply_SmartLoadSharingConfig_highLoadLevelTreshold;
      default 70;
    }
    leaf lowLoadLevelThreshold {
      description "PSU load level. When reached, switches PSU to standby mode.";
      yexte:dependencies "highLoadLevelThreshold >= lowLoadLevelThreshold*2+5";
      type erienmnrmrespowersupply:ddt-ResPowerSupply_SmartLoadSharingConfig_lowLoadLevelThreshold;
      default 30;
    }
  } // end 'grouping struct-SmartLoadSharingConfig'
  grouping moc-PowerSupply-keys {
    description "Key(s) for MOC PowerSupply";
    leaf id {
      erienmyext:no-notification;
      description "The value component of the RDN.";
      mandatory true;
      yexte:ecim-name powerSupplyId;
      type string;
    }
  } // end 'grouping moc-PowerSupply-keys'
  grouping moc-PowerSupply {
    description "This MO represents the logical resource providing configuration and supervision support for the cabinet power supply. Examples include configuration of charging algorithms and supervision levels and switching functions on/off etc.
\n
\nDependencies: Can only exist in the node when the attribute supportSystemControl is set to true on a parent MO EquipmentSupportFunction.";
    leaf userLabel {
      description "Label for free use.";
      type erienmnrmrespowersupply:ddt-ResPowerSupply_PowerSupply_userLabel;
    }
    container smartLoadSharingConfig {
      description "Configuration structure defining PSU Loads which trigger switching.";
      erienmyext:enm-type STRUCT;
      uses erienmnrmrespowersupply:struct-SmartLoadSharingConfig;
    } // end 'container smartLoadSharingConfig'
    leaf controlDomainRef {
      erienmyext:no-notification;
      description "The cabinet or hwGroup where functions represented by this MO are deployed.";
      erienmyext:enm-type MOREF;
      type string;
    }
    leaf systemUndervoltageAlarmLevel {
      status deprecated {
        yexte:status-information "Since 18A. Replaced by systemUndervoltageAlarmLevel on MO PowerDistribution. Planned to be removed.";
      }
      description "Alarm level for system undervoltage. 
\nThe alarm is raised when systemVoltage is lower than SystemUndervoltageAlarmLevel.
\nExample: The default value -475 (-47.5 V) gives an alarm if systemVoltage is e.g. -47.4 V.";
      yexte:dependencies "systemUndervoltageAlarmLevel < mainLoadUnderVoltageDisconnect";
      type erienmnrmrespowersupply:ddt-ResPowerSupply_PowerSupply_systemUndervoltageAlarmLevel;
      default -475;
    }
    leaf systemVoltage {
      status deprecated {
        yexte:status-information "Since 18A. Replaced by systemVoltage on MO PowerDistribution. Planned to be removed.";
      }
      erienmyext:no-notification;
      config false;
      description "The measured system voltage. It is equal to the attribute batteryVoltage, MO BatteryBackup, when the battery is connected.
\nUndefined value: indicates no connection with neither PDU, BFU nor PSU.";
      type erienmnrmrespowersupply:ddt-ResPowerSupply_PowerSupply_systemVoltage;
    }
    leaf nominalVoltage {
      description "The desired system voltage.";
      yexte:dependencies "Superseded by chargingVoltage when MO BatteryBackup is created";
      type erienmnrmrespowersupply:ddt-ResPowerSupply_PowerSupply_nominalVoltage;
      default -545;
    }
    leaf smartLoadSharing {
      description "Parameter responsible for activating/deactivation Smart PSU load sharing";
      yexte:takes-effect Immediately;
      type boolean;
      default true;
    }
    leaf systemOvervoltageAlarmLevel {
      status deprecated {
        yexte:status-information "Since 18A. Replaced by systemOvervoltageAlarmLevel on MO PowerDistribution. Planned to be removed.";
      }
      description "Alarm level for system over voltage. 
\nThe alarm active condition is true when systemVoltage is above SystemOvervoltageAlarmLevel.
\nExample: The default value -575 (-57.5 V) gives an alarm if systemVoltage is e.g. -57.6 V.";
      type erienmnrmrespowersupply:ddt-ResPowerSupply_PowerSupply_systemOvervoltageAlarmLevel;
      default -575;
    }
    leaf systemUndervoltageAlarmCeaseOffset {
      status deprecated {
        yexte:status-information "Since 18A. Planned to be removed.";
      }
      description "The offset for the system under voltage level above which the system undervoltage alarm ceases. 
\nThe alarm cease condition is true when systemVoltage is above SystemUndervoltageAlarmLevel - SystemUndervoltageAlarmCeaseOffset.
\nExample: The default values -440 - 30 = -470 (-47.0 V) gives an alarm cease if systemVoltage is e.g. -47.1 V";
      type erienmnrmrespowersupply:ddt-ResPowerSupply_PowerSupply_systemUndervoltageAlarmCeaseOffset;
      default 30;
    }
    leaf-list availabilityStatus {
      min-elements 0;
      config false;
      description "The availability status. It contains details about operationalState.";
      notife:notifiable-state-data true;
      type erienmnrmrespowersupply:enum-AvailStatus;
    }
    leaf operationalState {
      erienmyext:no-notification;
      config false;
      description "Defines the operational state.";
      type erienmnrmrespowersupply:enum-OperState;
    }
    leaf systemOvervoltageAlarmCeaseOffset {
      status deprecated {
        yexte:status-information "Since 18A. Planned to be removed.";
      }
      description "The offset for the system over voltage level below which the system over voltage alarm is ceased.
\nThe alarm cease condition is true when systemVoltage is below SystemOvervoltageAlarmLevel + SystemOvervoltageAlarmCeaseOffset.
\nExample: The default values -575 + 5 = -570 (-57.0 V) gives an alarm cease if systemVoltage is e.g. -56.9 V.";
      type erienmnrmrespowersupply:ddt-ResPowerSupply_PowerSupply_systemOvervoltageAlarmCeaseOffset;
      default 5;
    }
    leaf multiplePowerSystem {
      description "Indicates if all power supplies in the power domain provide the same load.
\n
\ntrue: Several power systems provide separate loads within same cabinet.
\nMultiple sub-racks operate individually and form one power system each.
\nfalse: All loads within same cabinet are powered from one power system.
\nMultiple sub-racks are internally connected by a cabinet bus bar.
\n";
      type boolean;
      default true;
    }
  } // end 'grouping moc-PowerSupply'
  augment /erienmnrmcomtop:ManagedElement/erienmnrmresequipmentsupportfunction:EquipmentSupportFunction {
    list PowerSupply {
      key id;
      description "This MO represents the logical resource providing configuration and supervision support for the cabinet power supply. Examples include configuration of charging algorithms and supervision levels and switching functions on/off etc.
\n
\nDependencies: Can only exist in the node when the attribute supportSystemControl is set to true on a parent MO EquipmentSupportFunction.";
      erienmyext:enm-type MOC;
      uses moc-PowerSupply-keys;
      container attributes {
        description "Attributes for PowerSupply";
        uses moc-PowerSupply;
      } // end 'container attributes'
    } // end 'list PowerSupply'
  }
}
