module ericsson-enm-RtnL2LagPort {
  yang-version 1.1;
  namespace urn:rdns:com:ericsson:ericsson-enm-RtnL2LagPort;
  prefix erienmnrmrtnl2lagport;
  yexte:ecim-name RtnL2LagPort;
  revision 2351-11-28 {
    yexte:version 1;
    yexte:release 2;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef enum-AdmState {
    description "The administrative state of a resource. ";
    type enumeration {
      enum LOCKED {
        description "The resource is administratively prohibited from performing services for its users.";
        value 0;
      }
      enum UNLOCKED {
        description "The resource is administratively permitted to perform services for its users.
\nThis is independent of its inherent operability.";
        value 1;
      }
      enum SHUTTINGDOWN {
        description "Use of the resource is administratively permitted to existing instances of use only.
\nWhile the system remains in the shutting down state the manager may at any time cause the managed object to revert to the locked state.";
        value 2;
      }
    }
  }
  typedef enum-OperState {
    description "The operational states of a resource.";
    type enumeration {
      enum DISABLED {
        description " The resource is  totally inoperable.";
        value 0;
      }
      enum ENABLED {
        description " The resource is partially or fully operable.";
        value 1;
      }
    }
  }
  typedef enum-AvailStatus {
    description "The availability status is used to qualify the operational state.
\n It indicates why the operational state has changed its value. ";
    type enumeration {
      enum IN_TEST {
        description "The resource is undergoing a test procedure. 
\nIf the administrative state is locked or  shutting down then normal users are precluded from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "This indicates a log full condition.";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef ddt-RtnL2LagPort_LagPort_userLabel {
    type string {
      length 1..128;
    }
  }
  typedef ddt-MacAddressStr {
    description "MAC address string, controlled by a regular expression.
\n
\nAddress should be specified in colon separated hexadecimal notation as described in IEEE 802. 
\nMAC addresses shall have 17 characters.
\nValid characters: 0123456789abcdefABCDEF\n
\nExample: 00:12:34:56:78:9A";
    type string {
      length 17..17;
    }
  }
  typedef ddt-RtnL2LagPort_LagPort_mtu {
    type int32;
  }
  grouping moc-LagPort-keys {
    description "Key(s) for MOC LagPort";
    leaf id {
      erienmyext:no-notification;
      description "The value component of the RDN.";
      mandatory true;
      yexte:ecim-name lagPortId;
      type string;
    }
  } // end 'grouping moc-LagPort-keys'
  grouping moc-LagPort {
    description "Represents group of Ethernet link ports bundled together to act as single link, to provide link redundancy and increased bandwidth.\n\nDependencies: EthernetPort MO that is encapsulated by LagPort MO, cannot be used for MO types VlanPort, Dot1xSupplicant, InterfaceIPv4 or InterfaceIPv6.";
    leaf-list encapsulation {
      min-elements 1;
      max-elements 4;
      description "List of references to underlying encapsulations.\nUnderlying encapsulations can be EthernetPort MOs.\nAll encapsulated EthernetPort MOs must have same value on admOperatingMode and admOperatingMode, equal to ANY is not allowed.";
      yexte:disturbances "Changing this attribute causes traffic disturbances.";
      yexte:dependencies "If EthernetPort MO is referenced by LagPort MO, EthernetPort MO may not be used by any other MOs except SyncEthInput MO or PtpBcOcPort MO for SyncE and PTP.\nCan only refer to existing EthernetPort MO.";
      erienmyext:enm-type MOREF;
      type string;
    }
    leaf userLabel {
      description "Label for free use.";
      type erienmnrmrtnl2lagport:ddt-RtnL2LagPort_LagPort_userLabel;
    }
    leaf macAddress {
      config false;
      description "Assigned individual MAC address.";
      notife:notifiable-state-data true;
      type erienmnrmrtnl2lagport:ddt-MacAddressStr;
    }
    leaf administrativeState {
      description "The administrative state.";
      yexte:disturbances "Changing this attribute causes traffic disturbances.";
      type erienmnrmrtnl2lagport:enum-AdmState;
      default LOCKED;
    }
    leaf-list reservedBy {
      min-elements 0;
      config false;
      description "Contains a list of MO instances that reserve this MO instance.";
      notife:notifiable-state-data true;
      erienmyext:enm-type MOREF;
      type string;
    }
    leaf-list availabilityStatus {
      min-elements 0;
      config false;
      description "The availability status.\nDetails about operationalState.\nDEGRADED if some of encapsulated EthernetPort MOs cannot be used due to Ethernet or LACP problems.\nFAILED or DEPENDENCY_FAILED if none of encapsulated EthernetPort MOs can be used due to Ethernet or LACP problems.";
      notife:notifiable-state-data true;
      type erienmnrmrtnl2lagport:enum-AvailStatus;
    }
    leaf operationalState {
      config false;
      description "The operational state.";
      notife:notifiable-state-data true;
      type erienmnrmrtnl2lagport:enum-OperState;
    }
    leaf lacpEnabled {
      description "Specifies whether LACP is enabled or not on links in LAG.\nWhen true, LACP is enabled. When false LAG group is static and LACP is not used on ports.\nLACP is in active mode when enabled.";
      type boolean;
      default true;
    }
    leaf mtu {
      config false;
      description "MTU.\nLargest PDU that Ethernet layer can pass on Ethernet port.\nPDU includes Ethernet header, Ethertype, payload and frame check sequence.";
      notife:notifiable-state-data true;
      type erienmnrmrtnl2lagport:ddt-RtnL2LagPort_LagPort_mtu;
    }
  } // end 'grouping moc-LagPort'
  augment /erienmnrmcomtop:ManagedElement/erienmnrmcomtop:Transport {
    list LagPort {
      key id;
      max-elements 2;
      description "Represents group of Ethernet link ports bundled together to act as single link, to provide link redundancy and increased bandwidth.\n\nDependencies: EthernetPort MO that is encapsulated by LagPort MO, cannot be used for MO types VlanPort, Dot1xSupplicant, InterfaceIPv4 or InterfaceIPv6.";
      erienmyext:enm-type MOC;
      uses moc-LagPort-keys;
      container attributes {
        description "Attributes for LagPort";
        uses moc-LagPort;
      } // end 'container attributes'
    } // end 'list LagPort'
  }
}
