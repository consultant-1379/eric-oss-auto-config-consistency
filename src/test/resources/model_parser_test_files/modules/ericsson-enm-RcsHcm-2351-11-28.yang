module ericsson-enm-RcsHcm {
  yang-version 1.1;
  namespace urn:rdns:com:ericsson:ericsson-enm-RcsHcm;
  prefix erienmnrmrcshcm;
  yexte:ecim-name RcsHcm;
  revision 2351-11-28 {
    yexte:version 1;
    yexte:release 2;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef enum-HcCategory {
    description "Lists the possible categories to which a health check rule can belong to.\nA category aims to facilitate the execution of rules to help customers the planning of their execution according to specific O&M activity.";
    type enumeration {
      enum BACKOFFICE {
        description "Indicates that the rule should be executed for backoffice operation tests.";
        status deprecated {
          yexte:status-information "Since 19.Q4.";
        }
        value 0;
      }
      enum DAILY {
        description "Indicates that the rule should be executed daily.";
        status deprecated {
          yexte:status-information "Since 19.Q4.";
        }
        value 1;
      }
      enum MANDATORY {
        description "Indicates that the rule should always be executed.";
        status deprecated {
          yexte:status-information "Since 19.Q4.";
        }
        value 2;
      }
      enum POSTUPDATE {
        description "Indicates that the rule should be executed after an update.";
        status deprecated {
          yexte:status-information "Since 19.Q4.";
        }
        value 3;
      }
      enum POSTUPGRADE {
        description "Indicates that the rule should be executed after an upgrade.";
        status deprecated {
          yexte:status-information "Since 19.Q4.";
        }
        value 4;
      }
      enum PREINSTALL {
        description "Indicates that the rule be executed before an installation.";
        status deprecated {
          yexte:status-information "Since 19.Q4.";
        }
        value 5;
      }
      enum PREUPDATE {
        description "Indicates that the rule should be executed before an update.";
        status deprecated {
          yexte:status-information "Since 19.Q4.";
        }
        value 6;
      }
      enum PREUPGRADE {
        description "Indicates that the rule should be executed before an upgrade.";
        status deprecated {
          yexte:status-information "Since 19.Q4.";
        }
        value 7;
      }
      enum SHORT {
        description "Indicates that the rule should be executed for quick checks.";
        status deprecated {
          yexte:status-information "Since 19.Q4.";
        }
        value 8;
      }
      enum TROUBLESHOOT {
        description "Indicates that the rule should be executed for troubleshooting.";
        status deprecated {
          yexte:status-information "Since 19.Q4.";
        }
        value 9;
      }
      enum OTHER {
        description "Indicates that the rule is not included in any of other categories.";
        status deprecated {
          yexte:status-information "Since 19.Q4.";
        }
        value 10;
      }
    }
  }
  typedef enum-ActionResultType {
    description "Lists the different results of an action.";
    type enumeration {
      enum SUCCESS {
        description "The asynchronous action ended with success.";
        value 1;
      }
      enum FAILURE {
        description "The asynchronous action ended with failure.";
        value 2;
      }
      enum NOT_AVAILABLE {
        description "No result is available yet.";
        value 3;
      }
    }
  }
  typedef enum-RuleSeverity {
    description "Lists the possible severity values of a rule.\nEach value describes how the node healthiness status is affected when the rule result is not the expected one.";
    type enumeration {
      enum CRITICAL {
        description "Indicates a rule which failure is critical for ME healthness.\nIn that case, the ME requires immediate actions.";
        value 0;
      }
      enum WARNING {
        description "Indicates a rule which failure is a warning for ME healthness.\nIn that case, the ME requires user attention. ";
        value 1;
      }
    }
  }
  typedef enum-ActionStateType {
    description "Lists the action states.";
    type enumeration {
      enum CANCELLING {
        description "Cancellation is in progress.";
        value 1;
      }
      enum RUNNING {
        description "The execution of the action is currently in progress.";
        value 2;
      }
      enum FINISHED {
        description "The action is finished.";
        value 3;
      }
      enum CANCELLED {
        description "The action has been cancelled and cancellation has been done.";
        value 4;
      }
    }
  }
  typedef enum-HealthStatus {
    description "Lists the possible health statuses, based on result of all executed rules.";
    type enumeration {
      enum HEALTHY {
        description "Indicates that the NE status is healthy.\nThe result of all executed rules is as expected.";
        value 0;
      }
      enum NOT_HEALTHY {
        description "Indicates that the NE status is not healthy.\nThe result of at least one rule, which severity is CRITICAL, is not as expected.";
        value 1;
      }
      enum WARNING {
        description "Indicates that the NE status is warning.    \nThe result of at least one rule, which severity is WARNING, is not as expected and the result of all CRITICAL ones is as expected.";
        value 2;
      }
      enum NOT_AVAILABLE {
        description "Indicates that the NE status is not available.\nThe result of all executed rules is still not available or the execution never started.";
        value 3;
      }
    }
  }
  typedef enum-BasicAdmState {
    description "Basic administrative states for a resource.";
    type enumeration {
      enum LOCKED {
        description " The resource is administratively prohibited from performing services for its users.";
        value 0;
      }
      enum UNLOCKED {
        description "The resource is administratively permitted to perform services for its users.\nThis is independent of its inherent operability.";
        value 1;
      }
    }
  }
  typedef ddt-ActionInvocationResult {
    description "This is the datatype for the Asychronous Action Id. ";
    type uint16;
  }
  typedef ddt-EcimPasswordString {
    description "Holds the password string.";
    type string;
  }
  typedef ddt-DateTime {
    description "Represents the international standard for the representation of date and time ( ISO 8601).\nThe string format is \"YYYY-MM-DDThh:mm:ss.SSSZ\" (excluding quotes).\nA DateTime string consists of a date part, a time part, and an optional time zone information part. The time zone part may be a \"Z\", representing the Coordinated Universal Time (UTC) time zone (equals to +00) or a time zone offset (for example, +02:00).\nIf the time zone part is not present, the DateTime value represents local time.\n\nThe following pattern describes the DateTime format:\nYYYY-MM-DDThh:mm:ss[.S+][Z|+-hh:mm]\nWhere:\nYYYY = Four digit year\nMM = Two digit month (01=January, and so on)\nDD = Two digit day of month (01 through 31)\nT = Time designator (shows start of time component)\nhh = Two digits of hour (00 through 23, AM/PM not allowed)\nmm = Two digits of minute (00 through 59)\nss = Two digits of second (00 through 59, leap second not allowed)\nS+ = One or more digits of decimal fraction of a second\nZ = Time is UTC\n+- = + or - character indicating positive or negative offset to UTC\n\nDateTime values are compliant with ISO 8601 \"Representation of dates and times\" but are restricted according to RFC 3339 \"Date and Time on the Internet: Timestamps\". The DateTime format is further restricted as follows:\n- T and Z designators are upper case.\n- . (dot) is used to indicate start of fractions of seconds (ISO 8601 also allows comma)";
    type string {
      length 19..31;
    }
  }
  grouping struct-FailedHcRule {
    description "Indicates some information about a failed health check rule.";
    leaf severity {
      description "Specifies the severity of the failed health check rule.";
      type erienmnrmrcshcm:enum-RuleSeverity;
      mandatory true;
    }
    leaf reason {
      description "Specifies a description of the health check rule failure.";
      type string;
      mandatory true;
    }
    leaf hcRule {
      description "Specifies the RDN of the failed health check rule.";
      type string;
      mandatory true;
    }
    leaf-list entity {
      min-elements 0;
      description "Refers to the failing entity.";
      type string;
    }
  } // end 'grouping struct-FailedHcRule'
  grouping struct-HcRuleCategory {
    description "Struct for health check categories.";
    leaf description {
      description "Description of category.";
      type string;
      mandatory true;
    }
    leaf category {
      description "Category name.";
      type string;
      mandatory true;
    }
  } // end 'grouping struct-HcRuleCategory'
  grouping struct-HcRuleInputParameter {
    description "Indicates a parameter into a rule that can be changed before a health check evaluation.\nThe name, a brief description and the default value are indicated.\nThe default value is used in case no user-defined value is provided into attribute inputParameters under MOC HcJob.";
    leaf name {
      description "Specifies the parameter name.";
      type string;
      mandatory true;
    }
    leaf description {
      description "Specifies a brief description of the rule parameter.";
      type string;
      mandatory true;
    }
    leaf value {
      description "Specifies the parameter value.";
      type string;
      mandatory true;
    }
  } // end 'grouping struct-HcRuleInputParameter'
  grouping struct-HcRuleParameter {
    description "Specifies an optional parameter that could be provided for rule evaluation.";
    leaf hcRule {
      description "Specifies the RDN of the HcRule object for which the parameter must be used.\nIt must be a string having the format \"HcRule=<RULE_ID>\".";
      type string;
      mandatory true;
    }
    leaf name {
      description "Specifies the parameter name.";
      type string;
      mandatory true;
    }
    leaf value {
      description "Specifies the parameter value.";
      type string;
      mandatory true;
    }
  } // end 'grouping struct-HcRuleParameter'
  grouping struct-AsyncActionProgress {
    description "Records the progress of an asynchronous action.";
    leaf result {
      description "Result state of a completed action.\nThis field has value NOT_AVAILABLE if the action is not finished.";
      type erienmnrmrcshcm:enum-ActionResultType;
    }
    leaf timeOfLastStatusUpdate {
      description "Date and time when the struct member state was last updated.";
      type erienmnrmrcshcm:ddt-DateTime;
      mandatory true;
    }
    leaf timeActionCompleted {
      description "Date and time when the action was completed (successfully or unsuccessfully).";
      type erienmnrmrcshcm:ddt-DateTime;
    }
    leaf-list additionalInfo {
      min-elements 0;
      description "Used for logging significant messages during execution of an action.";
      type string;
    }
    leaf actionId {
      description "Uniquely identifies the invocation of an action.\nIdentifies the invocation of an action when the managed object allows invocation of more than one action at a time.";
      type erienmnrmrcshcm:ddt-ActionInvocationResult;
      mandatory true;
    }
    leaf progressPercentage {
      description "Progress of the action.\nThe range is between 0 and 100.";
      type uint8;
    }
    leaf progressInfo {
      description "Textual information that describes the actual state of the action execution.";
      type string;
    }
    leaf state {
      description "Current state of the action.";
      type erienmnrmrcshcm:enum-ActionStateType;
    }
    leaf timeActionStarted {
      description "Date and time when the current action was started.";
      type erienmnrmrcshcm:ddt-DateTime;
      mandatory true;
    }
    leaf resultInfo {
      description "Textual description of the outcome/result of the action containing useful information for the NMS.\nIf the action failed, it can contain an error message.";
      type string;
    }
    leaf actionName {
      description "Name of the invoked asynchronous action.";
      type string;
    }
  } // end 'grouping struct-AsyncActionProgress'
  grouping moc-HealthCheckM-keys {
    description "Key(s) for MOC HealthCheckM";
    leaf id {
      erienmyext:no-notification;
      description "Holds the name used when identifying the MO.";
      mandatory true;
      yexte:ecim-name healthCheckMId;
      type string;
    }
  } // end 'grouping moc-HealthCheckM-keys'
  grouping moc-HealthCheckM {
    description "Represents the root MOC for Health Check Management function.\nThe Health Check Management function reports summary views of the managed element current state highlighting any deviations from a normal behavior. It can be used to attend upgrades and to support preventive maintenance and problem resolution.\nThe healthiness status is obtained by verifying a set of rules according to their severity, grouped in predefined categories. For instance, if the result of at least one critical rule is not as expected, node status is evaluated as not healthy requiring an immediate action.\nThe categories of rules which the Health Check Management function is acting upon are system installed.\nA health check job can be created selecting one or more categories of rules on which the ME healthiness is evaluated.\nA report file is generated for each executed health check job and stored in the predefined folder with a compressed archive file containing logs used for the rules evaluation to be used for further investigation.";
    leaf lastExecutedJob {
      config false;
      description "Specifies the DN of the last job executed to check the ME healthiness.";
      notife:notifiable-state-data true;
      erienmyext:enm-type MOREF;
      type string;
    }
    leaf lastStatus {
      config false;
      description "Specifies the ME healthiness status according to the last executed job.";
      notife:notifiable-state-data true;
      type erienmnrmrcshcm:enum-HealthStatus;
    }
    leaf lastUpdateTime {
      config false;
      description "Specifies the date and time of the last time the health of the system has been updated.";
      notife:notifiable-state-data true;
      type erienmnrmrcshcm:ddt-DateTime;
    }
    leaf maxNoOfReportFiles {
      description "Specifies the maximum number of report files with related log files archive maintained in the ME.\nIf a new file is created and the limit is exceeded, the oldest file is deleted.";
      type uint16;
      default 10;
    }
  } // end 'grouping moc-HealthCheckM'
  grouping moc-HcRule-keys {
    description "Key(s) for MOC HcRule";
    leaf id {
      erienmyext:no-notification;
      description "Holds the name used when identifying the MO.\nIts value is divided into two parts. The first one is an unique identifier for the rule provider while the second one is a numeric identifier (a progressive number for example).";
      mandatory true;
      yexte:ecim-name hcRuleId;
      type string;
    }
  } // end 'grouping moc-HcRule-keys'
  grouping moc-HcRule {
    description "Represents a health check rule.\nThis class facilitates in providing detailed information about an individual health check rule.\nEach rule belongs to one or more health check categories.\nEach rule is also associated with a severity value, warning or critical, that affects the evaluation of the overall NE healthiness. For instance, if the result of at least one critical rule is not as expected, node status is evaluated as not healthy requiring an immediate action.\nSome health check rules can accept optional parameters as input for the evaluation, if no values are provided system default input parameters are used.";
    leaf recommendedAction {
      config false;
      description "Specifies the step that needs to be performed when the health check rule execution fails.";
      notife:notifiable-state-data true;
      type string;
    }
    leaf severity {
      erienmyext:no-notification;
      config false;
      description "Specify the severity of the rule for the evaluation of the overall NE healthiness.";
      type erienmnrmrcshcm:enum-RuleSeverity;
    }
    leaf administrativeState {
      description "Specifies the administrative state of the rule. ";
      type erienmnrmrcshcm:enum-BasicAdmState;
      default UNLOCKED;
    }
    leaf name {
      erienmyext:no-notification;
      config false;
      description "Specifies the name of a health check rule.";
      type string;
    }
    list categoryList {
      min-elements 1;
      key auto-generated-struct-key;
      leaf auto-generated-struct-key {
        type uint16;
        description "This leaf has been injected to allow for struct instances in a sequence to be ordered.";
        mandatory true;
      }
      description "List of categories to which health check rule belongs.";
      erienmyext:enm-type STRUCT;
      uses erienmnrmrcshcm:struct-HcRuleCategory;
    } // end 'list categoryList'
    leaf description {
      erienmyext:no-notification;
      config false;
      description "Specifies health check rule description.";
      type string;
    }
    leaf-list categories {
      min-elements 1;
      status deprecated {
        yexte:status-information "Since 19.Q4. Replaced by categoryList. Planned to be removed.";
      }
      config false;
      description "Specifies the list of categories which the rule belongs to.";
      notife:notifiable-state-data true;
      type erienmnrmrcshcm:enum-HcCategory;
    }
    list inputParameters {
      min-elements 0;
      key auto-generated-struct-key;
      leaf auto-generated-struct-key {
        type uint16;
        description "This leaf has been injected to allow for struct instances in a sequence to be ordered.";
        mandatory true;
      }
      description "Specifies the list of input parameters accepted by the rule with related default values.\nIt is empty in case the rule does not accept any parameters change.";
      erienmyext:enm-type STRUCT;
      uses erienmnrmrcshcm:struct-HcRuleInputParameter;
    } // end 'list inputParameters'
  } // end 'grouping moc-HcRule'
  grouping moc-HcJob-keys {
    description "Key(s) for MOC HcJob";
    leaf id {
      erienmyext:no-notification;
      description "Holds the name used when identifying the MO.\nSpecifies the name of the health check job.";
      mandatory true;
      yexte:ecim-name hcJobId;
      type string;
    }
  } // end 'grouping moc-HcJob-keys'
  grouping moc-HcJob {
    description "Represents a health check job which can be executed on a ME.\nThis class facilitates in executing one or more categories of health check rules.\nAfter each job execution the attributes 'lastUpdateTime' and 'lastStatus' in HealthCheckM MOC are updated accordingly.\nIt is possible to execute the job on demand or by a scheduler.\nA report file is generated for each executed health check job and stored in the predefined folder with a compressed archive file containing logs used for the rules evaluation to be used for further investigation.";
    leaf localFileStorePath {
      erienmyext:no-notification;
      config false;
      description "Specifies the filesystem path where the ouput report files can be fetched.\nIt is empty if FileM is not installed/configured.";
      type string;
    }
    leaf lastReportFileName {
      erienmyext:no-notification;
      config false;
      description "Specifies the name of the report file which is generated from the latest execution of the job.\nAll the report files are placed in a predefined folder, as indicated by the 'localFileStorePath' attribute value. An archive containing some log files is generated as well.\nThe name format of the report file generated is <MEId>_<JobName>_<Timestamp>. Timestamp is in the format YYYYMMDDTHHmmSS, where 4 digits for the year, 2 digits for the month, 2 digits for the date, 2 digits for the hours, 2 digits for the minutes and 2 digits for the seconds are specified. 'T' acts as a delimiter between date and time in the above timestamp format. If the job is executed by the action, the suffix \"_man\" is added at the end of the file name.";
      type string;
    }
    leaf lastRunTime {
      config false;
      description "Specifies the date and time of the last time the job has been executed.";
      notife:notifiable-state-data true;
      type erienmnrmrcshcm:ddt-DateTime;
    }
    container progressReport {
      description "Specifies the execution status and result of the health check job.";
      erienmyext:enm-type STRUCT;
      uses erienmnrmrcshcm:struct-AsyncActionProgress;
    } // end 'container progressReport'
    leaf-list ruleCategoryList {
      min-elements 0;
      description "List of health check rule categories to be executed.";
      yexte:dependencies "Each value must equal a category in categoryList in HcRule MO instance(s).";
      type string;
    }
    leaf-list rulesCategories {
      min-elements 0;
      status deprecated {
        yexte:status-information "Since 19.Q4. Replaced by rulesCategoryList. Planned to be removed.";
      }
      description "Specifies the list of categories of health check rules to be executed.";
      type erienmnrmrcshcm:enum-HcCategory;
    }
    leaf jobToTrigger {
      description "Specifies the DN of another job to be executed when the current job reports ME is not healthy.\nThe execution of another job, for instance to execute rules associated to different categories, might give more detailed information about NE status.";
      erienmyext:enm-type MOREF;
      type string;
    }
    list failedRules {
      min-elements 0;
      key auto-generated-struct-key;
      leaf auto-generated-struct-key {
        type uint16;
        description "This leaf has been injected to allow for struct instances in a sequence to be ordered.";
        mandatory true;
      }
      description "Provides a condensed status for the last job execution.\nProvides the list of the rules for which the result was not the expected one. \nIt is empty when job status is healthy or not available.";
      erienmyext:enm-type STRUCT;
      uses erienmnrmrcshcm:struct-FailedHcRule;
    } // end 'list failedRules'
    list inputParameters {
      min-elements 0;
      key auto-generated-struct-key;
      leaf auto-generated-struct-key {
        type uint16;
        description "This leaf has been injected to allow for struct instances in a sequence to be ordered.";
        mandatory true;
      }
      description "Specifies customizable input parameters for rules evaluation.\nEach item in the list is a triple <hcRule, parameter_name, parameter_value> for which a user-defined attribute can be provided.";
      erienmyext:enm-type STRUCT;
      uses erienmnrmrcshcm:struct-HcRuleParameter;
    } // end 'list inputParameters'
    leaf status {
      config false;
      description "Specifies the health status based on result of all executed rules. ";
      notife:notifiable-state-data true;
      type erienmnrmrcshcm:enum-HealthStatus;
    }
    action cancel {
      description "Cancels the current HcJob execution.\nThe action returns true if the action is accepted, otherwise false is returned.\n";
      output {
        leaf result {
          type boolean;
        }
      }
    }
    action execute {
      description "Executes the health check job.\nThis action executes the health check job, executing the rules for the configured categories, and optionally exports the report file.\n\nThe action returns immediately after invocation. The progress of the action can be tracked by attribute progressReport . The action returns an error message if the action cannot start for some reason, for example, another parallel action is in progress. When the action is successfully started, an action ID is returned. The action ID is unique for every invocation of the action.";
      input {
        leaf exportUri {
          description "Specifies the URI where the job execution output file is to be exported.\nThis URI must not contain the file name, that is specified by 'lastReportFileName' attribute value.\nThe generic URI syntax is defined by RFC 3986.\nExample for SFTP: sftp://myuser@myhostname.ericsson.local/dir/subdir/\nExample for HTTP: http://myhostname.ericsson.local/dir/subdir/\nThe URI must not contain any password. (The password must be provided in the second parameter of this action).\nThe URI may be local relative (e.g., data/dir/subdir/), or local absolute (e.g., file:///data/dir/subdir/), or remote (e.g., sftp://myuser@hostname/dir/subdir/).\nIf the URI is local relative, report and logs archive files are stored starting from path specified by attribute localFileStorePath.";
          type string;
        }
        leaf exportPassword {
          description "Specifies the password required to access the location specified by the uri. \nIf no password is required, this parameter is ignored. ";
          type erienmnrmrcshcm:ddt-EcimPasswordString;
        }
      }
      output {
        leaf result {
          type erienmnrmrcshcm:ddt-ActionInvocationResult;
        }
      }
    }
  } // end 'grouping moc-HcJob'
  augment /erienmnrmcomtop:ManagedElement/erienmnrmcomtop:SystemFunctions {
    list HealthCheckM {
      key id;
      max-elements 1;
      description "Represents the root MOC for Health Check Management function.\nThe Health Check Management function reports summary views of the managed element current state highlighting any deviations from a normal behavior. It can be used to attend upgrades and to support preventive maintenance and problem resolution.\nThe healthiness status is obtained by verifying a set of rules according to their severity, grouped in predefined categories. For instance, if the result of at least one critical rule is not as expected, node status is evaluated as not healthy requiring an immediate action.\nThe categories of rules which the Health Check Management function is acting upon are system installed.\nA health check job can be created selecting one or more categories of rules on which the ME healthiness is evaluated.\nA report file is generated for each executed health check job and stored in the predefined folder with a compressed archive file containing logs used for the rules evaluation to be used for further investigation.";
      yexte:is-system-created;
      erienmyext:enm-type MOC;
      uses moc-HealthCheckM-keys;
      container attributes {
        description "Attributes for HealthCheckM";
        uses moc-HealthCheckM;
      } // end 'container attributes'
    } // end 'list HealthCheckM'
  }
  augment /erienmnrmcomtop:ManagedElement/erienmnrmcomtop:SystemFunctions/erienmnrmrcshcm:HealthCheckM {
    list HcRule {
      key id;
      description "Represents a health check rule.\nThis class facilitates in providing detailed information about an individual health check rule.\nEach rule belongs to one or more health check categories.\nEach rule is also associated with a severity value, warning or critical, that affects the evaluation of the overall NE healthiness. For instance, if the result of at least one critical rule is not as expected, node status is evaluated as not healthy requiring an immediate action.\nSome health check rules can accept optional parameters as input for the evaluation, if no values are provided system default input parameters are used.";
      yexte:is-system-created;
      erienmyext:enm-type MOC;
      uses moc-HcRule-keys;
      container attributes {
        description "Attributes for HcRule";
        uses moc-HcRule;
      } // end 'container attributes'
    } // end 'list HcRule'
  }
  augment /erienmnrmcomtop:ManagedElement/erienmnrmcomtop:SystemFunctions/erienmnrmrcshcm:HealthCheckM {
    list HcJob {
      key id;
      description "Represents a health check job which can be executed on a ME.\nThis class facilitates in executing one or more categories of health check rules.\nAfter each job execution the attributes 'lastUpdateTime' and 'lastStatus' in HealthCheckM MOC are updated accordingly.\nIt is possible to execute the job on demand or by a scheduler.\nA report file is generated for each executed health check job and stored in the predefined folder with a compressed archive file containing logs used for the rules evaluation to be used for further investigation.";
      erienmyext:enm-type MOC;
      uses moc-HcJob-keys;
      container attributes {
        description "Attributes for HcJob";
        uses moc-HcJob;
      } // end 'container attributes'
    } // end 'list HcJob'
  }
}
