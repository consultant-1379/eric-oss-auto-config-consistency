module ericsson-enm-RmeUlSpectrumAnalyzer {
  yang-version 1.1;
  namespace urn:rdns:com:ericsson:ericsson-enm-RmeUlSpectrumAnalyzer;
  prefix erienmnrmrmeulspectrumanalyzer;
  yexte:ecim-name RmeUlSpectrumAnalyzer;
  revision 2351-11-28 {
    yexte:version 3;
    yexte:release 2;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RmeSupport {
    prefix erienmnrmrmesupport;
  }
  typedef enum-TcpStatus {
    description "Status of TCP.";
    type enumeration {
      enum UNKNOWN {
        value 0;
      }
      enum STARTED {
        value 1;
      }
      enum FINISHED {
        value 2;
      }
      enum FAILED {
        value 3;
      }
      enum STOPPED {
        value 4;
      }
    }
  }
  typedef enum-UlSpectrumSamplingType {
    description "Type of sampling operation last ordered.";
    type enumeration {
      enum SNAPSHOT_SAMPLING {
        description "A single sample is requested.";
        value 0;
      }
      enum CONTINUOUS_SAMPLING {
        description "Several samples are requested, one at a time, with an  interval according to attribute samplingInterval. When no interval is specified, best effort is used.";
        value 1;
      }
      enum CONDITIONAL_SAMPLING {
        description "A single sample is requested with a specific trigger condition specified.";
        value 2;
      }
    }
  }
  typedef enum-InfoType {
    description "Information on the reason for latest unsuccessful action.";
    type enumeration {
      enum UNDEFINED {
        description "Initial default value.";
        value 0;
      }
      enum PARAMETERS_NOT_SUPPORTED {
        description "One or more parameters out of range.";
        value 1;
      }
      enum TIMEOUT_AT_FILE_UPLOAD {
        description "Transfer of sample file exceeds time limit.";
        value 2;
      }
      enum NO_CARRIERS_SETUP_ON_RADIO {
        description "No active carriers on radio.";
        value 3;
      }
      enum CONDITIONAL_MEASUREMENT_TIMEOUT {
        description "Trigger condition not fulfilled within time limit.";
        value 4;
      }
      enum RADIO_IS_BUSY_WITH_ANOTHER_SAMPLING {
        description "Conditional sampling already started in radio.";
        value 5;
      }
      enum NO_CONTACT_WITH_RADIO {
        description "No access to specified radio.";
        value 6;
      }
      enum NO_RESOURCES {
        description "Radio unable to set up sampling configuration.";
        value 7;
      }
      enum NO_CONTACT_WITH_RADIO_MEASUREMENT_SERVER {
        description "No contact with radio measurement server.";
        value 8;
      }
      enum NO_VALID_LICENSE {
        description "No feature license available on the node.";
        value 9;
      }
      enum PARTIALLY_FINISHED {
        description "In case of continuous sampling, distinguishes partially finished sampling state from completely finished one.";
        value 10;
      }
    }
  }
  typedef ddt-UlSpectrumAnalyzer_startUlsaSampling_centerFrequency {
    type uint32;
  }
  typedef ddt-UlSpectrumAnalyzer_startSampling_powerLevel {
    type int32;
  }
  typedef ddt-RmeUlSpectrumAnalyzer_UlsaCapabilityConfig_maxPower {
    type int32;
  }
  typedef ddt-UlSpectrumAnalyzer_startSampling_centerFrequency {
    type uint32;
  }
  typedef ddt-RmeUlSpectrumAnalyzer_UlsaCapabilityConfig_numSpectrumTypes {
    type uint32 {
      range 0..64;
    }
  }
  typedef ddt-EcimPasswordString {
    description "This type enables secure handling of passwords.";
    type string;
  }
  typedef ddt-UlSpectrumAnalyzer_startUlsaSampling_samplingInterval {
    type uint32;
  }
  typedef ddt-IpDNSAddress {
    description "The IpDNSAddress type represents an IP address or a DNS domain name.\n\nA unicast IPv4 address is presented in three-digit decimal blocks. It is specified in dotted-quad decimal notation (i.e. three-digit decimal blocks) in accordance with RFC791, The blocks are separated by a dot.\n- The unicast IPV4  address is within range [1-126,128-223].[0-255].[0-255].[0-255], 7-15 characters.\n- The IP address range 127.0.0.0 – 127.255.255.255 is reserved for loopback\n- The IP address range 0– 0.255.255.255 are reserved\n- The IP address range 169.254.1.0 - 169.254.254.255 is used for link-local addresses.\n\nAn  IPv6 address is specified by 8 groups of 16 bit hexadecimal values separated by colons as described in RFC 4291. If multiple consecutive groups contain only zeros, the use of “::” indicates one or more groups of 16 bits of zeros, as described in RFC 4291, section 2.2 bullet 2. A link-local address will have prefix fe80::/10. The format of the embedded IPv4/IPv6 addresses is described in RFC 6052.\n- IPv6 minimum length = 3 and maximum length = 39.\n- Valid characters: 0123456789abcdefABCDEF:\n\nA domain name is specified in dot separated alphanumeric notation  as described in RFC 1034. The domain name consists of one or more parts, called labels, that are delimited by dots.\n- Domain Name's length: 253 characters\n- Label's length: 63 characters.\n- Valid characters: a-z, A-Z, 0,1,2,3,4,5,6,7,8,9,-\n- The Label’s first character is a letter.\n- Labels shall not start or end with a hyphen.\n- Labels shall not start with a numbers\n- Labels shall end with a number or a letter.";
    type string {
      length 1..253;
    }
  }
  typedef ddt-RmeUlSpectrumAnalyzer_UlsaCapabilityConfig_minPower {
    type int32;
  }
  typedef ddt-RmeUlSpectrumAnalyzer_CapabilityConfigData_numTriggerTypes {
    type uint32 {
      range 0..4;
    }
  }
  typedef ddt-UlSpectrumAnalyzer_startSampling_resolutionBandwidth {
    type uint32;
  }
  typedef ddt-UlSpectrumAnalyzer_startSampling_samplingInterval {
    type uint32;
  }
  typedef ddt-UlSpectrumAnalyzer_startUlsaSampling_triggerTimeOfDay {
    type string {
      length 0..128;
    }
  }
  typedef ddt-RmeUlSpectrumAnalyzer_CapabilityConfigData_measurementPort {
    type string {
      length 0..128;
    }
  }
  typedef ddt-UlSpectrumAnalyzer_startUlsaSampling_displayedBandwidth {
    type uint32;
  }
  typedef ddt-UlSpectrumAnalyzer_startUlsaSampling_resolutionBandwidth {
    type uint32;
  }
  typedef ddt-UlSpectrumAnalyzer_startSampling_targetMeasurementPort {
    type string {
      length 0..128;
    }
  }
  typedef ddt-RmeUlSpectrumAnalyzer_CapabilityConfigData_maxPower {
    type int32;
  }
  typedef ddt-UlSpectrumAnalyzer_startUlsaSampling_targetRfPort {
    type string {
      length 0..128;
    }
  }
  typedef ddt-RmeUlSpectrumAnalyzer_UlsaCapabilityConfig_numTriggerTypes {
    type uint32 {
      range 0..4;
    }
  }
  typedef ddt-UlSpectrumAnalyzer_getSamplingCapability_targetRadioUnit {
    type string {
      length 0..128;
    }
  }
  typedef ddt-RmeUlSpectrumAnalyzer_UlsaCapabilityConfig_carrierRfPort {
    type uint32 {
      range 1..8;
    }
  }
  typedef ddt-RmeUlSpectrumAnalyzer_CapabilityConfigData_numSpectrumTypes {
    type uint32 {
      range 0..64;
    }
  }
  typedef ddt-UlSpectrumAnalyzer_startUlsaSampling_samplingTimeout {
    type uint32;
  }
  typedef ddt-RmeUlSpectrumAnalyzer_CapabilityConfigData_minPower {
    type int32;
  }
  typedef ddt-UlSpectrumAnalyzer_startUlsaSampling_powerLevel {
    type int32;
  }
  typedef ddt-UlSpectrumAnalyzer_startSampling_displayedBandwidth {
    type uint32;
  }
  typedef ddt-UlSpectrumAnalyzer_startSampling_triggerTimeOfDay {
    type string {
      length 0..128;
    }
  }
  typedef ddt-UlSpectrumAnalyzer_stopUlsaSampling_targetRfPort {
    type string {
      length 0..128;
    }
  }
  typedef ddt-UlSpectrumAnalyzer_startSampling_samplingTimeout {
    type uint32;
  }
  typedef ddt-UlSpectrumAnalyzer_getUlsaSamplingCapability_targetRadioUnit {
    type string {
      length 0..128;
    }
  }
  grouping struct-UlsaCapabilityConfig {
    description "Returns value of action getUlsaSamplingCapability that fetches UL Spectrum Analyzer capabilities from radio and returns result in an array of struct UlsaCapabilityConfig.";
    leaf numSpectrumTypes {
      description "Number of spectrum types for RF branch.";
      type erienmnrmrmeulspectrumanalyzer:ddt-RmeUlSpectrumAnalyzer_UlsaCapabilityConfig_numSpectrumTypes;
      mandatory true;
    }
    leaf numTriggerTypes {
      description "Number of trigger types for RF branch.";
      type erienmnrmrmeulspectrumanalyzer:ddt-RmeUlSpectrumAnalyzer_UlsaCapabilityConfig_numTriggerTypes;
      mandatory true;
    }
    leaf-list maxFrequency {
      min-elements 0;
      max-elements 64;
      description "Upper RF range for RF branch. Spectrum information parameter.";
      type int32;
    }
    leaf trigger1DataDefined {
      description "Indicates if valid trigger1 data is included for carrierRfPort.";
      type boolean;
      mandatory true;
    }
    leaf-list samplingRate {
      min-elements 0;
      max-elements 64;
      description "Different sampling rate values for ADC and filter branch. Spectrum information parameter.";
      type uint32;
    }
    leaf-list flatGainBW {
      min-elements 0;
      max-elements 64;
      description "Flat gain portion of bandwidth that can be configured for associated carrier. Spectrum information parameter.";
      type uint32;
    }
    leaf carrierRfPort {
      description "RfPort for RF branch. Port A equals 1, port B equals 2, and so on.";
      type erienmnrmrmeulspectrumanalyzer:ddt-RmeUlSpectrumAnalyzer_UlsaCapabilityConfig_carrierRfPort;
      mandatory true;
    }
    leaf minPower {
      description "Lower level of UL power range. Trigger information parameter.";
      type erienmnrmrmeulspectrumanalyzer:ddt-RmeUlSpectrumAnalyzer_UlsaCapabilityConfig_minPower;
      mandatory true;
    }
    leaf maxPower {
      description "Upper level of UL power range. Trigger information parameter.";
      type erienmnrmrmeulspectrumanalyzer:ddt-RmeUlSpectrumAnalyzer_UlsaCapabilityConfig_maxPower;
      mandatory true;
    }
    leaf-list maxNumSamplings {
      min-elements 0;
      max-elements 64;
      description "Number of sampling values in sample file. LTE 64K and WCDMA 40K spectrum information parameters.";
      type uint32;
    }
    leaf-list minFrequency {
      min-elements 0;
      max-elements 64;
      description "Lower RF range for RF branch. Spectrum information parameter.";
      type uint32;
    }
  } // end 'grouping struct-UlsaCapabilityConfig'
  grouping struct-CapabilityConfigData {
    description "Returns value of action getSamplingCapability that fetches UL Spectrum Analyzer capabilities from radio and returns result in an array of struct CapabilityConfigData.";
    leaf numSpectrumTypes {
      description "Number of spectrum types for RF branch.";
      type erienmnrmrmeulspectrumanalyzer:ddt-RmeUlSpectrumAnalyzer_CapabilityConfigData_numSpectrumTypes;
      mandatory true;
    }
    leaf numTriggerTypes {
      description "Number of trigger types for RF branch.";
      type erienmnrmrmeulspectrumanalyzer:ddt-RmeUlSpectrumAnalyzer_CapabilityConfigData_numTriggerTypes;
      mandatory true;
    }
    leaf measurementPort {
      description "LDN of RfPort for CPRI radio or LDN of Transceiver for eCPRI radio.";
      type erienmnrmrmeulspectrumanalyzer:ddt-RmeUlSpectrumAnalyzer_CapabilityConfigData_measurementPort;
      mandatory true;
    }
    leaf-list maxFrequency {
      min-elements 0;
      max-elements 64;
      description "Upper RF range for RF branch. Spectrum information parameter.";
      type int32;
    }
    leaf trigger1DataDefined {
      description "Indicates if valid trigger1 data is included for measurementPort.";
      type boolean;
      mandatory true;
    }
    leaf-list samplingRate {
      min-elements 0;
      max-elements 64;
      description "Different sampling rate values for ADC and filter branch. Spectrum information parameter.";
      type uint32;
    }
    leaf-list flatGainBW {
      min-elements 0;
      max-elements 64;
      description "Flat gain portion of bandwidth that can be configured for associated carrier. Spectrum information parameter.";
      type uint32;
    }
    leaf minPower {
      description "Lower level of UL power range. Trigger information parameter.";
      type erienmnrmrmeulspectrumanalyzer:ddt-RmeUlSpectrumAnalyzer_CapabilityConfigData_minPower;
      mandatory true;
    }
    leaf maxPower {
      description "Upper level of UL power range. Trigger information parameter.";
      type erienmnrmrmeulspectrumanalyzer:ddt-RmeUlSpectrumAnalyzer_CapabilityConfigData_maxPower;
      mandatory true;
    }
    leaf-list maxNumSamplings {
      min-elements 0;
      max-elements 64;
      description "Number of sampling values in sample file. NR 40K, LTE 40K, LTE 64K and WCDMA 40K spectrum information parameters.";
      type uint32;
    }
    leaf-list minFrequency {
      min-elements 0;
      max-elements 64;
      description "Lower RF range for RF branch. Spectrum information parameter.";
      type uint32;
    }
  } // end 'grouping struct-CapabilityConfigData'
  grouping moc-UlSpectrumAnalyzer-keys {
    description "Key(s) for MOC UlSpectrumAnalyzer";
    leaf id {
      erienmyext:no-notification;
      description "The value component of the RDN.\n";
      mandatory true;
      yexte:ecim-name ulSpectrumAnalyzerId;
      type string;
    }
  } // end 'grouping moc-UlSpectrumAnalyzer-keys'
  grouping moc-UlSpectrumAnalyzer {
    description "This MO is used when requesting UL spectrum sampling for one specified radio unit and to store the sampling result file(s) in a SMRS Server. The MO also allows queries to be sent to any radio unit for availible UL spectrum sampling capabilities.\n";
    leaf samplingType {
      erienmyext:no-notification;
      config false;
      description "Type of sampling operation last ordered. Before any sample is requested, value is SNAPSHOT_SAMPLING.";
      type erienmnrmrmeulspectrumanalyzer:enum-UlSpectrumSamplingType;
    }
    leaf targetMeasurementPort {
      erienmyext:no-notification;
      config false;
      description "Shows the measurementPort last targeted for sample request. Value is LDN of targeted RfPort for CPRI radio or LDN of targeted Transceiver for eCPRI radio.\nBefore any sampling is requested, the value is empty string.";
      type string;
    }
    leaf filename {
      config false;
      description "When each sampling run is finished, filename is updated with new collected file name. For continuous sampling, only latest file name is used. ";
      notife:notifiable-state-data true;
      type string;
    }
    leaf targetRfPort {
      status deprecated {
        yexte:status-information "Since 20.Q4. Replaced by targetMeasurementPort. Planned to be removed.";
      }
      erienmyext:no-notification;
      config false;
      description "Shows the RfPort last targeted for sample request. Value is LDN of the targeted RfPort for CPRI radio. Before any sampling is requested, the value is empty string.\n";
      type string;
    }
    leaf ulSpectrumSamplingStatus {
      config false;
      description "Status of latest action. ";
      notife:notifiable-state-data true;
      type erienmnrmrmeulspectrumanalyzer:enum-TcpStatus;
    }
    leaf info {
      config false;
      description "Information on the reason for latest unsuccessful action.";
      notife:notifiable-state-data true;
      type erienmnrmrmeulspectrumanalyzer:enum-InfoType;
    }
    action stopUlsaSampling {
      description "Stops a continuous sampling or preempts a conditional sampling.";
      input {
        leaf targetRfPort {
          mandatory true;
          description "LDN value of targeted RfPort to stop sampling.";
          type erienmnrmrmeulspectrumanalyzer:ddt-UlSpectrumAnalyzer_stopUlsaSampling_targetRfPort;
        }
      }
    }
    action startUlsaSampling {
      description "Requests one or several UL spectrum samples to be collected from radio unit and stored on an SMRS server.\nFile name is displayed in filename.";
      input {
        leaf samplingType {
          mandatory true;
          description "Type of sampling. Possible values are SNAPSHOT_SAMPLING, CONTINUOUS_SAMPLING or CONDITIONAL_SAMPLING.";
          type erienmnrmrmeulspectrumanalyzer:enum-UlSpectrumSamplingType;
          default SNAPSHOT_SAMPLING;
        }
        leaf resolutionBandwidth {
          mandatory true;
          description "Must be a non-zero positive number.";
          type erienmnrmrmeulspectrumanalyzer:ddt-UlSpectrumAnalyzer_startUlsaSampling_resolutionBandwidth;
        }
        leaf samplingTimeout {
          mandatory true;
          description "Maximum waiting time for a specified trigger condition to happen or maximum duration of a continuous sampling type. Range is 10-7200. Recommended value is 1000 seconds for CONDITIONAL_SAMPLING and 3600 seconds for CONTINUOUS_SAMPLING. Parameter has no meaning for samplingType SNAPSHOT_SAMPLING.";
          type erienmnrmrmeulspectrumanalyzer:ddt-UlSpectrumAnalyzer_startUlsaSampling_samplingTimeout;
        }
        leaf ipAddress {
          mandatory true;
          description "IP address for SMRS server, used for measurement files. Required for all sampling types.";
          type erienmnrmrmeulspectrumanalyzer:ddt-IpDNSAddress;
        }
        leaf powerLevel {
          mandatory true;
          description "Power trigger threshold at antenna reference point. Used for CONDITIONAL_SAMPLING. The parameter has no meaning for other samplingTypes. Value must be specified in range of parameters minPower and maxPower received from action getUlsaSamplingCapability. For CONDITIONAL_SAMPLING measurement trigger powerLevel is valid when parameter triggerTimeOfDay is set to ff:ff:ff.fff.";
          type erienmnrmrmeulspectrumanalyzer:ddt-UlSpectrumAnalyzer_startUlsaSampling_powerLevel;
        }
        leaf uploadDirectory {
          mandatory true;
          description "Path to directory in SMRS server where sampling results are stored. Required for all sampling types.";
          type string;
        }
        leaf samplingInterval {
          mandatory true;
          description "Delay time after one sampling is finished until start of next sampling for samplingType value CONTINUOUS_SAMPLING. Parameter has no meaning for other samplingTypes. Value 0 means continuous best effort. ";
          type erienmnrmrmeulspectrumanalyzer:ddt-UlSpectrumAnalyzer_startUlsaSampling_samplingInterval;
        }
        leaf password {
          mandatory true;
          description "Password for connecting to SMRS server. Required for all sampling types.";
          type erienmnrmrmeulspectrumanalyzer:ddt-EcimPasswordString;
        }
        leaf targetRfPort {
          mandatory true;
          description "RF port to be used for sampling. LDN value of targeted RfPort.\nRequired for all sampling types.";
          type erienmnrmrmeulspectrumanalyzer:ddt-UlSpectrumAnalyzer_startUlsaSampling_targetRfPort;
        }
        leaf displayedBandwidth {
          mandatory true;
          description "Value 0 means display is not required.";
          type erienmnrmrmeulspectrumanalyzer:ddt-UlSpectrumAnalyzer_startUlsaSampling_displayedBandwidth;
        }
        leaf centerFrequency {
          mandatory true;
          description "Value must be specified in range of parameters minFrequency and maxFrequency received as a return value from action getUlsaSamplingCapability.";
          type erienmnrmrmeulspectrumanalyzer:ddt-UlSpectrumAnalyzer_startUlsaSampling_centerFrequency;
        }
        leaf triggerTimeOfDay {
          mandatory true;
          description "Time in form of hh:mm:ss.sss when a sampling can be requested from radio. Used for CONDITIONAL_SAMPLING. Parameter has no meaning for other samplingTypes. Value ff:ff:ff.fff means not used.";
          type erienmnrmrmeulspectrumanalyzer:ddt-UlSpectrumAnalyzer_startUlsaSampling_triggerTimeOfDay;
        }
        leaf username {
          mandatory true;
          description "User name for connecting to SMRS server. Required for all sampling types.";
          type string;
        }
      }
    }
    action getUlsaSamplingCapability {
      description "Fetches UL spectrum analyzer capabilities from radio and returns result in an array of struct UlsaCapabilityConfig. When radio has no measurable spectrum types in any RF branch, size of returning array equals 0.";
      input {
        leaf targetRadioUnit {
          mandatory true;
          description "targetRadioUnit is set to LDN for radio FieldReplaceableUnit MO.";
          type erienmnrmrmeulspectrumanalyzer:ddt-UlSpectrumAnalyzer_getUlsaSamplingCapability_targetRadioUnit;
        }
      }
      output {
        list result {
          min-elements 0;
          max-elements 8;
          key auto-generated-struct-key;
          leaf auto-generated-struct-key {
            type uint16;
            description "This leaf has been injected to allow for struct instances in a sequence to be ordered.";
            mandatory true;
          }
          uses erienmnrmrmeulspectrumanalyzer:struct-UlsaCapabilityConfig;
          erienmyext:enm-type STRUCT;
        } // end 'list result'
      }
    }
    action getSamplingCapability {
      description "Fetches UL spectrum analyzer capabilities from radio and returns result in an array of struct CapabilityConfigData. When radio has no measurable spectrum types in any RF branch, size of returning array equals 0.";
      input {
        leaf targetRadioUnit {
          mandatory true;
          description "targetRadioUnit is set to LDN for radio FieldReplaceableUnit MO.";
          type erienmnrmrmeulspectrumanalyzer:ddt-UlSpectrumAnalyzer_getSamplingCapability_targetRadioUnit;
        }
      }
      output {
        list result {
          min-elements 0;
          max-elements 8;
          key auto-generated-struct-key;
          leaf auto-generated-struct-key {
            type uint16;
            description "This leaf has been injected to allow for struct instances in a sequence to be ordered.";
            mandatory true;
          }
          uses erienmnrmrmeulspectrumanalyzer:struct-CapabilityConfigData;
          erienmyext:enm-type STRUCT;
        } // end 'list result'
      }
    }
    action stopSampling {
      description "Stops a continuous sampling or preempts a conditional sampling.";
    }
    action startSampling {
      description "Requests one or several UL spectrum samples to be collected from radio unit and stored on an SMRS server.\nFile name is displayed in filename.";
      input {
        leaf samplingType {
          mandatory true;
          description "Type of sampling. Possible values are SNAPSHOT_SAMPLING, CONTINUOUS_SAMPLING or CONDITIONAL_SAMPLING.";
          type erienmnrmrmeulspectrumanalyzer:enum-UlSpectrumSamplingType;
          default SNAPSHOT_SAMPLING;
        }
        leaf resolutionBandwidth {
          mandatory true;
          description "Must be a non-zero positive number.";
          type erienmnrmrmeulspectrumanalyzer:ddt-UlSpectrumAnalyzer_startSampling_resolutionBandwidth;
        }
        leaf targetMeasurementPort {
          mandatory true;
          description "Measurement port to be used for sampling. LDN value of targeted RfPort for CPRI radio, or LDN value of targeted Transceiver for eCPRI radio.\nRequired for all sampling types.";
          type erienmnrmrmeulspectrumanalyzer:ddt-UlSpectrumAnalyzer_startSampling_targetMeasurementPort;
        }
        leaf samplingTimeout {
          mandatory true;
          description "Maximum waiting time for a specified trigger condition to happen or maximum duration of a continuous sampling type. Range is 10-7200. Recommended value is 1000 seconds for CONDITIONAL_SAMPLING and 3600 seconds for CONTINUOUS_SAMPLING. Parameter has no meaning for samplingType SNAPSHOT_SAMPLING.";
          type erienmnrmrmeulspectrumanalyzer:ddt-UlSpectrumAnalyzer_startSampling_samplingTimeout;
        }
        leaf ipAddress {
          mandatory true;
          description "IP address for SMRS server, used for measurement files. Required for all sampling types. ";
          type erienmnrmrmeulspectrumanalyzer:ddt-IpDNSAddress;
        }
        leaf powerLevel {
          mandatory true;
          description "Power trigger threshold at antenna reference point. Used for CONDITIONAL_SAMPLING. Parameter has no meaning for other samplingTypes. Value must be specified in range of parameters minPower and maxPower received from action getSamplingCapability. For CONDITIONAL_SAMPLING, measurement trigger powerLevel is valid when parameter triggerTimeOfDay is set to ff:ff:ff.fff.";
          type erienmnrmrmeulspectrumanalyzer:ddt-UlSpectrumAnalyzer_startSampling_powerLevel;
        }
        leaf uploadDirectory {
          mandatory true;
          description "Path to directory in SMRS server where sampling results are stored. Required for all sampling types.";
          type string;
        }
        leaf samplingInterval {
          mandatory true;
          description "Delay time after one sampling is finished until start of next sampling for samplingType value CONTINUOUS_SAMPLING. Parameter has no meaning for other samplingTypes. Value 0 means continuous best effort.";
          type erienmnrmrmeulspectrumanalyzer:ddt-UlSpectrumAnalyzer_startSampling_samplingInterval;
        }
        leaf password {
          mandatory true;
          description "Password for connecting to SMRS server. Required for all sampling types.";
          type erienmnrmrmeulspectrumanalyzer:ddt-EcimPasswordString;
        }
        leaf displayedBandwidth {
          mandatory true;
          description "Value 0 means display is not required.";
          type erienmnrmrmeulspectrumanalyzer:ddt-UlSpectrumAnalyzer_startSampling_displayedBandwidth;
        }
        leaf centerFrequency {
          mandatory true;
          description "Value must be specified in range of parameters minFrequency and maxFrequency received as a return value from action getSamplingCapability. ";
          type erienmnrmrmeulspectrumanalyzer:ddt-UlSpectrumAnalyzer_startSampling_centerFrequency;
        }
        leaf triggerTimeOfDay {
          mandatory true;
          description "Time in form of hh:mm:ss.sss when a sampling can be requested from radio. Used for CONDITIONAL_SAMPLING. Parameter has no meaning for other samplingTypes. Value ff:ff:ff.fff means not used. ";
          type erienmnrmrmeulspectrumanalyzer:ddt-UlSpectrumAnalyzer_startSampling_triggerTimeOfDay;
        }
        leaf username {
          mandatory true;
          description "User name for connecting to SMRS server. Required for all sampling types.";
          type string;
        }
      }
    }
  } // end 'grouping moc-UlSpectrumAnalyzer'
  augment /erienmnrmcomtop:ManagedElement/erienmnrmrmesupport:NodeSupport {
    list UlSpectrumAnalyzer {
      key id;
      max-elements 4;
      description "This MO is used when requesting UL spectrum sampling for one specified radio unit and to store the sampling result file(s) in a SMRS Server. The MO also allows queries to be sent to any radio unit for availible UL spectrum sampling capabilities.\n";
      erienmyext:enm-type MOC;
      uses moc-UlSpectrumAnalyzer-keys;
      container attributes {
        description "Attributes for UlSpectrumAnalyzer";
        uses moc-UlSpectrumAnalyzer;
      } // end 'container attributes'
    } // end 'list UlSpectrumAnalyzer'
  }
}
