module ericsson-enm-RtnTwamp {
  yang-version 1.1;
  namespace urn:rdns:com:ericsson:ericsson-enm-RtnTwamp;
  prefix erienmnrmrtntwamp;
  yexte:ecim-name RtnTwamp;
  revision 2351-11-28 {
    yexte:version 1;
    yexte:release 7;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RtnL3Router {
    prefix erienmnrmrtnl3router;
  }
  typedef enum-ResponderType {
    description "Responder type.";
    type enumeration {
      enum LIGHT {
        description "TWAMP light stateful.
\n
\nLight (stateful) : the sequence number in the reflected packet is generated by the responder, which enables measurement of packet loss in forward and reverse direction.";
        value 1;
      }
      enum LIGHT_SL {
        description "TWAMP light stateless.
\n
\nLight-SL (stateless) : the sequence number is copied from the sender's test packet to the reflected packet, thus it is only possible to measure round trip packet loss.";
        value 2;
      }
    }
  }
  typedef ddt-RtnTwamp_TwampLightResponder_udpPort {
    type uint16 {
      range "4000..4007 | 5000..5007";
    }
  }
  typedef ddt-RtnTwamp_TwampLightResponder_userLabel {
    type string {
      length 1..128;
    }
  }
  grouping moc-TwampLightResponder-keys {
    description "Key(s) for MOC TwampLightResponder";
    leaf id {
      erienmyext:no-notification;
      description "Value component of the RDN.";
      mandatory true;
      yexte:ecim-name twampLightResponderId;
      type string;
    }
  } // end 'grouping moc-TwampLightResponder-keys'
  grouping moc-TwampLightResponder {
    description "Two Way Active Measurement Protocol Responder.
\n
\nThis MO represents the session responder functionality (according to RFC 5357) in a TWAMP light architecture.
\nWhen created, the node reflects TWAMP packets received on the specified UDP port.";
    leaf userLabel {
      description "Label for free use.";
      type erienmnrmrtntwamp:ddt-RtnTwamp_TwampLightResponder_userLabel;
    }
    leaf ipAddress {
      description "Responder assigned IP address.
\n
\nValid reference is an AddressIpv4 or an AddressIpv6 MO in the L3 infra fragment.";
      mandatory true;
      yexte:dependencies "The combination of udpPort and ipAddress for TwampLightResponder must be unique in the same router.\nTwampLightResponder can refer only to an ipAddress in the same router.";
      erienmyext:enm-type MOREF;
      type string;
    }
    leaf udpPort {
      description "Specify a UDP port to send and receive TWAMP test packets.";
      mandatory true;
      yexte:dependencies "The combination of udpPort and ipAddress for TwampLightResponder must be unique in the same router.";
      type erienmnrmrtntwamp:ddt-RtnTwamp_TwampLightResponder_udpPort;
    }
    leaf responderType {
      config false;
      description "Type of the responder.";
      notife:notifiable-state-data true;
      type erienmnrmrtntwamp:enum-ResponderType;
    }
  } // end 'grouping moc-TwampLightResponder'
  augment /erienmnrmcomtop:ManagedElement/erienmnrmcomtop:Transport/erienmnrmrtnl3router:Router {
    list TwampLightResponder {
      key id;
      max-elements 8;
      description "Two Way Active Measurement Protocol Responder.
\n
\nThis MO represents the session responder functionality (according to RFC 5357) in a TWAMP light architecture.
\nWhen created, the node reflects TWAMP packets received on the specified UDP port.";
      status deprecated;
      erienmyext:enm-type MOC;
      uses moc-TwampLightResponder-keys;
      container attributes {
        description "Attributes for TwampLightResponder";
        uses moc-TwampLightResponder;
      } // end 'container attributes'
    } // end 'list TwampLightResponder'
  }
}
