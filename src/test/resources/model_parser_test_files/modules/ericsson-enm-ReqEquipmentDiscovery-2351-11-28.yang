module ericsson-enm-ReqEquipmentDiscovery {
  yang-version 1.1;
  namespace urn:rdns:com:ericsson:ericsson-enm-ReqEquipmentDiscovery;
  prefix erienmnrmreqequipmentdiscovery;
  yexte:ecim-name ReqEquipmentDiscovery;
  revision 2351-11-28 {
    yexte:version 1;
    yexte:release 6;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RmeSupport {
    prefix erienmnrmrmesupport;
  }
  typedef enum-EquipmentDiscoveryStatus {
    description "Status of Equipment Discovery operations.";
    type enumeration {
      enum UNKNOWN {
        description "Status for Equipment Discovery is unknown.";
        value 0;
      }
      enum SCAN_STARTED {
        description "Antenna Device Scan is started.";
        value 1;
      }
      enum SCAN_FINISHED {
        description "Antenna Device Scan is finished.";
        value 2;
      }
      enum SCAN_FAILED {
        description "Antenna Device Scan failed.";
        value 3;
      }
      enum CONFIGURING {
        description "Automated configuration of AISG units is in progress.";
        value 4;
      }
      enum CONFIG_PARTIAL {
        description "AISG units cannot be configured for at least one radio.";
        value 5;
      }
      enum CONFIG_MISSING_DEPENDENCY {
        description "Automated configuration of AISG units is finished but some MO references cannot be resolved.";
        value 6;
      }
      enum CONFIG_FAILED {
        description "Automated configuration of AISG units failed.";
        value 7;
      }
      enum MO_CREATION_FAILURE {
        description "Automated configuration of AISG units finished with MO creation failure. One of the MOs could not be created.";
        value 8;
      }
      enum SCANNED_AND_CONFIGURED {
        description "Antenna equipment is scanned and configured.";
        value 9;
      }
    }
  }
  typedef enum-TcpStatus {
    description "The status of the TCP.";
    type enumeration {
      enum UNKNOWN {
        value 0;
      }
      enum STARTED {
        value 1;
      }
      enum FINISHED {
        value 2;
      }
      enum FAILED {
        value 3;
      }
    }
  }
  typedef enum-DeviceScanPortConfiguration {
    description "Port Configuration used for full device scan.";
    type enumeration {
      enum SCAN_ALL_PORTS_WITH_DEFAULT_VOLTAGE {
        description "All ports are scanned. No change to default voltage configuration. ";
        status deprecated;
        value 1;
      }
      enum SCAN_ALL_PORTS_WITH_CHOSEN_VOLTAGE {
        description "All ports are scanned using chosen voltage.";
        value 2;
      }
      enum SCAN_RET_PORT_ONLY {
        description "Sets output DC voltage to 0 for RF Ports. Only RET ports are scanned.";
        value 0;
      }
    }
  }
  typedef enum-DeviceScanDcVoltage {
    description "The value represents the nominal DC voltage supplied to the antenna system during device scan.\nPlease note that choosing a higher voltage than the maximum voltage capability of the antenna equipment may cause permanent damage to the antenna equipment.\nChoosing a too low voltage may cause unsuccessful result for large installations due to maximum current supply limitation in the Radio.";
    type enumeration {
      enum DC_12V {
        value 0;
      }
      enum DC_17V {
        value 1;
      }
      enum DC_30V {
        value 2;
      }
    }
  }
  typedef enum-AisgDataRate {
    description "The bit rate used for communication with the AISG units.";
    type enumeration {
      enum BITRATE_9600 {
        description "The transmission bit rate is 9600 bps.";
        value 0;
      }
      enum BITRATE_38400 {
        description "The transmission bit rate is 38400 bps.";
        value 1;
      }
      enum BITRATE_115200 {
        description "The transmission bit rate is 115200 bps.";
        value 2;
      }
    }
  }
  typedef ddt-EquipmentDiscovery_antennaDeviceScan_path {
    type string {
      length 0..255;
    }
  }
  typedef ddt-EquipmentDiscovery_antennaDeviceScan_userName {
    type string {
      length 0..254;
    }
  }
  typedef ddt-ReqEquipmentDiscovery_EquipmentDiscovery_sftpServerIpAddress {
    type string {
      length 0..255;
    }
  }
  typedef ddt-ReqEquipmentDiscovery_EquipmentDiscovery_sftpServerPath {
    type string {
      length 0..255;
    }
  }
  typedef ddt-ReqEquipmentDiscovery_EquipmentDiscovery_sftpUsername {
    type string {
      length 0..254;
    }
  }
  typedef ddt-EquipmentDiscovery_antennaDeviceScan_password {
    type string {
      length 0..20;
    }
  }
  typedef ddt-EcimPasswordString {
    description "This type enables secure handling of passwords.";
    type string {
      length 0..20;
    }
  }
  typedef ddt-EquipmentDiscovery_antennaDeviceScan_server {
    type string {
      length 0..255;
    }
  }
  grouping moc-EquipmentDiscovery-keys {
    description "Key(s) for MOC EquipmentDiscovery";
    leaf id {
      erienmyext:no-notification;
      description "The value component of the RDN.";
      mandatory true;
      yexte:ecim-name equipmentDiscoveryId;
      type string;
    }
  } // end 'grouping moc-EquipmentDiscovery-keys'
  grouping moc-EquipmentDiscovery {
    description "Used to perform AISG Device Scan. Scan finds all radio RF and RET ports in RBS. It lists all AISG units with their unique HW IDs and how they are connected. Operator can select file storage.";
    leaf sftpServerIpAddress {
      description "IP address or hostname of SFTP server that stores file.";
      yexte:takes-effect "Next full or background scan";
      type erienmnrmreqequipmentdiscovery:ddt-ReqEquipmentDiscovery_EquipmentDiscovery_sftpServerIpAddress;
    }
    leaf sftpPassword {
      description "Password to SFTP server that stores file.";
      yexte:takes-effect "Next full or background scan";
      type erienmnrmreqequipmentdiscovery:ddt-EcimPasswordString;
    }
    leaf portConfiguration {
      description "Can choose which ports are configured with given DC voltage.
\nNot used by Device Scan in background.";
      yexte:takes-effect "Next full scan";
      type erienmnrmreqequipmentdiscovery:enum-DeviceScanPortConfiguration;
      default SCAN_ALL_PORTS_WITH_CHOSEN_VOLTAGE;
    }
    leaf antennaDeviceScanStatus {
      status deprecated {
        yexte:status-information "Since 20.Q3. Replaced by equipmentDiscoveryStatus. Planned to be removed.";
      }
      config false;
      description "Status of ongoing performFullAntennaDeviceScan operation and Antenna Device Scan in background.";
      notife:notifiable-state-data true;
      type erienmnrmreqequipmentdiscovery:enum-TcpStatus;
    }
    leaf equipmentDiscoveryStatus {
      config false;
      description "Status of Equipment Discovery operations, including Antenna Device Scan and automated configuration of AISG devices.";
      notife:notifiable-state-data true;
      type erienmnrmreqequipmentdiscovery:enum-EquipmentDiscoveryStatus;
    }
    leaf autoCreateAisgUnits {
      description "Whether detection of unconfigured AISG units resulting in autocreation is enabled for corresponding MOs.";
      type boolean;
      default false;
    }
    leaf sftpServerPath {
      description "File path to result file.";
      yexte:takes-effect "Next full or background scan";
      type erienmnrmreqequipmentdiscovery:ddt-ReqEquipmentDiscovery_EquipmentDiscovery_sftpServerPath;
    }
    leaf antennaDeviceScanInBackground {
      description "If true, Antenna Device Scan is run periodically in background. Scan results contain only ALDs that are not configured. Only configured ports are scanned.
\nResult file is stored in SFTP location indicated by sftpServerIpAddress and sftpServerPath.";
      yexte:precondition "Attributes sftpServerIpAddress, sftpServerPath, sftpUsername, sftpPassword must be set in order to start Antenna Device Scan in background.";
      type boolean;
      default false;
    }
    leaf dataRate {
      description "Bit rate used for communication with AISG units during execution of performFullAntennaDeviceScan action.
\nNot used by Device Scan in background.";
      yexte:takes-effect "Next full scan";
      type erienmnrmreqequipmentdiscovery:enum-AisgDataRate;
      default BITRATE_9600;
    }
    leaf portVoltage {
      description "Nominal DC antenna voltage supplied to system during execution of performFullAntennaDeviceScan action.
\n
\nNOTE: High voltage can cause permanent damage to some antenna system equipment.
\nLow voltage can cause unsuccessful result for large antenna system configurations.
\n
\nNot used by Device Scan in background.";
      yexte:disturbances "High voltage can cause permanent damage to antenna system equipment.";
      yexte:takes-effect "Next full scan";
      type erienmnrmreqequipmentdiscovery:enum-DeviceScanDcVoltage;
      default DC_12V;
    }
    leaf sftpUsername {
      description "User name to SFTP server that stores file.";
      yexte:takes-effect "Next full or background scan";
      type erienmnrmreqequipmentdiscovery:ddt-ReqEquipmentDiscovery_EquipmentDiscovery_sftpUsername;
    }
    action performFullAntennaDeviceScan {
      description "Scans connected AISG units and stores results on the SFTP location indicated by sftpServerIpAddress and sftpServerPath. Contains unique unit ID, device type and how units are connected to RBS. Result is used to detect and correct configuration errors in antenna system, such as unique ID of cascaded ARET units.\nSFTP credentials are stored in the following attributes:\n- sftpServerIpAddress\n- sftpServerPath\n- sftpUsername\n- sftpPassword.\nScan state can be observed through attribute equipmentDiscoveryStatus. Complete scan can take several minutes.\n\nNOTE: Scan result is incomplete in the following cases:\n- If any connected device is not operational.\n- If connection to any device is broken.\n- If corresponding radio units do not support device scan.";
    }
    action antennaDeviceScan {
      description "Starts a scan of connected AISG units. The scan result is stored on the chosen FTP server. It contains the unique ID and device type of the detected units, and how the units are connected to the RBS. The result can be used to detect and correct configuration errors in the antenna system, such as the unique ID of cascaded ARET units.
\nIf any equipment connected to the antenna system is not rated for 30 Volts then there is a risk that it will be permanently damaged.
\nNote that the scan result is incomplete if any of the connected devices are not operational. This also applies if the connection to any device is broken, or if any of the corresponding radio units do not support device scan.
\nThe state of the scan can be observed through attribute antennaDeviceScanStatus. A complete scan can take several minutes.";
      input {
        leaf server {
          mandatory true;
          description "The IP address or hostname of the FTP server storing the file.";
          type erienmnrmreqequipmentdiscovery:ddt-EquipmentDiscovery_antennaDeviceScan_server;
        }
        leaf path {
          mandatory true;
          description "The file path where to store the result file.";
          type erienmnrmreqequipmentdiscovery:ddt-EquipmentDiscovery_antennaDeviceScan_path;
        }
        leaf password {
          mandatory true;
          description "The password to the FTP server storing the file.";
          type erienmnrmreqequipmentdiscovery:ddt-EquipmentDiscovery_antennaDeviceScan_password;
        }
        leaf dataRate {
          mandatory true;
          description "The bit rate used for communication with the AISG units during device scan.";
          type erienmnrmreqequipmentdiscovery:enum-AisgDataRate;
        }
        leaf portVoltage {
          mandatory true;
          description "The value represents the nominal DC voltage supplied to the antenna system during device scan. 
\nPlease note that choosing a higher voltage than the maximum voltage capability of the antenna equipment may cause permanent damage to the antenna equipment. 
\nChoosing a too low voltage may cause unsuccessful result for large installations due to maximum current supply limitation in the Radio.";
          type erienmnrmreqequipmentdiscovery:enum-DeviceScanDcVoltage;
        }
        leaf userName {
          mandatory true;
          description "The user name to the FTP server storing the file.";
          type erienmnrmreqequipmentdiscovery:ddt-EquipmentDiscovery_antennaDeviceScan_userName;
        }
      }
    }
  } // end 'grouping moc-EquipmentDiscovery'
  augment /erienmnrmcomtop:ManagedElement/erienmnrmrmesupport:NodeSupport {
    list EquipmentDiscovery {
      key id;
      max-elements 1;
      description "Used to perform AISG Device Scan. Scan finds all radio RF and RET ports in RBS. It lists all AISG units with their unique HW IDs and how they are connected. Operator can select file storage.";
      yexte:is-system-created;
      erienmyext:enm-type MOC;
      uses moc-EquipmentDiscovery-keys;
      container attributes {
        description "Attributes for EquipmentDiscovery";
        uses moc-EquipmentDiscovery;
      } // end 'container attributes'
    } // end 'list EquipmentDiscovery'
  }
}
