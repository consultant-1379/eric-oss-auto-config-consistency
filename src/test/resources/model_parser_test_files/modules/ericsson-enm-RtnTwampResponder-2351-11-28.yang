module ericsson-enm-RtnTwampResponder {
  yang-version 1.1;
  namespace urn:rdns:com:ericsson:ericsson-enm-RtnTwampResponder;
  prefix erienmnrmrtntwampresponder;
  yexte:ecim-name RtnTwampResponder;
  revision 2351-11-28 {
    yexte:version 1;
    yexte:release 1;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RtnL3Router {
    prefix erienmnrmrtnl3router;
  }
  typedef enum-ResponderType {
    description "Responder type.";
    type enumeration {
      enum LIGHT {
        description "TWAMP light stateful.
\n
\nLight (stateful) : the sequence number in the reflected packet is generated by the responder, which enables measurement of packet loss in forward and reverse direction.";
        value 1;
      }
      enum LIGHT_SL {
        description "TWAMP light stateless.
\n
\nLight-SL (stateless) : the sequence number is copied from the sender's test packet to the reflected packet, thus it is only possible to measure round trip packet loss.";
        value 2;
      }
    }
  }
  typedef ddt-RtnTwampResponder_TwampResponder_udpPort {
    type uint16 {
      range "4000..4007 | 5000..5007";
    }
  }
  typedef ddt-RtnTwampResponder_TwampResponder_userLabel {
    type string {
      length 1..128;
    }
  }
  grouping moc-TwampResponder-keys {
    description "Key(s) for MOC TwampResponder";
    leaf id {
      erienmyext:no-notification;
      description "Value component of the RDN.";
      mandatory true;
      yexte:ecim-name twampResponderId;
      type string;
    }
  } // end 'grouping moc-TwampResponder-keys'
  grouping moc-TwampResponder {
    description "Two Way Active Measurement Protocol Responder.
\n
\nThis MO represents the session responder functionality (according to RFC 5357) in a TWAMP light architecture.
\nWhen created, the node reflects TWAMP packets received on the specified UDP port.\n\nDependencies: TwampResponder and TwampLightResponder are mutually exclusive.";
    leaf userLabel {
      description "Label for free use.";
      type erienmnrmrtntwampresponder:ddt-RtnTwampResponder_TwampResponder_userLabel;
    }
    leaf ipAddress {
      description "Responder assigned IP address.
\n
\nValid reference is an AddressIpv4 or an AddressIpv6 MO in the L3 infra fragment.";
      mandatory true;
      yexte:dependencies "The combination of udpPort and ipAddress for TwampLightResponder must be unique in the same router.\nTwampLightResponder can refer only to an ipAddress in the same router.";
      erienmyext:enm-type MOREF;
      type string;
    }
    leaf udpPort {
      description "Specify a UDP port to send and receive TWAMP test packets.";
      mandatory true;
      yexte:dependencies "The combination of udpPort and ipAddress for TwampLightResponder must be unique in the same router.";
      type erienmnrmrtntwampresponder:ddt-RtnTwampResponder_TwampResponder_udpPort;
    }
    leaf responderType {
      config false;
      description "Type of the responder.";
      notife:notifiable-state-data true;
      type erienmnrmrtntwampresponder:enum-ResponderType;
    }
  } // end 'grouping moc-TwampResponder'
  augment /erienmnrmcomtop:ManagedElement/erienmnrmcomtop:Transport/erienmnrmrtnl3router:Router {
    list TwampResponder {
      key id;
      max-elements 8;
      description "Two Way Active Measurement Protocol Responder.
\n
\nThis MO represents the session responder functionality (according to RFC 5357) in a TWAMP light architecture.
\nWhen created, the node reflects TWAMP packets received on the specified UDP port.\n\nDependencies: TwampResponder and TwampLightResponder are mutually exclusive.";
      erienmyext:enm-type MOC;
      uses moc-TwampResponder-keys;
      container attributes {
        description "Attributes for TwampResponder";
        uses moc-TwampResponder;
      } // end 'container attributes'
    } // end 'list TwampResponder'
  }
}
