module ericsson-enm-ReqTransceiver {
  yang-version 1.1;
  namespace urn:rdns:com:ericsson:ericsson-enm-ReqTransceiver;
  prefix erienmnrmreqtransceiver;
  yexte:ecim-name ReqTransceiver;
  revision 2351-11-28 {
    yexte:version 1;
    yexte:release 4;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqFieldReplaceableUnit {
    prefix erienmnrmreqfieldreplaceableunit;
  }
  import ericsson-enm-ReqEquipment {
    prefix erienmnrmreqequipment;
  }
  typedef enum-MicroSleepTxRadioCapability {
    type enumeration {
      enum NO_SUPPORT {
        description "Radio can not support feature.";
        value 0;
      }
      enum FULL_SUPPORT {
        description "Radio can fully support feature.";
        value 1;
      }
      enum LIMITED_SUPPORT {
        description "Radio has limited support for feature because HW cannot save power on every symbol position.";
        value 2;
      }
    }
  }
  typedef enum-OperState {
    description "Operational states of a resource.";
    type enumeration {
      enum DISABLED {
        description "The resource is  totally inoperable.";
        value 0;
      }
      enum ENABLED {
        description "The resource is partially or fully operable.";
        value 1;
      }
    }
  }
  typedef enum-AvailStatus {
    description "The availability status is used to qualify the operational state.
\n It indicates why the operational state has changed its value. ";
    type enumeration {
      enum IN_TEST {
        description "The resource is undergoing a test procedure. 
\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.
\nThe semantics are defined in CCITT Rec. X.735 | ISO/IEC 10164-6. ";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef enum-MicroSleepTxRadioStatus {
    type enumeration {
      enum ENABLED {
        description "Feature support in radio is enabled.";
        value 0;
      }
      enum DISABLED {
        description "Feature support in radio is disabled because some other feature is prioritized.";
        value 1;
      }
    }
  }
  typedef ddt-ReqTransceiver_Transceiver_minTotalTilt {
    type int32 {
      range -900..900;
    }
  }
  typedef ddt-ReqTransceiver_Transceiver_dlFrequencyRanges {
    type string {
      length 0..256;
    }
  }
  typedef ddt-ReqTransceiver_Transceiver_mechanicalAntennaTilt {
    type int32 {
      range -900..900;
    }
  }
  typedef ddt-ReqTransceiver_Transceiver_maxTotalTilt {
    type int32 {
      range -900..900;
    }
  }
  typedef ddt-ReqTransceiver_Transceiver_totalTilt {
    type int32 {
      range -900..900;
    }
  }
  typedef ddt-ReqTransceiver_Transceiver_ulFrequencyRanges {
    type string {
      length 0..256;
    }
  }
  grouping moc-Transceiver-keys {
    description "Key(s) for MOC Transceiver";
    leaf id {
      erienmyext:no-notification;
      description "The value component of the RDN.";
      mandatory true;
      yexte:ecim-name transceiverId;
      type string;
    }
  } // end 'grouping moc-Transceiver-keys'
  grouping moc-Transceiver {
    description "This MO models the UL and DL antenna streams in a radio with an embedded antenna system.";
    leaf minTotalTilt {
      description "Minimum antenna elevation including installed tilt and tilt applied by Remote Electrical Tilt (RET). Described by inclination of antenna main beam maximum with respect to horizontal plane. A signed value. Positive indicates downtilt, negative indicates uptilt.\nLimitation on total tilt is found by following equation:\nTotalTilt = AntennaUnit.mechanicaAntennalTilt + RetSubunit.electricalTilt\nIf RET not installed, total tilt value does not necessarily account for inclination the antenna beam can have by default, with respect to orthogonal direction to antenna element axis.";
      type erienmnrmreqtransceiver:ddt-ReqTransceiver_Transceiver_minTotalTilt;
      default -900;
    }
    leaf dlFrequencyRanges {
      config false;
      description "Multiple downlink frequency ranges that transceiver supports, displayed as string.\nFor transceiver with no valid downlink frequency range, the string shows \"Not supported\". ";
      notife:notifiable-state-data true;
      type erienmnrmreqtransceiver:ddt-ReqTransceiver_Transceiver_dlFrequencyRanges;
    }
    leaf retSubUnitRef {
      description "Refers to an instance of a retSubUnit from which this antenna near unit is controlled and supplied with power.";
      erienmyext:enm-type MOREF;
      type string;
    }
    leaf mechanicalAntennaTilt {
      description "Fixed antenna tilt of installation, defined as inclination of antenna element axis with respect to vertical plane.\nA signed value. Positive indicates downtilt, negative indicates uptilt.";
      type erienmnrmreqtransceiver:ddt-ReqTransceiver_Transceiver_mechanicalAntennaTilt;
      default 0;
    }
    leaf microSleepTxRadioCapability {
      config false;
      description "Capability in radio to support Micro Sleep Tx functionality.";
      notife:notifiable-state-data true;
      type erienmnrmreqtransceiver:enum-MicroSleepTxRadioCapability;
    }
    leaf ulFrequencyRanges {
      config false;
      description "Multiple uplink frequency ranges that transceiver supports, displayed as string.\nFor transceiver with no valid uplink frequency range, the string shows \"Not supported\". ";
      notife:notifiable-state-data true;
      type erienmnrmreqtransceiver:ddt-ReqTransceiver_Transceiver_ulFrequencyRanges;
    }
    leaf microSleepTxRadioStatus {
      config false;
      description "Current status in radio for supporting Micro Sleep Tx functionality.";
      notife:notifiable-state-data true;
      type erienmnrmreqtransceiver:enum-MicroSleepTxRadioStatus;
    }
    leaf totalTilt {
      config false;
      description "Total antenna elevation including installed tilt and tilt applied by Remote Electrical Tilt (RET).\nTotal tilt is defined as inclination of antenna main beam maximum with respect to horizontal plane.\nTilt is a signed value. Positive indicates downtilt, negative indicates uptilt. Can be found by following equation:\ntotalTilt = AntennaUnit.mechanicaAntennalTilt + RetSubunit.electricalTilt\nIf RET not installed, this value does not account for inclination that antenna beam can have by default, with respect to orthogonal direction to antenna element axis.";
      notife:notifiable-state-data true;
      type erienmnrmreqtransceiver:ddt-ReqTransceiver_Transceiver_totalTilt;
    }
    leaf-list reservedBy {
      min-elements 0;
      erienmyext:no-notification;
      config false;
      description "Contains a list of MO instances that reserve this MO instance.";
      erienmyext:enm-type MOREF;
      type string;
    }
    leaf operationalState {
      config false;
      description "The operational state.";
      notife:notifiable-state-data true;
      type erienmnrmreqtransceiver:enum-OperState;
    }
    leaf-list availabilityStatus {
      min-elements 0;
      config false;
      description "The availability status.\nIt contains details about operationalState.";
      notife:notifiable-state-data true;
      type erienmnrmreqtransceiver:enum-AvailStatus;
    }
    leaf maxTotalTilt {
      description "Maximum antenna elevation including installed tilt and tilt applied by Remote Electrical Tilt (RET).\nDescribed by inclination of antenna main beam maximum with respect to horizontal plane. A signed value. Positive indicates downtilt, negative indicates uptilt.\nSets a limitation on total tilt which is given by following formula:\nTotalTilt = AntennaUnit.mechanicaAntennalTilt + RetSubunit.electricalTilt\nIf RET not installed, this value does not account for inclination that antenna beam can have by default, with respect to orthogonal direction to antenna element axis.";
      type erienmnrmreqtransceiver:ddt-ReqTransceiver_Transceiver_maxTotalTilt;
      default 900;
    }
  } // end 'grouping moc-Transceiver'
  augment /erienmnrmcomtop:ManagedElement/erienmnrmreqequipment:Equipment/erienmnrmreqfieldreplaceableunit:FieldReplaceableUnit {
    list Transceiver {
      key id;
      description "This MO models the UL and DL antenna streams in a radio with an embedded antenna system.";
      erienmyext:enm-type MOC;
      uses moc-Transceiver-keys;
      container attributes {
        description "Attributes for Transceiver";
        uses moc-Transceiver;
      } // end 'container attributes'
    } // end 'list Transceiver'
  }
}
