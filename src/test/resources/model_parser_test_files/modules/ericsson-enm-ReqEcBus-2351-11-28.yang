module ericsson-enm-ReqEcBus {
  yang-version 1.1;
  namespace urn:rdns:com:ericsson:ericsson-enm-ReqEcBus;
  prefix erienmnrmreqecbus;
  yexte:ecim-name ReqEcBus;
  revision 2351-11-28 {
    yexte:version 3;
    yexte:release 0;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqEquipment {
    prefix erienmnrmreqequipment;
  }
  typedef ddt-RegExprEcBusConnectionType {
    description "Valid values: [EC,SAU]";
    type string {
      length 1..3;
    }
  }
  grouping moc-EcBus-keys {
    description "Key(s) for MOC EcBus";
    leaf id {
      erienmyext:no-notification;
      description "The value component of the RDN.";
      mandatory true;
      yexte:takes-effect Immediately;
      yexte:ecim-name ecBusId;
      type string;
    }
  } // end 'grouping moc-EcBus-keys'
  grouping moc-EcBus {
    description "Represents the EC bus used to communicate with the support system.";
    leaf ecBusConnectorRef {
      description "Reference to processing unit connected to EC bus in cabinet.";
      mandatory true;
      yexte:takes-effect Immediately;
      erienmyext:enm-type MOREF;
      type string;
    }
    leaf-list reservedBy {
      min-elements 0;
      erienmyext:no-notification;
      config false;
      description "Contains a list of MO instances that reserve this MO instance.
\n";
      yexte:takes-effect Immediately;
      erienmyext:enm-type MOREF;
      type string;
    }
    leaf equipmentSupportFunctionRef {
      description "References to the EquipmentSupportFunction MO instances that the EC bus belongs.";
      yexte:takes-effect Immediately;
      yexte:dependencies "This attribute is relevant when more than one MO EquipmentSupportFunction exists.  
\nThrows exception [InvalidReferenceException | IllegalRelationException]";
      erienmyext:enm-type MOREF;
      type string;
    }
    leaf ecBusConnectionType {
      description "Type of EC-bus connection.";
      type erienmnrmreqecbus:ddt-RegExprEcBusConnectionType;
      default EC;
    }
  } // end 'grouping moc-EcBus'
  augment /erienmnrmcomtop:ManagedElement/erienmnrmreqequipment:Equipment {
    list EcBus {
      key id;
      description "Represents the EC bus used to communicate with the support system.";
      erienmyext:enm-type MOC;
      uses moc-EcBus-keys;
      container attributes {
        description "Attributes for EcBus";
        uses moc-EcBus;
      } // end 'container attributes'
    } // end 'list EcBus'
  }
}
