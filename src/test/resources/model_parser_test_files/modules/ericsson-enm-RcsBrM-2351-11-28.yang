module ericsson-enm-RcsBrM {
  yang-version 1.1;
  namespace urn:rdns:com:ericsson:ericsson-enm-RcsBrM;
  prefix erienmnrmrcsbrm;
  yexte:ecim-name RcsBrM;
  revision 2351-11-28 {
    yexte:version 3;
    yexte:release 0;
    yexte:correction 4;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef enum-DayOfWeek {
    description "Presents the day of the week.";
    type enumeration {
      enum SUNDAY {
        description Sunday.;
        value 7;
      }
      enum MONDAY {
        description Monday.;
        value 1;
      }
      enum TUESDAY {
        description Tuesday.;
        value 2;
      }
      enum WEDNESDAY {
        description Wednesday.;
        value 3;
      }
      enum THURSDAY {
        description Thursday.;
        value 4;
      }
      enum FRIDAY {
        description Friday.;
        value 5;
      }
      enum SATURDAY {
        description Saturday.;
        value 6;
      }
      enum ALL {
        description "All days.";
        value 0;
      }
    }
  }
  typedef enum-BrmDeactivatePostAction {
    description "Indicates what to do in the post action phase of the deactivate step.
\nNOP means no operation.
\nCLEAR_LIST means clear the restoreEscalationList.
\nADD_BACKUP_TO_LIST means clear the restoreEscalationList then add the failsafe backup just created to the restoreEscalationList.";
    type enumeration {
      enum NOP {
        description "Do nothing.";
        value 1;
      }
      enum CLEAR_LIST {
        description "Clear the restoreEscalationList.
\n";
        value 2;
      }
      enum ADD_BACKUP_TO_LIST {
        description "Add the backup to the restoreEscalationList.";
        value 3;
      }
    }
  }
  typedef enum-UsageState {
    description "The usage state describes the usage of a resource.\nThe allowed values are defined by ITU-T X.731.";
    type enumeration {
      enum IDLE {
        description "The resource is not currently in use.\nDefined by ITU-T X.731.";
        value 0;
      }
      enum ACTIVE {
        description "The resource is in use and it has sufficient spare operating capacity.\nSpare operating capacity to provide for additional users simultaneously.\nDefined by ITU-T X.731.";
        value 1;
      }
      enum BUSY {
        description "The resource is in use, but it has no spare operating capacity.\nSpare operating capacity to provide for additional users at this instant.\nDefined by ITU-T X.731.";
        value 2;
      }
    }
  }
  typedef enum-ActionResultType {
    description "Lists the different results of an action.";
    type enumeration {
      enum SUCCESS {
        description "The asynchronous action ended with success.";
        value 1;
      }
      enum FAILURE {
        description "The asynchronous action ended with failure.";
        value 2;
      }
      enum NOT_AVAILABLE {
        description "No result is available yet.";
        value 3;
      }
    }
  }
  typedef enum-BrmBackupEncryptionMethod {
    description "Determines the encryption method to be used.
\nIn case the encryption is enabled for the particular scheduled backup.
\nThe available methods are:
\n - Using encryption key from URI
\n - Using a password to generate the encryption key.";
    type enumeration {
      enum PASSWORD {
        description "Specifies the Password method for encrypting the backup.
\nThe encryption key is generated from a password.";
        value 2;
      }
      enum URI {
        description "Specifies the URI method for encrypting the backup.
\nThe encryption key is obtained from URI.";
        value 1;
      }
    }
  }
  typedef enum-BrmBackupCreationType {
    description "Backup creation type.";
    type enumeration {
      enum MANUAL {
        description "Backup created via a manual operation. 
\nA backup of this creation type is subject to housekeeping based on \"maximum number\" defined in BrmBackupHousekeeping MO and \"remove-oldest\" policy.";
        value 1;
      }
      enum SCHEDULED {
        description "Backup created automatically based on a preconfigured schedule. 
\nA backup of this creation type is subject to housekeeping based on \"maximum number\" defined in BrmBackupScheduler MO and \"remove-oldest\" policy";
        value 2;
      }
      enum SYSTEM_CREATED {
        description "Backup automatically created by the managed element.
\nA backup of this creation type is not subject to any housekeeping policy defined by the management system and can only be removed by the managed element. Such a backup is primarily used for automatic recovery from catastrophic failures, but may also be used as any other backup if the management system chooses to restore the managed element with it.
\n";
        value 3;
      }
    }
  }
  typedef enum-DayOfWeekOccurrence {
    description "The occurrence of a day in the month, for example the first Monday of the month.\nThis is used in combination with DayOfWeek to schedule an event on a certain occurence of that day in the month, for example first Monday or last Friday of the month.";
    type enumeration {
      enum FIRST {
        description "First occurrence.";
        value 1;
      }
      enum SECOND {
        description "Second occurrence.";
        value 2;
      }
      enum THIRD {
        description "Third occurrence.";
        value 3;
      }
      enum FOURTH {
        description "Fourth occurrence.";
        value 4;
      }
      enum LAST {
        description "Last occurrence.";
        value 5;
      }
      enum ALL {
        description "All occurrences.";
        value 0;
      }
    }
  }
  typedef enum-BasicAdmState {
    description "Basic administrative states for a resource.";
    type enumeration {
      enum LOCKED {
        description " The resource is administratively prohibited from performing services for its users.";
        value 0;
      }
      enum UNLOCKED {
        description "The resource is administratively permitted to perform services for its users.\nThis is independent of its inherent operability.";
        value 1;
      }
    }
  }
  typedef enum-ActionStateType {
    description "Lists the action states.";
    type enumeration {
      enum CANCELLING {
        description "Cancellation is in progress.";
        value 1;
      }
      enum RUNNING {
        description "The execution of the action is currently in progress.";
        value 2;
      }
      enum FINISHED {
        description "The action is finished.";
        value 3;
      }
      enum CANCELLED {
        description "The action has been cancelled and cancellation has been done.";
        value 4;
      }
    }
  }
  typedef enum-BrmAutoExport {
    description "Indicates whether or not a scheduled backup is automatically exported at successful creation.";
    type enumeration {
      enum DISABLED {
        description Disabled.;
        value 2;
      }
      enum ENABLED {
        description Enabled.;
        value 1;
      }
    }
  }
  typedef enum-BrmManualBackupAutoDelete {
    description "Automatically delete manual backups.
\nIndicates whether or not the implementation of BRM automatically does the housekeeping of manual backups.";
    type enumeration {
      enum ENABLED {
        description Enabled.;
        value 1;
      }
      enum DISABLED {
        description Disabled.;
        value 2;
      }
    }
  }
  typedef enum-BrmBackupStatus {
    description "Indicates the status of a Backup. 
\nThe status is INCOMPLETE during creation or deletion of a backup. Once a backup is successfully created, its status is COMPLETE. If the integrity of the backup is violated, it is marked as CORRUPTED.";
    type enumeration {
      enum BRM_BACKUP_COMPLETE {
        description "The backup is complete and can be safely restored.";
        value 1;
      }
      enum BRM_BACKUP_INCOMPLETE {
        description "The backup is incomplete. The reason can be failure during creation or deletion. 
\nAn incomplete backup can never be restored. The only operation permitted on an incomplete backup is to delete it.";
        value 2;
      }
      enum BRM_BACKUP_CORRUPTED {
        description "The backup is corrupted. 
\nA corrupted backup is never allowed to be restored. The only operation permitted on a corrupted backup is to delete it.";
        value 3;
      }
    }
  }
  typedef enum-BrmSchedBackupStrategy {
    description "The supported strategies for housekeeping of scheduled backups.";
    type enumeration {
      enum REPLACE_PER_SCHEDULE {
        description "Takes the event type into account when deciding which backup to remove.";
        value 2;
      }
      enum REMOVE_OLDEST {
        description "Remove the oldest backup when the max scheduled backup limit is reached.";
        value 1;
      }
    }
  }
  typedef ddt-EcimBackupNameString {
    description "String type of the backup name prefix.";
    type string;
  }
  typedef ddt-RcsBrM_BrmFailsafeBackup_timeoutLength {
    type uint64 {
      range 1..86400;
    }
  }
  typedef ddt-Month {
    description "Represents a month in digits.
\nThe string format is \"M\" or \"MM\" (excluding quotes).
\nM or MM = One or two digit month (1 or 0 1=January, and so on)
\n0 denotes all months.";
    type int16 {
      range 0..12;
    }
  }
  typedef ddt-ActionInvocationResult {
    description "This is the datatype for the Asychronous Action Id. ";
    type uint16;
  }
  typedef ddt-BrmActionInvocationResult {
    description "Indicates whether an asynchronous operation was successfully invoked.
\n(The actual result of the operation will be communicated by other means.)
\n
\nA value of zero indicates success. Non-zero error codes are implementation-specific.";
    type int32;
  }
  typedef ddt-RcsBrM_BrmBackupScheduler_maxStoredScheduledBackups {
    type uint16 {
      range 0..5;
    }
  }
  typedef ddt-DayOfMonth {
    description "Represents a day in the month in digits.\nThe string format is \"D\" or \"DD\"(excluding quotes).\nD or DD = One or two digit day (1 through 31)\n0 denotes all days.";
    type int16 {
      range 0..31;
    }
  }
  typedef ddt-Time {
    description "Represents the international standard for the representation of local time (ISO 8601).\nThe following pattern describes the Time format:\nhh:mm:ss\nWhere:\nhh = Two digits of hour (00 through 23, AM/PM not allowed)\nmm = Two digits of minute (00 through 59)\nss   = Two digits of second (00 through 59, leap second not allowed)";
    type string;
  }
  typedef ddt-RcsBrM_BrmBackupHousekeeping_maxStoredManualBackups {
    type uint16 {
      range 0..30;
    }
  }
  typedef ddt-EcimPasswordString {
    description "Holds the password string.";
    type string;
  }
  typedef ddt-DateTime {
    description "Represents the international standard for the representation of date and time ( ISO 8601).\nThe string format is \"YYYY-MM-DDThh:mm:ss.SSSZ\" (excluding quotes).\nA DateTime string consists of a date part, a time part, and an optional time zone information part. The time zone part may be a \"Z\", representing the Coordinated Universal Time (UTC) time zone (equals to +00) or a time zone offset (for example, +02:00).\nIf the time zone part is not present, the DateTime value represents local time.\n\nThe following pattern describes the DateTime format:\nYYYY-MM-DDThh:mm:ss[.S+][Z|+-hh:mm]\nWhere:\nYYYY = Four digit year\nMM = Two digit month (01=January, and so on)\nDD = Two digit day of month (01 through 31)\nT = Time designator (shows start of time component)\nhh = Two digits of hour (00 through 23, AM/PM not allowed)\nmm = Two digits of minute (00 through 59)\nss = Two digits of second (00 through 59, leap second not allowed)\nS+ = One or more digits of decimal fraction of a second\nZ = Time is UTC\n+- = + or - character indicating positive or negative offset to UTC\n\nDateTime values are compliant with ISO 8601 \"Representation of dates and times\" but are restricted according to RFC 3339 \"Date and Time on the Internet: Timestamps\". The DateTime format is further restricted as follows:\n- T and Z designators are upper case.\n- . (dot) is used to indicate start of fractions of seconds (ISO 8601 also allows comma)";
    type string {
      length 19..31;
    }
  }
  typedef ddt-EcimEmpty {
    description "Represents a leaf that has no value, it conveys information by its presence or absence.";
    type boolean;
  }
  grouping struct-ProductData {
    description "Represents an Ericsson software product.\nThe product name, product number, and product revision represent product information stored in PRIM realization part.";
    leaf productionDate {
      description "Production date of the product.";
      type erienmnrmrcsbrm:ddt-DateTime;
      mandatory true;
    }
    leaf description {
      description "Free text description of the product.";
      type string;
      mandatory true;
    }
    leaf productNumber {
      description "Product number of the product.";
      type string;
      mandatory true;
    }
    leaf type {
      description "Free text description of the product type.";
      type string;
      mandatory true;
    }
    leaf productName {
      description "Name of the product.";
      type string;
      mandatory true;
    }
    leaf productRevision {
      description "Revision state of the product.";
      type string;
      mandatory true;
    }
  } // end 'grouping struct-ProductData'
  grouping struct-EcimPassword {
    description "Stores the password.";
    leaf password {
      description "Holds the password or passphrase text.";
      type string;
      mandatory true;
    }
    leaf cleartext {
      description "Indicates whether or not the password is entered in cleartext.";
      type erienmnrmrcsbrm:ddt-EcimEmpty;
    }
  } // end 'grouping struct-EcimPassword'
  grouping struct-AsyncActionProgress {
    description "Records the progress of an asynchronous action.";
    leaf result {
      description "Result state of a completed action.\nThis field has value NOT_AVAILABLE if the action is not finished.";
      type erienmnrmrcsbrm:enum-ActionResultType;
    }
    leaf timeOfLastStatusUpdate {
      description "Date and time when the struct member state was last updated.";
      type erienmnrmrcsbrm:ddt-DateTime;
      mandatory true;
    }
    leaf timeActionCompleted {
      description "Date and time when the action was completed (successfully or unsuccessfully).";
      type erienmnrmrcsbrm:ddt-DateTime;
    }
    leaf-list additionalInfo {
      min-elements 0;
      description "Used for logging significant messages during execution of an action.";
      type string;
    }
    leaf actionId {
      description "Uniquely identifies the invocation of an action.\nIdentifies the invocation of an action when the managed object allows invocation of more than one action at a time.";
      type erienmnrmrcsbrm:ddt-ActionInvocationResult;
      mandatory true;
    }
    leaf progressPercentage {
      description "Progress of the action.\nThe range is between 0 and 100.";
      type uint8;
    }
    leaf progressInfo {
      description "Textual information that describes the actual state of the action execution.";
      type string;
    }
    leaf state {
      description "Current state of the action.";
      type erienmnrmrcsbrm:enum-ActionStateType;
    }
    leaf timeActionStarted {
      description "Date and time when the current action was started.";
      type erienmnrmrcsbrm:ddt-DateTime;
      mandatory true;
    }
    leaf resultInfo {
      description "Textual description of the outcome/result of the action containing useful information for the NMS.\nIf the action failed, it can contain an error message.";
      type string;
    }
    leaf actionName {
      description "Name of the invoked asynchronous action.";
      type string;
    }
  } // end 'grouping struct-AsyncActionProgress'
  grouping moc-BrmPeriodicEvent-keys {
    description "Key(s) for MOC BrmPeriodicEvent";
    leaf id {
      erienmyext:no-notification;
      description "The value component of the RDN. 
\n";
      mandatory true;
      yexte:ecim-name brmPeriodicEventId;
      type string;
    }
  } // end 'grouping moc-BrmPeriodicEvent-keys'
  grouping moc-BrmPeriodicEvent {
    description "Periodic backup event.
\nThis construct can be used to configure a periodic scheduled backup event by specifying the number of months, weeks, days, hours, or minutes. For instance, in order to configure a scheduled backup event to occur every 12 hours, the following setup must be done: hours = 12.
\nIf more than one attribute is set, the values are added when calculating the next scheduled event. For example, if hours = 6 and minutes = 30, the scheduled backup event occurs every 6 hour and 30 minutes. The start time for calculating scheduled events is assumed to be the current system time by default, unless explicitly set using the startTime attribute. Furthermore, if the configured event is to stop at a specific date, attribute stopTime must be set accordingly. Note that the default value of stopTime is the end of a century. Daylight saving adjustments in Spring and Fall are addressed in such a way that the affected scheduled backup events are triggered exactly once only";
    leaf hours {
      description "The number of hours.";
      mandatory true;
      type uint16;
    }
    leaf months {
      status deprecated {
        yexte:status-information "CalendarBasedPeriodicEvent  is used for monthly scheduling";
      }
      description "Deprecated, The number of months.\nReplaced by CalendarBasedPeriodicEvent.month.";
      type uint16;
      default 0;
    }
    leaf weeks {
      description "The number of weeks.";
      type uint16;
      default 0;
    }
    leaf minutes {
      description "The number of minutes.";
      type uint16;
      default 0;
    }
    leaf days {
      description "The number of days.";
      type uint16;
      default 0;
    }
    leaf startTime {
      description "Start time. It is an optional attribute.\nIf not specified, the implementation uses the current system time as the default value.";
      type erienmnrmrcsbrm:ddt-DateTime;
    }
    leaf stopTime {
      description "Stop time. It is an optional attribute. The default value is the end of the century.";
      type erienmnrmrcsbrm:ddt-DateTime;
    }
  } // end 'grouping moc-BrmPeriodicEvent'
  grouping moc-BrmBackupScheduler-keys {
    description "Key(s) for MOC BrmBackupScheduler";
    leaf id {
      erienmyext:no-notification;
      description "The value component of the RDN.";
      mandatory true;
      yexte:ecim-name brmBackupSchedulerId;
      type string;
    }
  } // end 'grouping moc-BrmBackupScheduler-keys'
  grouping moc-BrmBackupScheduler {
    description "Provides optional support for scheduling backup creation.
\nEach instance of BrmBackupScheduler MOC serves as the backup scheduler for the backup type indicated by its parent instance of BrmBackupManager. The scheduled backup events can be instances of BrmSingleEvent MOC, BrmCalnedarBasedPeriodicEvent MOC, or BrmPeriodicEvent MOC contained in the instance of BrmBackupScheduler.
\n
\nSome optional attributes which are mentioned below are used only if encryption of sensitive parts of the backups is needed.
\nIn case the backup must be encrypted then this can be enabled by using the enableEncryption attribute. In this case the encryption method must be selected (URI or PASSWORD). Also all the necessary parameters for the selected method must be set as follows:
\nFor URI method: cryptoKeyUri, cryptoKeyUriPassword, cryptoKeyPassword (this one is optional. Needed if the key file is encrypted).
\nFor PASSWORD method: backupPassword. ";
    leaf userLabel {
      description "A free text stored together with each created secured backup.
\nA secured backup has some sensitive parts of the backup encrypted.
\nUsed to identify the key or the password to decrypt the sensitive data in the backup during restore.
\nOptional. Used only if sensitive data in the backup is encrypted.
\nUsed for both URI and PASSWORD encryption methods.";
      type string;
    }
    container progressReport {
      description "Reports the progress and final result of the ongoing (asynchronous) scheduled backup operation.";
      erienmyext:enm-type STRUCT;
      uses erienmnrmrcsbrm:struct-AsyncActionProgress;
    } // end 'container progressReport'
    leaf housekeepingStrategy {
      description "Determines the strategy to be used when performing housekeeping on scheduled backups.";
      type erienmnrmrcsbrm:enum-BrmSchedBackupStrategy;
      default REMOVE_OLDEST;
    }
    container backupPassword {
      description "The backupPassword is used to generate encryption key.
\nThis key is used to encrypt sensitive parts of the backup.
\nUsed for the PASSWORD encryption method.
\nOptional. Used only if sensitive data in the backup is encrypted.";
      erienmyext:enm-type STRUCT;
      uses erienmnrmrcsbrm:struct-EcimPassword;
    } // end 'container backupPassword'
    leaf autoExport {
      description "Determines whether a scheduled backup is to be automatically exported at successful creation.
\nIf set to ENABLED, the scheduled backup specified by the attribute mostRecentlyCreatedAutoBackup is exported to the location specified by attribute autoExportUri after it is successfully created. Note that the automatic export is only triggered if creation of the scheduled backup was successful. Otherwise, no export operation is triggered, even if this attribute is set to ENABLED. Also, note that setting this attribute to ENABLED has no impact on the scheduled backups that were already created and stored prior to the new configuration.
\n
\n";
      type erienmnrmrcsbrm:enum-BrmAutoExport;
      default DISABLED;
    }
    leaf autoExportUri {
      description "Uri used by the backup scheduler when automatically exporting a scheduled backup.
\nIf attribute autoExport is set to ENABLED, this uri specifies the location to which the scheduled backup is automatically exported.";
      type string;
    }
    container autoExportPassword {
      description "Password used by the backup scheduler when automatically exporting a scheduled backup.
\nIf attribute autoExport is set to ENABLED, this password is used for authentication when automatically exporting the scheduled backup. No need to specify this attribute if no password is required for accessing autoExportUri.";
      erienmyext:enm-type STRUCT;
      uses erienmnrmrcsbrm:struct-EcimPassword;
    } // end 'container autoExportPassword'
    leaf encryptionMethod {
      description "Must be set if encryption is enabled.
\nTogether with other attributes depending on the method.
\nUsed only if sensitive data in the backup must be encrypted.
\nThe available methods are URI and PASSWORD.
\nThe default is set to PASSWORD.";
      yexte:takes-effect "If encryption is enabled";
      type erienmnrmrcsbrm:enum-BrmBackupEncryptionMethod;
      default PASSWORD;
    }
    leaf scheduledBackupName {
      description "The configurable portion of the scheduled backup name.
\nThe scheduled backups are named <scheduledBackupName>-<creation date and time>, where creation date and time is of type DateTime defined in the common library.";
      type string;
      default BACKUP;
    }
    leaf maxStoredScheduledBackups {
      description "The maximum number of scheduled backups, per backup type, to store in the ME.
\nWhen this limit is reached, the oldest scheduled backup is deleted by BRM before creating a new one.";
      type erienmnrmrcsbrm:ddt-RcsBrM_BrmBackupScheduler_maxStoredScheduledBackups;
      default 5;
    }
    container keyDecryptionKey {
      description "Optional password for the encryption key file in case it is encrypted.
\nUsed for the URI encryption method.
\nUsed only if sensitive data in the backup must be encrypted.";
      erienmyext:enm-type STRUCT;
      uses erienmnrmrcsbrm:struct-EcimPassword;
    } // end 'container keyDecryptionKey'
    leaf adminState {
      description "Administrative state of the scheduler.";
      type erienmnrmrcsbrm:enum-BasicAdmState;
      default UNLOCKED;
    }
    container cryptoKeyUriPassword {
      description "The password for the remote URI where the encryption key file is stored.
\nOptional. Used only if sensitive data in the backup must be encrypted.";
      erienmyext:enm-type STRUCT;
      uses erienmnrmrcsbrm:struct-EcimPassword;
    } // end 'container cryptoKeyUriPassword'
    leaf mostRecentlyCreatedAutoBackup {
      config false;
      description "The name of the scheduled backup created most recently by the backup scheduler.";
      notife:notifiable-state-data true;
      type string;
    }
    leaf nextScheduledTime {
      config false;
      description "The date and time when the next scheduled event is triggered.
\nThis is the earliest scheduled event from the set of configured events, i.e. single, periodic, and calendar-based periodic events.";
      notife:notifiable-state-data true;
      type erienmnrmrcsbrm:ddt-DateTime;
    }
    leaf enableEncryption {
      description "Specifies if the encryption of sensitive parts of a backup is enabled or not.
\nThe default value is false (disabled).";
      type boolean;
      default false;
    }
    leaf cryptoKeyUri {
      description "The remote URI location where the encryption key is located.
\nFor example:
\nsftp://user@hostname/dir/subdir/key_file
\nOptional. Used only if sensitive data in the backup must be encrypted.";
      type string;
    }
  } // end 'grouping moc-BrmBackupScheduler'
  grouping moc-BrmFailsafeBackup-keys {
    description "Key(s) for MOC BrmFailsafeBackup";
    leaf id {
      erienmyext:no-notification;
      description "The value component of the RDN. 
\n";
      mandatory true;
      yexte:ecim-name brmFailsafeBackupId;
      type string;
    }
  } // end 'grouping moc-BrmFailsafeBackup-keys'
  grouping moc-BrmFailsafeBackup {
    description "MO for activating and deactivating failsafe backups.
\nFailsafe backups can be used when making changes to sensitive parts of the model, in which an error in configuration can lead to lost OAM connectivity or other failures from which the system can recover by a restore from a backup. When activated the failsafe backup function will automatically restore the system from a backup if the configuration as not been confirmed within a defined time period.";
    leaf usageState {
      config false;
      description "Shows if the failsafe function is activated or not.
\nMultiple failsafe points is not possible, therefore this state is either IDLE or BUSY.";
      notife:notifiable-state-data true;
      type erienmnrmrcsbrm:enum-UsageState;
    }
    container progressReport {
      description "Represents the progress report and  final result of creating backup for failsafe configuration.
\nIt will return the same information as the progressReport attribute of the BrmBackupManager managed object class.
\n            ";
      erienmyext:enm-type STRUCT;
      uses erienmnrmrcsbrm:struct-AsyncActionProgress;
    } // end 'container progressReport'
    leaf timeoutLength {
      description "The number of seconds the system waits before activating the failsafe function.\n
\nIf the value is set while the function is active the timeRemaining will be changed to that time instead.
\n";
      type erienmnrmrcsbrm:ddt-RcsBrM_BrmFailsafeBackup_timeoutLength;
      default 1200;
    }
    leaf timeRemaining {
      erienmyext:no-notification;
      config false;
      description "The number of seconds that remains before the system is restored from the selected backup.";
      type uint64;
    }
    leaf backupName {
      config false;
      description "Name of the backup that will be restored in case the failsafe function is activated.";
      notife:notifiable-state-data true;
      type string;
    }
    action activate {
      description "Activates a failsafe backup, which is created when this action is invoked.";
      output {
        leaf result {
          type erienmnrmrcsbrm:ddt-BrmActionInvocationResult;
        }
      }
    }
    action deactivate {
      description "Deactivates failsafe function and the failsafe backup is removed.";
      input {
        leaf postAction {
          description "Optional parameter to perform post deactivate actions.
\nThere are three possible values:
\nNOP means no operation.
\nCLEAR_LIST means clear the restoreEscalationList.
\nADD_BACKUP_TO_LIST means clear the restoreEscalationList then add the failsafe backup just created to the restoreEscalationList.";
          type erienmnrmrcsbrm:enum-BrmDeactivatePostAction;
        }
      }
      output {
        leaf result {
          type erienmnrmrcsbrm:ddt-BrmActionInvocationResult;
        }
      }
    }
  } // end 'grouping moc-BrmFailsafeBackup'
  grouping moc-BrmBackupManager-keys {
    description "Key(s) for MOC BrmBackupManager";
    leaf id {
      erienmyext:no-notification;
      description "The value component of the RDN. 
\n";
      mandatory true;
      yexte:ecim-name brmBackupManagerId;
      type string;
    }
  } // end 'grouping moc-BrmBackupManager-keys'
  grouping moc-BrmBackupManager {
    description "Serves as container for Backup instances of a particular backupType and backupDomain.
\n
\nThis class also provides the actions for creating new backups, importing backups from other locations, and deleting existing backups of the corresponding type and domain.";
    leaf backupDomain {
      config false;
      description "Backup domain, for example System.";
      notife:notifiable-state-data true;
      type string;
    }
    container progressReport {
      description "Represents the progress report and  final result of the ongoing (asynchronous) action.
\nFor example: createBackup. 
\nThis MO supports only one action to be executed at a time.
\n            ";
      erienmyext:enm-type STRUCT;
      uses erienmnrmrcsbrm:struct-AsyncActionProgress;
    } // end 'container progressReport'
    leaf autoExport {
      description "Determines whether a manual backup is to be automatically exported at successful creation.
\nIf set to ENABLED, the manual backup most recently created is exported to the location specified by attribute autoExportUri after it is successfully created. Note that the automatic export is only triggered if creation of the manual backup was successful. Otherwise, no export operation is triggered, even if this attribute is set to ENABLED. Also, note that setting this attribute to ENABLED has no impact on the manual backups that were already created and stored prior to the new configuration.
\n
\n";
      type erienmnrmrcsbrm:enum-BrmAutoExport;
      default DISABLED;
    }
    leaf autoExportUri {
      description "Uri used by the backup scheduler when automatically exporting a manual backup.
\nIf attribute autoExport is set to ENABLED, this uri specifies the location to which the manual backup is automatically exported.";
      type string;
    }
    leaf manualBackupName {
      description "Used as a prefix for the name of the manual backup.\nThe backups are named <manualbackupName>-<creation date and time> if manualBackupName is not the empty string.\nThe default value is the empty string. If used the name must only contain lower case, upper case, digits, hyphen, underscore or dot characters.\nIf the optional 'name' parameter is supplied to any of the actionsto create backup then it takes precedence over this attribute.";
      type erienmnrmrcsbrm:ddt-EcimBackupNameString;
    }
    container autoExportPassword {
      description "Password used by the backup scheduler when automatically exporting a manual backup.
\nIf attribute autoExport is set to ENABLED, this password is used for authentication when automatically exporting the manual backup. No need to specify this attribute if no password is required for accessing autoExportUri.";
      erienmyext:enm-type STRUCT;
      uses erienmnrmrcsbrm:struct-EcimPassword;
    } // end 'container autoExportPassword'
    leaf backupType {
      config false;
      description " Type of backup, for example System Data or User Data.
\n            ";
      notife:notifiable-state-data true;
      type string;
    }
    action deleteBackup {
      description "Delete a backup.
\nSpecified by the backup name, the backupType and backupDomain managed by this BackupManager.
\nThis is an asynchronous action. The progress and result are reported in the progressReport attribute.";
      input {
        leaf name {
          mandatory true;
          description "The name of the backup to delete.";
          type string;
        }
      }
      output {
        leaf result {
          type erienmnrmrcsbrm:ddt-BrmActionInvocationResult;
        }
      }
    }
    action createSecuredBackupWithURI {
      description "Creates a new Secure backup of the backupType and backupDomain managed by the BackupManager.
\nA secured backup has some sensitive parts of the backup encrypted.
\nThis is an asynchronous action - progress and result will be reported in the progressReport attribute.
\nThe encryption key is located remotely at some URI.
\nThis action takes optional backup name, uri, uriPassword, optional keyDecryptionKey and userLabel.
\nIf the key container file is not encrypted then the keyDecryptionKey can be omitted.
\nuserLabel is a free text string used to describe the backup details.";
      input {
        leaf userLabel {
          mandatory true;
          description "Free text to describe the secured backup.
\nCan be used to identify the key or the password to decrypt the backup during restore.
\nFor example:
\n\"Encrypted System Backup taken on 18-Jun-2019\"";
          type string;
        }
        leaf keyDecryptionKey {
          description "Optional password for the encryption key file in case it is encrypted.";
          type erienmnrmrcsbrm:ddt-EcimPasswordString;
        }
        leaf name {
          description "The Secure Backup name to create.
\nIf specified, input name validation is done by the implementation to forbid illegal names. Backup name validation rules are defined by the implementation and include duplicate backup names, names exceeding maximum allowed length, etc.
\nIf specified it will take precedence over the manualBackupName attribute.
\nIf not specified, the implementation will use the manualBackupName attribute (which could be empty) to generate a backup name automatically with format defined by the implementation, example: <managedElementId>_<YYYY-MM-DDThh-mm-ss>.";
          type string;
        }
        leaf uriPassword {
          mandatory true;
          description "The password for the remote URI where the encryption key file is stored.";
          type erienmnrmrcsbrm:ddt-EcimPasswordString;
        }
        leaf uri {
          mandatory true;
          description "The remote URI location where the encryption key is located.
\nFor example:
\nsftp://user@hostname/dir/subdir/key_file";
          type string;
        }
      }
      output {
        leaf result {
          type erienmnrmrcsbrm:ddt-BrmActionInvocationResult;
        }
      }
    }
    action cancelCurrentAction {
      description "Cancel an ongoing asynchronous createBackup, deleteBackup, or importBackup operation.";
      output {
        leaf result {
          type erienmnrmrcsbrm:ddt-BrmActionInvocationResult;
        }
      }
    }
    action createBackup {
      description "Create a new backup of the backupType and backupDomain managed by this BackupManager.
\nThis is an asynchronous action - the progress and result are reported in the progressReport attribute.";
      input {
        leaf name {
          description "The name of the backup to create.
\nIf specified, input name validation is done by the implementation to forbid illegal names. Backup name validation rules are defined by the implementation and include duplicate backup names, names exceeding maximum allowed length, etc.
\nIf specified it will take precedence over the manualBackupName attribute.
\nIf not specified, the implementation will use the manualBackupName attribute (which could be empty) to generate a backup name automatically with format defined by the implementation, example: <managedElementId>_<YYYY-MM-DDThh-mm-ss>.";
          type string;
        }
      }
      output {
        leaf result {
          type erienmnrmrcsbrm:ddt-BrmActionInvocationResult;
        }
      }
    }
    action createSecuredBackupWithPasswd {
      description "Creates a new secured backup of the backupType and backupDomain managed by the BackupManager.
\nA secured backup has some sensitive parts of the backup encrypted.
\nThis is an asynchronous action - progress and result will be reported in the progressReport attribute.
\nThe encryption key is generated by using the backupPassword.
\nThis action takes optional backup name, backupPassword and userLabel.
\nuserLabel is a free text string used to describe the backup details.";
      input {
        leaf userLabel {
          mandatory true;
          description "Free text to describe the secured backup.
\nCan be used to identify the key or the password to decrypt the backup during restore.
\nFor example:
\n\"Encrypted System Backup taken on 18-Jun-2019\"";
          type string;
        }
        leaf backupPassword {
          mandatory true;
          description "The password used to generate the encryption key used to encrypt the backup.";
          type erienmnrmrcsbrm:ddt-EcimPasswordString;
        }
        leaf name {
          description "The Secure Backup name to create.
\nIf specified, input name validation is done by the implementation to forbid illegal names. Backup name validation rules are defined by the implementation and include duplicate backup names, names exceeding maximum allowed length, etc.
\nIf specified it will take precedence over the manualBackupName attribute.\n
\nIf not specified, the implementation will use the manualBackupName attribute (which could be empty) to generate a backup name automatically with format defined by the implementation, example: <managedElementId>_<YYYY-MM-DDThh-mm-ss>.";
          type string;
        }
      }
      output {
        leaf result {
          type erienmnrmrcsbrm:ddt-BrmActionInvocationResult;
        }
      }
    }
    action importBackup {
      description "Import a backup using the specified resource identifier (uri). 
\nThis is an asynchronous action where the progress and result are reported in the progressReport attribute. Note that the type and domain of the backup to be imported must match the backup type and domain indicated by the instance of the backup manager on which this action is invoked.";
      input {
        leaf password {
          description "The password required to access the location specified by the uri.
\nIf no password is required, this parameter may be omitted.";
          type erienmnrmrcsbrm:ddt-EcimPasswordString;
        }
        leaf uri {
          mandatory true;
          description "Specifies url (location) or urn (resource name).
\nIn case of url this is the location where the backup is to be imported from.
\nIn case of urn this is the resource name that encapsulates the backup import procedure.";
          type string;
        }
      }
      output {
        leaf result {
          type erienmnrmrcsbrm:ddt-BrmActionInvocationResult;
        }
      }
    }
  } // end 'grouping moc-BrmBackupManager'
  grouping moc-BrmBackup-keys {
    description "Key(s) for MOC BrmBackup";
    leaf id {
      erienmyext:no-notification;
      description "The value component of the RDN. 
\n";
      mandatory true;
      yexte:ecim-name brmBackupId;
      type string;
    }
  } // end 'grouping moc-BrmBackup-keys'
  grouping moc-BrmBackup {
    description "Represents one backup of the type and domain specified by the BrmBackupManager.
\nThis backup is contained in the corresponding parent BrmBackupManager instance.";
    leaf creationType {
      config false;
      description "Creation type; whether manually created or automatically via BrmBackupScheduler.";
      notife:notifiable-state-data true;
      type erienmnrmrcsbrm:enum-BrmBackupCreationType;
    }
    leaf userLabel {
      config false;
      description "Free text provided as userLabel parameter to the create action when the backup is created.
\nOptional. Used in case sensitive data in the backup is encrypted.
\nCan be used to identify the key or the password to decrypt the backup during restore.
\nRead only.";
      notife:notifiable-state-data true;
      type string;
    }
    leaf cryptoPasswordId {
      config false;
      description "Encryption Password Identifier.
\nA unique hash generated from password when the backup is created.
\nOptional. Used in case sensitive data in the backup is encrypted.
\nRead only.";
      notife:notifiable-state-data true;
      type string;
    }
    list swVersion {
      min-elements 0;
      key auto-generated-struct-key;
      leaf auto-generated-struct-key {
        type uint16;
        description "This leaf has been injected to allow for struct instances in a sequence to be ordered.";
        mandatory true;
      }
      description "The administrative data portion of active software versions.
\nAs specified in the software inventory management when the backup is created.
\n";
      erienmyext:enm-type STRUCT;
      uses erienmnrmrcsbrm:struct-ProductData;
    } // end 'list swVersion'
    leaf creationTime {
      config false;
      description "Date and time when the backup was created, i.e., start time of backup procedure.";
      notife:notifiable-state-data true;
      type erienmnrmrcsbrm:ddt-DateTime;
    }
    container progressReport {
      description "Represents the progress report and  final result of the ongoing (asynchronous) action in this MO.
\nFor example: restore.
\nThis MO supports only one action to be executed at a time.
\n            ";
      erienmyext:enm-type STRUCT;
      uses erienmnrmrcsbrm:struct-AsyncActionProgress;
    } // end 'container progressReport'
    leaf cryptoKeyId {
      config false;
      description "Unique Encryption Key Identifier.
\nA unique hash generated from the backup crypto key when the backup is created.
\nOptional. Used in case sensitive data in the backup is encrypted.
\nRead only.
\n";
      notife:notifiable-state-data true;
      type string;
    }
    leaf backupName {
      config false;
      description "Backup name, provided by the operator. ";
      notife:notifiable-state-data true;
      type string;
    }
    leaf status {
      config false;
      description "Status of the backup.";
      notife:notifiable-state-data true;
      type erienmnrmrcsbrm:enum-BrmBackupStatus;
    }
    action restore {
      description "Restore from this backup.\nThis is an asynchronous action - progress and result are reported in the progressReport attribute.";
      output {
        leaf result {
          type erienmnrmrcsbrm:ddt-BrmActionInvocationResult;
        }
      }
    }
    action restoreSecuredBackupWithPasswd {
      description "Restore the current secured backup of the backupType and backupDomain managed by the BackupManager.
\nA secured backup has some sensitive parts of the backup encrypted.
\nThis is an asynchronous action - progress and result will be reported in the progressReport attribute.
\nThe backupPassword is used to generate the decryption key used to decrypt any secure parts of the the backup.
\nThis action takes backupPassword.";
      input {
        leaf backupPassword {
          mandatory true;
          description "The backupPassword is used to generate the encryption key used to encrypt the backup.";
          type erienmnrmrcsbrm:ddt-EcimPasswordString;
        }
      }
      output {
        leaf result {
          type erienmnrmrcsbrm:ddt-BrmActionInvocationResult;
        }
      }
    }
    action cancelCurrentAction {
      description "Cancel an ongoing asynchronous restore or export operation.";
      output {
        leaf result {
          type erienmnrmrcsbrm:ddt-BrmActionInvocationResult;
        }
      }
    }
    action restoreSecuredBackupWithURI {
      description "Restore the current secured backup of the backupType and backupDomain managed by the BackupManager.
\nA secured backup has some sensitive parts of the backup encrypted.
\nThis is an asynchronous action - progress and result will be reported in the progressReport attribute.
\nThe decryption key is located remotely at some URI.
\nThis action takes uri, uriPassword and optional keyDecryptionKey.
\nIf the key container file is not encrypted then the keyDecryptionKey can be omitted.";
      input {
        leaf keyDecryptionKey {
          description "Optional password for the encryption key file in case it is encrypted.";
          type erienmnrmrcsbrm:ddt-EcimPasswordString;
        }
        leaf uriPassword {
          mandatory true;
          description "The password for the remote URI where the encryption key file is stored.";
          type erienmnrmrcsbrm:ddt-EcimPasswordString;
        }
        leaf uri {
          mandatory true;
          description "The remote URI location where the encryption key can be obtained from.
\nFor example:
\nsftp://user@hostname/dir/subdir/key_file";
          type string;
        }
      }
      output {
        leaf result {
          type erienmnrmrcsbrm:ddt-BrmActionInvocationResult;
        }
      }
    }
    action export {
      description "Export the backup using the specified resource identifier (uri). 
\nThis is an asynchronous action. Progress and the result are reported in the progressReport attribute. Note: When backup successfully completed, a copy of the backup is transferred and the original backup remains in the ME.";
      input {
        leaf password {
          description "The password required to access the location specified by the uri.
\nIf no password is required, this parameter may be omitted.";
          type erienmnrmrcsbrm:ddt-EcimPasswordString;
        }
        leaf uri {
          mandatory true;
          description "Specifies url (location) or urn (resource name).
\nIn case of url this is the location where the backup is to be exported.
\nIn case of urn this is the resource name that encapsulates the backup export procedure.
\n";
          type string;
        }
      }
      output {
        leaf result {
          type erienmnrmrcsbrm:ddt-BrmActionInvocationResult;
        }
      }
    }
  } // end 'grouping moc-BrmBackup'
  grouping moc-BrmBackupLabelStore-keys {
    description "Key(s) for MOC BrmBackupLabelStore";
    leaf id {
      erienmyext:no-notification;
      description "The value component of the RDN.";
      mandatory true;
      yexte:ecim-name brmBackupLabelStoreId;
      type string;
    }
  } // end 'grouping moc-BrmBackupLabelStore-keys'
  grouping moc-BrmBackupLabelStore {
    description "Provides optional support for labeling of certain backups.
\nThis class contains attributes that help distinguish certain backups such as the last restored backup, primary restore candidate, and so on.";
    leaf-list restoreEscalationList {
      min-elements 0;
      config false;
      description "Specifies a list of backups by name, in the order that is to be used to restore the ME when needed.
\nSpecifically, the first element of this ordered list identifies the “primary restore candidate”. If the attempt to restore the ME with a given backup fails, the next backup in the list must be tried.";
      notife:notifiable-state-data true;
      type string;
    }
    leaf lastCreatedBackup {
      config false;
      description "The name of the last backup created.
\nThis backup can be MANUAL or SCHEDULED. Note that this attribute is not updated in the case of a failed attempt to create a backup, which would result in an INCOMPLETE backup.";
      notife:notifiable-state-data true;
      type string;
    }
    leaf lastExportedBackup {
      config false;
      description "The name of the last backup exported from the ME.
\nNote that this attribute is not updated in the case of a failed attempt to export a backup.";
      notife:notifiable-state-data true;
      type string;
    }
    leaf lastImportedBackup {
      config false;
      description "The name of the last backup imported to the ME.
\nNote that this attribute is not updated in the case of a failed attempt to import a backup.";
      notife:notifiable-state-data true;
      type string;
    }
    leaf lastRestoredBackup {
      config false;
      description "The name of the backup that was last used to restore the ME.
\nThis does not imply that the currently running version of the system is the same as this backup, but instead shows which one of the backups was last used to restore the ME. In a system that has never been restored using a backup, this attribute is empty.";
      notife:notifiable-state-data true;
      type string;
    }
  } // end 'grouping moc-BrmBackupLabelStore'
  grouping moc-BrmSingleEvent-keys {
    description "Key(s) for MOC BrmSingleEvent";
    leaf id {
      erienmyext:no-notification;
      description "The value component of the RDN. 
\n";
      mandatory true;
      yexte:ecim-name brmSingleEventId;
      type string;
    }
  } // end 'grouping moc-BrmSingleEvent-keys'
  grouping moc-BrmSingleEvent {
    description "A single scheduled backup event.
\nThis construct can be used to configure a single, one-shot, scheduled backup event by specifying the desired date and time.
\n";
    leaf scheduledTime {
      description "Scheduled time.";
      mandatory true;
      type erienmnrmrcsbrm:ddt-DateTime;
    }
  } // end 'grouping moc-BrmSingleEvent'
  grouping moc-BrM-keys {
    description "Key(s) for MOC BrM";
    leaf id {
      erienmyext:no-notification;
      description "The value component of the RDN. 
\n";
      mandatory true;
      yexte:ecim-name brMId;
      type string;
    }
  } // end 'grouping moc-BrM-keys'
  grouping moc-BrM {
    description "ECIM Backup and Restore Management top-level class.
\n
\nECIM BRM encompasses all the operations associated with the backup and restore of the managed element.";
    leaf exportPackageLabelPrefix {
      description "Free text to help better identify a backup export package when residing outside the ME.
\nIf specified, BRM prefixes this text to the label that it generates for the backup export package.";
      type string;
    }
  } // end 'grouping moc-BrM'
  grouping moc-BrmBackupHousekeeping-keys {
    description "Key(s) for MOC BrmBackupHousekeeping";
    leaf id {
      erienmyext:no-notification;
      description "The value component of the RDN. 
\n";
      mandatory true;
      yexte:ecim-name brmBackupHousekeepingId;
      type string;
    }
  } // end 'grouping moc-BrmBackupHousekeeping-keys'
  grouping moc-BrmBackupHousekeeping {
    description "Provides optional support for automated housekeeping of manually created backups. 
\n
\nIf autoDelete is set to ENABLED before creating a new manual backup, BRM first checks the number of manual backups, and if the limit specified by the value of maxStoredManualBackups is reached, BRM removes the oldest manual backup before creating a new one.";
    leaf autoDelete {
      description "Determines whether automated housekeeping of manual backups is enabled.
\nIf ENABLED and the number of backups already stored on the ME is equal to the value of maxStoredManualBackups, the oldest backup is removed before creating a new one. If set to DISABLED, no backup is removed. Instead, when action createBackup() is invoked, it returns a failure parameter.";
      type erienmnrmrcsbrm:enum-BrmManualBackupAutoDelete;
      default ENABLED;
    }
    leaf maxStoredManualBackups {
      description "Maximum number of manual backups, per backup type, to store in the ME. 
\nWhen this limit is reached, if autoDelete=ENABLED, BRM removes the oldest manual backup before creating a new one. Otherwise an error is returned when createBackup() is invoked and the NMS must perform the required housekeeping activity before attempting to create a new backup.";
      type erienmnrmrcsbrm:ddt-RcsBrM_BrmBackupHousekeeping_maxStoredManualBackups;
      default 20;
    }
  } // end 'grouping moc-BrmBackupHousekeeping'
  grouping moc-BrmRollbackAtRestore-keys {
    description "Key(s) for MOC BrmRollbackAtRestore";
    leaf id {
      erienmyext:no-notification;
      description "The value component of the RDN.";
      mandatory true;
      yexte:ecim-name brmRollbackAtRestoreId;
      type string;
    }
  } // end 'grouping moc-BrmRollbackAtRestore-keys'
  grouping moc-BrmRollbackAtRestore {
    description "Provides optional support for confirmation of a restore action or automatic rollback.
\nThe existence of an instance of this class indicates that this feature is supported by the implementation.
\nIf configured then the action confirmRestore must be invoked within the configured time by the timeAllowedBeforeRollback attribute otherwise the system will be rolled back to the state before the backup being restored.";
    leaf timeRemainingBeforeRollback {
      config false;
      description "The remaining number of seconds before performing the rollback to the state before restore.
\nThe countdown stops after confirmRestore action is invoked on the BrmBackup MO, representing the restored backup. If action confirmRestore is not invoked before the expiration of the rollback timer, an automatic rollback is triggered. Countdown starts at restore, and stops when confirmRestore() is invoked.";
      notife:notifiable-state-data true;
      type uint16;
    }
    leaf timeAllowedBeforeRollback {
      description "Number of seconds to wait for action confirmRestore.
\nIf the confirmRestore action is not invoked before this time expires then the system will be rolled back to the state before restore.";
      type uint16;
    }
    action confirmRestore {
      description "Invoking this action indicates acceptance of the previously executed restore operation.
\nThe restore supervision timer, counting down from the initial value indicated by the timeAllowedBeforeRollback attribute, is stopped when this action is invoked. If this action is not invoked before the supervision timer expires, the system is restored to the state it was in before the last restore operation was invoked. This is a synchronous action.";
      output {
        leaf result {
          type erienmnrmrcsbrm:ddt-BrmActionInvocationResult;
        }
      }
    }
  } // end 'grouping moc-BrmRollbackAtRestore'
  grouping moc-BrmCalendarBasedPeriodicEvent-keys {
    description "Key(s) for MOC BrmCalendarBasedPeriodicEvent";
    leaf id {
      erienmyext:no-notification;
      description "The value component of the RDN.";
      mandatory true;
      yexte:ecim-name brmCalendarBasedPeriodicEventId;
      type string;
    }
  } // end 'grouping moc-BrmCalendarBasedPeriodicEvent-keys'
  grouping moc-BrmCalendarBasedPeriodicEvent {
    description "Periodic backup event using calendar-based interval.
\nThis construct can be used to configure a periodic scheduled backup event by specifying the desired interval using the calendar. For instance, in order to configure a scheduled backup event to occur every night at 2:00 am, the following setup must be done: time = 02:00:00.
\nThe start time for calculating scheduled events is by default the current system time, unless explicitly set using the startTime attribute. Furthermore, if the configured event is to stop at a specific date, stopTime attribute must be set accordingly. Note that the default value of stopTime is the end of the century. A scheduled backup event of this type is triggered only if ALL the conditions with regard to attribute values are satisfied. 
\nFor example, if dayOfWeek is set to Monday and dayOfMonth is set to 1, the event is triggered only if the first day of month is Monday.
\nIn another example if dayOfWeekOccurence is set to Second and dayOfWeek is set to Tuesday then the event will occur on the second Tuesday of every month. 
\nIf dayOfWeekOccurence is set to All and dayOfWeek is set to Wednesday then there will be event on every Wednesday (of every month). 
\nDaylight saving adjustments in Spring and Fall are addressed in such a way that the affected scheduled backup events are triggered exactly once.";
    leaf dayOfWeekOccurrence {
      description "The occurrence of the day of week specified by dayOfWeek attribute in the month.";
      type erienmnrmrcsbrm:enum-DayOfWeekOccurrence;
      default ALL;
    }
    leaf dayOfWeek {
      description "Day of week.";
      type erienmnrmrcsbrm:enum-DayOfWeek;
      default ALL;
    }
    leaf month {
      description Month.;
      type erienmnrmrcsbrm:ddt-Month;
      default 0;
    }
    leaf dayOfMonth {
      description "Day of month.";
      type erienmnrmrcsbrm:ddt-DayOfMonth;
      default 0;
    }
    leaf startTime {
      description "Start time. It is an optional attribute.\nIf not specified, the implementation uses the current system time as the default value.";
      type erienmnrmrcsbrm:ddt-DateTime;
    }
    leaf stopTime {
      description "Stop time. It is an optional attribute. The default value is the end of the century.";
      type erienmnrmrcsbrm:ddt-DateTime;
    }
    leaf time {
      description "This is the time when the scheduled event must occur.";
      mandatory true;
      type erienmnrmrcsbrm:ddt-Time;
    }
  } // end 'grouping moc-BrmCalendarBasedPeriodicEvent'
  augment /erienmnrmcomtop:ManagedElement/erienmnrmcomtop:SystemFunctions/erienmnrmrcsbrm:BrM/erienmnrmrcsbrm:BrmBackupManager/erienmnrmrcsbrm:BrmBackupScheduler {
    list BrmPeriodicEvent {
      key id;
      description "Periodic backup event.
\nThis construct can be used to configure a periodic scheduled backup event by specifying the number of months, weeks, days, hours, or minutes. For instance, in order to configure a scheduled backup event to occur every 12 hours, the following setup must be done: hours = 12.
\nIf more than one attribute is set, the values are added when calculating the next scheduled event. For example, if hours = 6 and minutes = 30, the scheduled backup event occurs every 6 hour and 30 minutes. The start time for calculating scheduled events is assumed to be the current system time by default, unless explicitly set using the startTime attribute. Furthermore, if the configured event is to stop at a specific date, attribute stopTime must be set accordingly. Note that the default value of stopTime is the end of a century. Daylight saving adjustments in Spring and Fall are addressed in such a way that the affected scheduled backup events are triggered exactly once only";
      erienmyext:enm-type MOC;
      uses moc-BrmPeriodicEvent-keys;
      container attributes {
        description "Attributes for BrmPeriodicEvent";
        uses moc-BrmPeriodicEvent;
      } // end 'container attributes'
    } // end 'list BrmPeriodicEvent'
  }
  augment /erienmnrmcomtop:ManagedElement/erienmnrmcomtop:SystemFunctions/erienmnrmrcsbrm:BrM/erienmnrmrcsbrm:BrmBackupManager {
    list BrmBackupScheduler {
      key id;
      max-elements 1;
      description "Provides optional support for scheduling backup creation.
\nEach instance of BrmBackupScheduler MOC serves as the backup scheduler for the backup type indicated by its parent instance of BrmBackupManager. The scheduled backup events can be instances of BrmSingleEvent MOC, BrmCalnedarBasedPeriodicEvent MOC, or BrmPeriodicEvent MOC contained in the instance of BrmBackupScheduler.
\n
\nSome optional attributes which are mentioned below are used only if encryption of sensitive parts of the backups is needed.
\nIn case the backup must be encrypted then this can be enabled by using the enableEncryption attribute. In this case the encryption method must be selected (URI or PASSWORD). Also all the necessary parameters for the selected method must be set as follows:
\nFor URI method: cryptoKeyUri, cryptoKeyUriPassword, cryptoKeyPassword (this one is optional. Needed if the key file is encrypted).
\nFor PASSWORD method: backupPassword. ";
      yexte:is-system-created;
      erienmyext:enm-type MOC;
      uses moc-BrmBackupScheduler-keys;
      container attributes {
        description "Attributes for BrmBackupScheduler";
        uses moc-BrmBackupScheduler;
      } // end 'container attributes'
    } // end 'list BrmBackupScheduler'
  }
  augment /erienmnrmcomtop:ManagedElement/erienmnrmcomtop:SystemFunctions/erienmnrmrcsbrm:BrM/erienmnrmrcsbrm:BrmBackupManager {
    list BrmFailsafeBackup {
      key id;
      max-elements 1;
      description "MO for activating and deactivating failsafe backups.
\nFailsafe backups can be used when making changes to sensitive parts of the model, in which an error in configuration can lead to lost OAM connectivity or other failures from which the system can recover by a restore from a backup. When activated the failsafe backup function will automatically restore the system from a backup if the configuration as not been confirmed within a defined time period.";
      yexte:is-system-created;
      erienmyext:enm-type MOC;
      uses moc-BrmFailsafeBackup-keys;
      container attributes {
        description "Attributes for BrmFailsafeBackup";
        uses moc-BrmFailsafeBackup;
      } // end 'container attributes'
    } // end 'list BrmFailsafeBackup'
  }
  augment /erienmnrmcomtop:ManagedElement/erienmnrmcomtop:SystemFunctions/erienmnrmrcsbrm:BrM {
    list BrmBackupManager {
      key id;
      description "Serves as container for Backup instances of a particular backupType and backupDomain.
\n
\nThis class also provides the actions for creating new backups, importing backups from other locations, and deleting existing backups of the corresponding type and domain.";
      yexte:is-system-created;
      erienmyext:enm-type MOC;
      uses moc-BrmBackupManager-keys;
      container attributes {
        description "Attributes for BrmBackupManager";
        uses moc-BrmBackupManager;
      } // end 'container attributes'
    } // end 'list BrmBackupManager'
  }
  augment /erienmnrmcomtop:ManagedElement/erienmnrmcomtop:SystemFunctions/erienmnrmrcsbrm:BrM/erienmnrmrcsbrm:BrmBackupManager {
    list BrmBackup {
      key id;
      description "Represents one backup of the type and domain specified by the BrmBackupManager.
\nThis backup is contained in the corresponding parent BrmBackupManager instance.";
      yexte:is-system-created;
      erienmyext:enm-type MOC;
      uses moc-BrmBackup-keys;
      container attributes {
        description "Attributes for BrmBackup";
        uses moc-BrmBackup;
      } // end 'container attributes'
    } // end 'list BrmBackup'
  }
  augment /erienmnrmcomtop:ManagedElement/erienmnrmcomtop:SystemFunctions/erienmnrmrcsbrm:BrM/erienmnrmrcsbrm:BrmBackupManager {
    list BrmBackupLabelStore {
      key id;
      max-elements 1;
      description "Provides optional support for labeling of certain backups.
\nThis class contains attributes that help distinguish certain backups such as the last restored backup, primary restore candidate, and so on.";
      yexte:is-system-created;
      erienmyext:enm-type MOC;
      uses moc-BrmBackupLabelStore-keys;
      container attributes {
        description "Attributes for BrmBackupLabelStore";
        uses moc-BrmBackupLabelStore;
      } // end 'container attributes'
    } // end 'list BrmBackupLabelStore'
  }
  augment /erienmnrmcomtop:ManagedElement/erienmnrmcomtop:SystemFunctions/erienmnrmrcsbrm:BrM/erienmnrmrcsbrm:BrmBackupManager/erienmnrmrcsbrm:BrmBackupScheduler {
    list BrmSingleEvent {
      key id;
      description "A single scheduled backup event.
\nThis construct can be used to configure a single, one-shot, scheduled backup event by specifying the desired date and time.
\n";
      erienmyext:enm-type MOC;
      uses moc-BrmSingleEvent-keys;
      container attributes {
        description "Attributes for BrmSingleEvent";
        uses moc-BrmSingleEvent;
      } // end 'container attributes'
    } // end 'list BrmSingleEvent'
  }
  augment /erienmnrmcomtop:ManagedElement/erienmnrmcomtop:SystemFunctions {
    list BrM {
      key id;
      max-elements 1;
      description "ECIM Backup and Restore Management top-level class.
\n
\nECIM BRM encompasses all the operations associated with the backup and restore of the managed element.";
      yexte:is-system-created;
      erienmyext:enm-type MOC;
      uses moc-BrM-keys;
      container attributes {
        description "Attributes for BrM";
        uses moc-BrM;
      } // end 'container attributes'
    } // end 'list BrM'
  }
  augment /erienmnrmcomtop:ManagedElement/erienmnrmcomtop:SystemFunctions/erienmnrmrcsbrm:BrM/erienmnrmrcsbrm:BrmBackupManager {
    list BrmBackupHousekeeping {
      key id;
      max-elements 1;
      description "Provides optional support for automated housekeeping of manually created backups. 
\n
\nIf autoDelete is set to ENABLED before creating a new manual backup, BRM first checks the number of manual backups, and if the limit specified by the value of maxStoredManualBackups is reached, BRM removes the oldest manual backup before creating a new one.";
      yexte:is-system-created;
      erienmyext:enm-type MOC;
      uses moc-BrmBackupHousekeeping-keys;
      container attributes {
        description "Attributes for BrmBackupHousekeeping";
        uses moc-BrmBackupHousekeeping;
      } // end 'container attributes'
    } // end 'list BrmBackupHousekeeping'
  }
  augment /erienmnrmcomtop:ManagedElement/erienmnrmcomtop:SystemFunctions/erienmnrmrcsbrm:BrM {
    list BrmRollbackAtRestore {
      key id;
      max-elements 1;
      description "Provides optional support for confirmation of a restore action or automatic rollback.
\nThe existence of an instance of this class indicates that this feature is supported by the implementation.
\nIf configured then the action confirmRestore must be invoked within the configured time by the timeAllowedBeforeRollback attribute otherwise the system will be rolled back to the state before the backup being restored.";
      yexte:is-system-created;
      erienmyext:enm-type MOC;
      uses moc-BrmRollbackAtRestore-keys;
      container attributes {
        description "Attributes for BrmRollbackAtRestore";
        uses moc-BrmRollbackAtRestore;
      } // end 'container attributes'
    } // end 'list BrmRollbackAtRestore'
  }
  augment /erienmnrmcomtop:ManagedElement/erienmnrmcomtop:SystemFunctions/erienmnrmrcsbrm:BrM/erienmnrmrcsbrm:BrmBackupManager/erienmnrmrcsbrm:BrmBackupScheduler {
    list BrmCalendarBasedPeriodicEvent {
      key id;
      description "Periodic backup event using calendar-based interval.
\nThis construct can be used to configure a periodic scheduled backup event by specifying the desired interval using the calendar. For instance, in order to configure a scheduled backup event to occur every night at 2:00 am, the following setup must be done: time = 02:00:00.
\nThe start time for calculating scheduled events is by default the current system time, unless explicitly set using the startTime attribute. Furthermore, if the configured event is to stop at a specific date, stopTime attribute must be set accordingly. Note that the default value of stopTime is the end of the century. A scheduled backup event of this type is triggered only if ALL the conditions with regard to attribute values are satisfied. 
\nFor example, if dayOfWeek is set to Monday and dayOfMonth is set to 1, the event is triggered only if the first day of month is Monday.
\nIn another example if dayOfWeekOccurence is set to Second and dayOfWeek is set to Tuesday then the event will occur on the second Tuesday of every month. 
\nIf dayOfWeekOccurence is set to All and dayOfWeek is set to Wednesday then there will be event on every Wednesday (of every month). 
\nDaylight saving adjustments in Spring and Fall are addressed in such a way that the affected scheduled backup events are triggered exactly once.";
      erienmyext:enm-type MOC;
      uses moc-BrmCalendarBasedPeriodicEvent-keys;
      container attributes {
        description "Attributes for BrmCalendarBasedPeriodicEvent";
        uses moc-BrmCalendarBasedPeriodicEvent;
      } // end 'container attributes'
    } // end 'list BrmCalendarBasedPeriodicEvent'
  }
}
