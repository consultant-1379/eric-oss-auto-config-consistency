module ericsson-enm-Lrat {
  yang-version 1.1;
  namespace urn:rdns:com:ericsson:ericsson-enm-Lrat;
  prefix erienmnrmlrat;
  yexte:ecim-name Lrat;
  revision 2067-10-22 {
    yexte:version 3;
    yexte:release 80;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef enum-NeighCellConfig {
    type enumeration {
      enum DIFF_MBSFN_SUBFRAMES {
        description "Not all neighbour cells have the same MBSFN subframe allocation as the serving cell.\n\nNote that the value used in SIB3, SIB5 and MeasObjectEUTRA is '00' for DIFF_MBSFN_SUBFRAMES as specified in TS 36.331.";
        value 0;
      }
      enum SAME_MBSFN_SUBFRAMES {
        description "The MBSFN subframe allocations of all neighbour cells are identical to or subsets of that in the serving cell.\n\nNote that the value used in SIB3, SIB5 and MeasObjectEUTRA is '10' for SAME_MBSFN_SUBFRAMES as specified in TS 36.331.";
        value 1;
      }
      enum NO_MBSFN_SUBFRAMES {
        description "No MBSFN subframes are present in all neighbour cells.\n\nNote that the value used in SIB3, SIB5 and MeasObjectEUTRA is '01' for NO_MBSFN_SUBFRAMES as specified in TS 36.331.";
        value 2;
      }
      enum DIFF_UL_DL_ALLOCATION {
        description "Different UL/DL allocation in neighboring cells for TDD compared to the serving cell.\n\nNote that the value used in SIB3, SIB5 and MeasObjectEUTRA is '11' for DIFF_UL_DL_ALLOCATION as specified in TS 36.331.";
        value 3;
      }
    }
  }
  typedef enum-UnlicensedEarfcnList {
    type enumeration {
      enum NONE {
        description "No channel selected.";
        value 0;
      }
      enum EARFCN_46890 {
        description "EARFCN 46890 (46A) allowed for transmission.";
        value 1;
      }
      enum EARFCN_47090 {
        description "EARFCN 47090 (46A) allowed for transmission. Corresponds to Wi-Fi channel 36.";
        value 2;
      }
      enum EARFCN_47290 {
        description "EARFCN 47290 (46A) allowed for transmission. Corresponds to Wi-Fi channel 40.";
        value 3;
      }
      enum EARFCN_47490 {
        description "EARFCN 47490 (46A) allowed for transmission. Corresponds to Wi-Fi channel 44.";
        value 4;
      }
      enum EARFCN_47690 {
        description "EARFCN 47690 (46A) allowed for transmission. Corresponds to Wi-Fi channel 48.";
        value 5;
      }
      enum EARFCN_47890 {
        description "EARFCN 47890 (46B) allowed for transmission. Corresponds to Wi-Fi channel 52.";
        value 6;
      }
      enum EARFCN_48090 {
        description "EARFCN 48090 (46B) allowed for transmission. Corresponds to Wi-Fi channel 56.";
        value 7;
      }
      enum EARFCN_48290 {
        description "EARFCN 48290 (46B) allowed for transmission. Corresponds to Wi-Fi channel 60.";
        value 8;
      }
      enum EARFCN_48490 {
        description "EARFCN 48490 (46B) allowed for transmission. Corresponds to Wi-Fi channel 64.";
        value 9;
      }
      enum EARFCN_48690 {
        description "EARFCN 48690 (46B) allowed for transmission.";
        value 10;
      }
      enum EARFCN_50090 {
        description "EARFCN 50090 (46C) allowed for transmission.";
        value 11;
      }
      enum EARFCN_50290 {
        description "EARFCN 50290 (46C) allowed for transmission. Corresponds to Wi-Fi channel 100.";
        value 12;
      }
      enum EARFCN_50490 {
        description "EARFCN 50490 (46C) allowed for transmission. Corresponds to Wi-Fi channel 104.";
        value 13;
      }
      enum EARFCN_50690 {
        description "EARFCN 50690 (46C) allowed for transmission. Corresponds to Wi-Fi channel 108.";
        value 14;
      }
      enum EARFCN_50890 {
        description "EARFCN 50890 (46C) allowed for transmission. Corresponds to Wi-Fi channel 112.";
        value 15;
      }
      enum EARFCN_51090 {
        description "EARFCN 51090 (46C) allowed for transmission. Corresponds to Wi-Fi channel 116.";
        value 16;
      }
      enum EARFCN_51290 {
        description "EARFCN 51290 (46C) allowed for transmission. Corresponds to Wi-Fi channel 120.";
        value 17;
      }
      enum EARFCN_51490 {
        description "EARFCN 51490 (46C) allowed for transmission. Corresponds to Wi-Fi channel 124.";
        value 18;
      }
      enum EARFCN_51690 {
        description "EARFCN 51690 (46C) allowed for transmission. Corresponds to Wi-Fi channel 128.";
        value 19;
      }
      enum EARFCN_51890 {
        description "EARFCN 51890 (46C) allowed for transmission. Corresponds to Wi-Fi channel 132.";
        value 20;
      }
      enum EARFCN_52090 {
        description "EARFCN 52090 (46C) allowed for transmission. Corresponds to Wi-Fi channel 136.";
        value 21;
      }
      enum EARFCN_52290 {
        description "EARFCN 52290 (46C) allowed for transmission. Corresponds to Wi-Fi channel 140.";
        value 22;
      }
      enum EARFCN_52490 {
        description "EARFCN 52490 (46D) allowed for transmission. Corresponds to Wi-Fi channel 144.";
        value 23;
      }
      enum EARFCN_52740 {
        description "EARFCN 52740 (46D) allowed for transmission. Corresponds to Wi-Fi channel 149.";
        value 24;
      }
      enum EARFCN_52940 {
        description "EARFCN 52940 (46D) allowed for transmission. Corresponds to Wi-Fi channel 153.";
        value 25;
      }
      enum EARFCN_53140 {
        description "EARFCN 53140 (46D) allowed for transmission. Corresponds to Wi-Fi channel 157.";
        value 26;
      }
      enum EARFCN_53340 {
        description "EARFCN 53340 (46D) allowed for transmission. Corresponds to Wi-Fi channel 161.";
        value 27;
      }
      enum EARFCN_53540 {
        description "EARFCN 53540 (46D) allowed for transmission. Corresponds to Wi-Fi channel 165.";
        value 28;
      }
      enum EARFCN_53740 {
        description "EARFCN 53740 (46D) allowed for transmission.";
        value 29;
      }
      enum EARFCN_53940 {
        description "EARFCN 53940 (46D) allowed for transmission.";
        value 30;
      }
      enum EARFCN_54140 {
        description "EARFCN 54140 (46D) allowed for transmission.";
        value 31;
      }
      enum EARFCN_54340 {
        description "EARFCN 54340 (46D) allowed for transmission.";
        value 32;
      }
    }
  }
  typedef enum-PimMitigAggressiveness {
    type enumeration {
      enum LOW {
        description "Strict criteria for classification of UL transmission as PIM-affected.\nMitigation mechanism reduces number of UL transmissions that may require PIM mitigation through PDSCH resource muting. Minimizes impact on DL throughput.";
        value 0;
      }
      enum MEDIUM {
        description "Moderate criteria for classification of UL transmission as PIM-affected.\nMitigation mechanism increases number of UL transmissions that may require PDSCH resource muting.";
        value 1;
      }
      enum HIGH {
        description "Lenient criteria for classification of UL transmission as PIM-affected.\nMitigation mechanism covers wide range of UL transmissions. Yields noticeable degradation of DL throughput.";
        value 2;
      }
    }
  }
  typedef enum-ThresholdUtra {
    type enumeration {
      enum RSCP {
        description "Reference Signal Received Quality.\n";
        value 0;
      }
      enum ECNO {
        description "Ratio of energy per modulation bit to noise spectral density.";
        value 1;
      }
    }
  }
  typedef enum-OperState {
    description "Operational states of a resource.";
    type enumeration {
      enum DISABLED {
        description "The resource is  totally inoperable.";
        value 0;
      }
      enum ENABLED {
        description "The resource is partially or fully operable.";
        value 1;
      }
    }
  }
  typedef enum-Rat {
    type enumeration {
      enum UTRAN {
        value 0;
      }
      enum GERAN {
        value 1;
      }
    }
  }
  typedef enum-MeasureModeBr {
    type enumeration {
      enum DEFAULT_MEASUREMENT {
        description "A3 measurement with measurement gaps is always configured when UE enters RRC connected state, or when UE is moved to target cell during handover or RRC connection reestablishment.";
        value 0;
      }
      enum PUSCH_SINR_BASED {
        description "A3 measurement with measurement gaps is configured based on UL PUSCH SINR.";
        value 1;
      }
    }
  }
  typedef enum-MeasSelectionIrat {
    type enumeration {
      enum PERIODICAL {
        description "Periodical reporting.";
        value 0;
      }
      enum EVENT_B1 {
        description "Inter RAT neighbor becomes better than threshold.";
        value 1;
      }
      enum EVENT_B2 {
        description "PCell becomes worse than threshold1 and inter RAT neighbor becomes better than threshold2.";
        value 2;
      }
    }
  }
  typedef enum-SectorShape {
    type enumeration {
      enum MACRO {
        description "Sector shape with wider beam width in azimuth plane than in elevation plane. Refer to CPI for installed radio equipment for exact beam width for MACRO sector shape.";
        value 0;
      }
      enum HIGHRISE {
        description "Sector shape with wider beam width in elevation plane than in azimuth plane. Refer to CPI for installed radio equipment for exact beam width for HIGHRISE sector shape.";
        value 1;
      }
      enum HOTSPOT {
        description "Sector shape with wide beam width in both azimuth and elevation plane. Refer to CPI for installed radio equipment for exact beam width for HOTSPOT sector shape.";
        value 2;
      }
      enum MACRO_NARROW {
        description "Sector shape with wider beam width in azimuth plane than in elevation plane. Azimuth beam width is narrower than MACRO sector shape. Refer to CPI for installed radio equipment for exact beam width for MACRO_NARROW sector shape.";
        value 3;
      }
      enum MACRO_WIDE {
        description "Sector shape with wider beam width in azimuth plane than in elevation plane. Azimuth beam width is wider than MACRO sector shape. Refer to CPI for installed radio equipment for exact beam width for MACRO_WIDE sector shape.";
        value 4;
      }
      enum MACRO_2LOBE {
        description "Two lobed sector shape with wider beam width in azimuth plane than in elevation plane. Refer to CPI for installed radio equipment for exact beam width for MACRO_2LOBE sector shape.";
        value 5;
      }
    }
  }
  typedef enum-InhibitA2SearchConfig {
    type enumeration {
      enum NOT_INHIBIT {
        description "No inhibition of A2Search_RSRP nor A2Search_RSRQ report configuration.";
        value 0;
      }
      enum INHIBIT_A2SEARCH_RSRQ {
        description "Inhibition of the A2Search_RSRQ report configuration.";
        value 1;
      }
      enum INHIBIT_A2SEARCH_RSRP {
        description "Inhibition of the A2Search_RSRP report configuration.";
        value 2;
      }
    }
  }
  typedef enum-SleepPowerControlType {
    type enumeration {
      enum USE_MAX_POWER {
        description "MIMO sleep mode uses maximum power available on the transmit branches.";
        value 0;
      }
      enum RETAIN_SAME_POWER {
        description "MIMO sleep mode retains original power on the transmit branches.";
        value 1;
      }
    }
  }
  typedef enum-LoadBalancingVals {
    type enumeration {
      enum NOT_ALLOWED {
        value 0;
      }
      enum ALLOWED {
        value 1;
      }
      enum OFFLOAD {
        value 2;
      }
      enum IFO_AND_IFLB {
        description "Cell is allowed for both offload and load balancing actions.";
        value 3;
      }
    }
  }
  typedef enum-TransmissionModeFDD {
    type enumeration {
      enum TRANSMISSION_MODE_2 {
        description "Transmit diversity";
        value 2;
      }
      enum TRANSMISSION_MODE_3 {
        description "Transmit Diversity and Large delay CDD (depending on rank), also called Open-Loop Spatial Multiplexing";
        value 3;
      }
      enum TRANSMISSION_MODE_4 {
        description "Closed-Loop Spatial Multiplexing";
        value 4;
      }
      enum TRANSMISSION_MODE_9 {
        description "Multiple-Layer Beamforming with UE specific reference signals on Antenna Port 7 and 8.";
        value 9;
      }
    }
  }
  typedef enum-PmEventGroup {
    type enumeration {
      enum S1_PAGING {
        description "PM event S1_PAGING.";
        value 1;
      }
    }
  }
  typedef enum-DrxOperVals {
    type enumeration {
      enum DISABLED {
        description "DRX is disabled in the profile.";
        value 0;
      }
      enum ENABLED {
        description "DRX is enabled using the values defined in the profile.";
        value 1;
      }
      enum ENABLED_COVERAGE_OPTIMIZED {
        description "DRX is enabled only on UEs with good coverage.";
        value 2;
      }
    }
  }
  typedef enum-CaPreference {
    type enumeration {
      enum NONE {
        description "No preference between downlink and uplink carrier aggregation.";
        value 0;
      }
      enum DL {
        description "Downlink carrier aggregation is preferred over uplink carrier aggregation.";
        value 1;
      }
      enum UL {
        description "Uplink carrier aggregation is preferred over downlink carrier aggregation.";
        value 2;
      }
    }
  }
  typedef enum-MibContentScheduling {
    type enumeration {
      enum OFF {
        description "Standardized MIB format. IE SchedulingInfoSIB1-BR-r13 always part of MIB in Cat-M1 enabled cells.";
        value 0;
      }
      enum MODE_1_SCHEDULING {
        description "IE SchedulingInfoSIB1-BR-r13 not part of every MIB in Cat-M1 enabled cells. Schedule in favor of legacy LTE UEs MIB accessibility.";
        value 1;
      }
      enum MODE_2_SCHEDULING {
        description "IE SchedulingInfoSIB1-BR-r13 not part of every MIB in Cat-M1 enabled cells. Schedule in favor of Cat-M1 UEs MIB accessibility.";
        value 2;
      }
    }
  }
  typedef enum-EndcStage {
    type enumeration {
      enum ENDC_NR_CAPABLE {
        description "UE ENDC capability is confirmed.";
        value 0;
      }
      enum ENDC_NR_MATCHED {
        description "UE ENDC capability matches LTE cell configuration.";
        value 1;
      }
      enum ENDC_NR_ACTIVE {
        description "UE ENDC has been created and active.";
        value 2;
      }
      enum ENDC_UE_RELEASED {
        description "UE is released.";
        value 99;
      }
    }
  }
  typedef enum-PrsPerVals {
    type enumeration {
      enum PP160 {
        description "PP160 denotes 160 ms PRS occasion period.";
        value 0;
      }
      enum PP320 {
        description "PP320 denotes 320 ms PRS occasion period.";
        value 1;
      }
      enum PP640 {
        description "PP 640 denotes 640 ms PRS occasion period.\n";
        value 2;
      }
      enum PP1280 {
        description "PP1280 denotes 1280 ms PRS occasion period.";
        value 3;
      }
    }
  }
  typedef enum-AcBarringMode {
    type enumeration {
      enum OFF {
        description "Access Class Barring is de-activated in the cell.";
        value 0;
      }
      enum MANUAL {
        description "Access Class Barring depends on manual settings.";
        value 1;
      }
      enum AUTO {
        description "Access Class Barring is regulated by one of the following:\n- Load-Based Access Barring\n- Progressive Access Barring\n- Progressive Barring for Special Access Classes\n- PLMN-Specific Access Barring";
        value 2;
      }
    }
  }
  typedef enum-ServiceType {
    type enumeration {
      enum UNDEFINED {
        description "No service defined";
        value 0;
      }
      enum VOIP {
        description VoIP;
        value 1;
      }
      enum IMS_SIGNALING {
        description "Indicates bearer is used for IMS signaling.";
        value 2;
      }
      enum PTT {
        description "Indicates bearer is used for Mission Critical and non-Mission Critical Push to Talk.";
        value 3;
      }
      enum MC_SIGNALING {
        description "Indicates bearer is used for Mission Critical delay sensitive signaling.";
        value 4;
      }
    }
  }
  typedef enum-UtranLoadBalancingVals {
    type enumeration {
      enum NOT_ALLOWED {
        description "Load balancing is not allowed";
        value 0;
      }
      enum OFFLOAD {
        description "Offload is allowed";
        value 2;
      }
    }
  }
  typedef enum-ReportInterval {
    type enumeration {
      enum MS_120 {
        value 0;
      }
      enum MS_240 {
        value 1;
      }
      enum MS_480 {
        value 2;
      }
      enum MS_640 {
        value 3;
      }
      enum MS_1024 {
        value 4;
      }
      enum MS_5120 {
        value 5;
      }
      enum MS_10240 {
        value 6;
      }
      enum MIN_1 {
        value 7;
      }
      enum MIN_6 {
        value 8;
      }
      enum MIN_12 {
        value 9;
      }
      enum MIN_30 {
        value 10;
      }
      enum MIN_60 {
        value 11;
      }
      enum MS_2048 {
        value 12;
      }
    }
  }
  typedef enum-InterFreqMeasType {
    type enumeration {
      enum EVENT_A5 {
        description "Event A5 Measurements";
        value 0;
      }
      enum EVENT_A3 {
        description "Event A3 Measurements";
        value 1;
      }
    }
  }
  typedef enum-AbsPrioOverride {
    type enumeration {
      enum NO_OVERRIDE {
        description "The default priority level is used in scheduling.";
        value 0;
      }
      enum HI_PRIO_OVERRIDE {
        description "The default priority level used in scheduling is always overriden; instead the priorities assigned to the QCIs are always used. These QCI priorities are higher (more important) than the default priority level.";
        value 1;
      }
    }
  }
  typedef enum-PowerClass {
    type enumeration {
      enum PC_1 {
        description "Power Class 1.";
        value 0;
      }
      enum PC_2 {
        description "Power Class 2.";
        value 1;
      }
    }
  }
  typedef enum-DynamicSCellSelectionMethod {
    type enumeration {
      enum ROUND_ROBIN {
        description "SCell selection order determined using a round robin selection of SCell candidates. Applicable only if Configurable SCell Priority FAJ 121 4701 is active.";
        value 0;
      }
      enum PRIORITIZED {
        description "SCell selection order determined using a prioritized selection of SCell candidates based on frequency prioritization. Applicable only if Configurable SCell Priority FAJ 121 4701 is active.";
        value 1;
      }
      enum PRIORITIZED_AUTOMATIC {
        description "SCell selection prioritizes carriers with best combination of bandwidth and potential number of layers. Applicable only if Automatic SCell Priority FAJ 121 4734 is active.";
        value 2;
      }
    }
  }
  typedef enum-MbsfnAreaCellStatus {
    type enumeration {
      enum NOT_ACTIVATED {
        description "The Mbsfn area is ready to be activated or reserved in the related cell.";
        value 0;
      }
      enum ACTIVATED {
        description "The Mbsfn area is activated in the related cell.";
        value 1;
      }
      enum FAILED {
        description "The Mbsfn area can not be activated in the related cell because of an configuration conflict.";
        value 2;
      }
      enum CELL_DISABLED {
        description "The Mbsfn area can not be activated in the related cell because the cell is disabled.";
        value 3;
      }
      enum RESERVED {
        description "The related cell is restricted for Unicast traffic on those radio resources that are configured by the MBSFN area. ";
        value 4;
      }
    }
  }
  typedef enum-LongDrxCycle {
    type enumeration {
      enum SF10 {
        description "Number of sub frames";
        value 0;
      }
      enum SF20 {
        description "Number of sub frames";
        value 1;
      }
      enum SF32 {
        description "Number of sub frames";
        value 2;
      }
      enum SF40 {
        description "Number of sub frames";
        value 3;
      }
      enum SF64 {
        description "Number of sub frames";
        value 4;
      }
      enum SF80 {
        description "Number of sub frames";
        value 5;
      }
      enum SF128 {
        description "Number of sub frames";
        value 6;
      }
      enum SF160 {
        description "Number of sub frames";
        value 7;
      }
      enum SF256 {
        description "Number of sub frames";
        value 8;
      }
      enum SF320 {
        description "Number of sub frames";
        value 9;
      }
      enum SF512 {
        description "Number of sub frames";
        value 10;
      }
      enum SF640 {
        description "Number of sub frames";
        value 11;
      }
      enum SF1024 {
        description "Number of sub frames";
        value 12;
      }
      enum SF1280 {
        description "Number of sub frames";
        value 13;
      }
      enum SF2048 {
        description "Number of sub frames";
        value 14;
      }
      enum SF2560 {
        description "Number of sub frames";
        value 15;
      }
    }
  }
  typedef enum-ServOrPrioTriggeredIFHoType {
    type enumeration {
      enum QCI {
        description "If the trigger type is set as QCI, it is preferred that the UE at E-RAB setup with QCI=1 be moved to the other frequency.";
        value 0;
      }
      enum ARP {
        description "If the trigger type is set as ARP,it is preferred that the UE at E-RAB setup with ARP Priroity Level in arpPriorityLevelForSPIFHo list set as true  be moved to the other frequency.";
        value 1;
      }
      enum NOT_ACTIVATED {
        description "If the feature Service or Priority-Triggered Inter-frequency Handover is OPERABLE and the trigger type is set as NOT_ACTIVATED, the feature is not activated.";
        value 2;
      }
    }
  }
  typedef enum-LastModificationSourceCell {
    type enumeration {
      enum OPERATOR {
        value 0;
      }
      enum PCI_MODIFICATION {
        value 1;
      }
      enum RACH_OPT_MODIFICATION {
        value 2;
      }
      enum OSS_PCI_MODIFICATION {
        value 3;
      }
    }
  }
  typedef enum-EUtranLbBnrPolicyVals {
    type enumeration {
      enum NOT_ALLOWED {
        value 0;
      }
      enum AUTO {
        value 1;
      }
      enum LB_ONLY {
        value 2;
      }
      enum OFFLOAD_ONLY {
        value 3;
      }
      enum IFO_AND_IFLB {
        description "Policy for setting cell on the given frequency relation as allowed for both offload and load balancing actions.";
        value 4;
      }
    }
  }
  typedef enum-DrxMode {
    type enumeration {
      enum NO_OVERRIDE {
        description "No override on DRX configuration for the subscriber group.";
        value 0;
      }
      enum DISABLE_DRX {
        description "Disable DRX for the subscriber group.";
        value 1;
      }
      enum RESERVED_FOR_FUTURE_USE {
        description "Reserved for future use.";
        value 2;
      }
    }
  }
  typedef enum-CreatedBy {
    type enumeration {
      enum SYSTEM {
        description "Automatically created by system.";
        value 0;
      }
      enum OPERATOR {
        description "Manually created by operator.";
        value 1;
      }
    }
  }
  typedef enum-TracePmStreamStatusEnum {
    type enumeration {
      enum INACTIVE {
        value 0;
      }
      enum ACTIVE {
        value 1;
      }
      enum CONNECTING {
        value 2;
      }
      enum RECONNECTING {
        value 3;
      }
      enum ERROR {
        value 4;
      }
      enum NOT_LICENSED {
        value 5;
      }
      enum LOAD_INHIBITED {
        description "Temporary turned off due to high load";
        value 6;
      }
      enum STREAM_REPORT_OFF {
        description "Stream reporting turned off because streamStatusNotification is set to false.";
        value 7;
      }
    }
  }
  typedef enum-EUtranProbCellPolicyVals {
    type enumeration {
      enum OFF {
        description "Problematic cell detection is off.";
        value 0;
      }
      enum AUTO_DETECT {
        description "Detection of problematic cell.";
        value 1;
      }
      enum AUTO_DETECT_AND_BAR {
        description "Detection of problematic cell, and when cell EUtranCellRelation::hoSuccLevel is changed from MEDIUM to LOW no handover is performed.";
        value 2;
      }
    }
  }
  typedef enum-RIMCapability {
    type enumeration {
      enum RIM_CAPABLE {
        description "The external cell is RIM capable";
        value 0;
      }
      enum RIM_INCAPABLE {
        description "The external cell is not RIM capable";
        value 1;
      }
      enum RIM_CAPABILITY_UNKNOWN {
        description "The RIM capability of the external cell is unknown";
        value 2;
      }
    }
  }
  typedef enum-OrderCode {
    type enumeration {
      enum RETAIN_EXISTING {
        value 0;
      }
      enum RENEW_ALL_EXISTING {
        value 2;
      }
    }
  }
  typedef enum-AvailStatus {
    description "The availability status is used to qualify the operational state.\n It indicates why the operational state has changed its value. ";
    type enumeration {
      enum IN_TEST {
        description "The resource is undergoing a test procedure.\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.\nThe semantics are defined in CCITT Rec. X.735 | ISO/IEC 10164-6. ";
        value 8;
      }
      enum DEPENDENCY_LOCKED {
        description "The administrative state of a resource that this resource depends on is locked.\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.\n or the availability status of the other resource is dependency shutting down. ";
        value 11;
      }
    }
  }
  typedef enum-SCellCandidate {
    type enumeration {
      enum NOT_ALLOWED {
        description "The cell indicated by the value of parameter cellrelation must not be used as secondary component carrier (SCell) for UE using this cell as their primary component carrier (PCell).";
        value 0;
      }
      enum ALLOWED {
        description "The cell indicated by the value of parameter cellrelation can be used as an SCell CC for UEs that use this cell as their PCell CC for both UL and DL.";
        value 1;
      }
      enum AUTO {
        description "Same as NOT_ALLOWED.";
        value 2;
      }
      enum ONLY_ALLOWED_FOR_DL {
        description "The current cell is allowed to use the cell indicated by the cell relation as an SCell candidate for DL CA only. This SCell cannot be used for UL CA. UL CA performance degradation in SCell occurs if the antenna of the SCell is placed more than 300 meters from the antenna from the PCell. It is recommended that this parameter is set for cases where this can occur.";
        value 3;
      }
    }
  }
  typedef enum-CsiRsConfigType8TxFDD {
    type enumeration {
      enum NZP_CSIRS {
        description "A set of NZP (Non-Zero-Power) CSI-RS (Channel State Information Reference Signal) configurations.";
        value 0;
      }
      enum NZP_ZP_CSIRS {
        description "A set of NZP (Non-Zero-Power) and ZP (Zero-Power) CSI-RS (Channel State Information Reference Signal)  configurations. ZP CSI-RS reduces interference to the CSI-RS of neighboring cell. ";
        value 1;
      }
    }
  }
  typedef enum-UlCalibrationMethod {
    type enumeration {
      enum NONE {
        description "No antenna calibration method.";
        value 0;
      }
      enum INTERNAL {
        description "Internal antenna calibration method.";
        value 1;
      }
    }
  }
  typedef enum-RlcMode {
    type enumeration {
      enum AM {
        value 0;
      }
      enum UM {
        value 1;
      }
      enum TM {
        value 2;
      }
    }
  }
  typedef enum-TransmissionScheme {
    type enumeration {
      enum ANTENNA_SWITCHING {
        description "Transmissions of PRS signals are done using Antenna switching.";
        value 0;
      }
      enum PRECODER_SWITCHING {
        description "Transmissions of PRS signals are done using Pre-coder switching.";
        value 1;
      }
    }
  }
  typedef enum-OnDurationTimer {
    description "Timer for DRX in TS 36.321 [6]. Value in number of PDCCH sub-frames. Value PSF1 corresponds to 1 PDCCH sub-frame, PSF2 corresponds to 2 PDCCH sub-frames and so on.";
    type enumeration {
      enum PSF1 {
        description "Number of PDCCH sub frames";
        value 0;
      }
      enum PSF2 {
        description "Number of PDCCH sub frames";
        value 1;
      }
      enum PSF3 {
        description "Number of PDCCH sub frames";
        value 2;
      }
      enum PSF4 {
        description "Number of PDCCH sub frames";
        value 3;
      }
      enum PSF5 {
        description "Number of PDCCH sub frames";
        value 4;
      }
      enum PSF6 {
        description "Number of PDCCH sub frames";
        value 5;
      }
      enum PSF8 {
        description "Number of PDCCH sub frames";
        value 6;
      }
      enum PSF10 {
        description "Number of PDCCH sub frames";
        value 7;
      }
      enum PSF20 {
        description "Number of PDCCH sub frames";
        value 8;
      }
      enum PSF30 {
        description "Number of PDCCH sub frames";
        value 9;
      }
      enum PSF40 {
        description "Number of PDCCH sub frames";
        value 10;
      }
      enum PSF50 {
        description "Number of PDCCH sub frames";
        value 11;
      }
      enum PSF60 {
        description "Number of PDCCH sub frames";
        value 12;
      }
      enum PSF80 {
        description "Number of PDCCH sub frames";
        value 13;
      }
      enum PSF100 {
        description "Number of PDCCH sub frames";
        value 14;
      }
      enum PSF200 {
        description "Number of PDCCH sub frames";
        value 15;
      }
    }
  }
  typedef enum-AmoStateVals {
    type enumeration {
      enum DISABLED {
        description "Function disabled";
        value 0;
      }
      enum ENABLED {
        description "Function enabled";
        value 1;
      }
    }
  }
  typedef enum-AdaptiveCfiHoProhibitMode {
    type enumeration {
      enum NO_HO_PROHIBIT_CFI {
        description "No prohibit of CFI when scheduling UEs that are in handover.";
        value 0;
      }
      enum HO_PROHIBIT_CFI_1 {
        description "Prohibit CFI=1 when scheduling UEs that are in handover.";
        value 1;
      }
      enum HO_PROHIBIT_CFI_1_AND_2 {
        description "Prohibit CFI=1 and 2 when scheduling UEs that are in handover.";
        value 2;
      }
    }
  }
  typedef enum-PreemptionCapability {
    type enumeration {
      enum SHALL_NOT_TRIGGER_PREEMPTION {
        description "E-RAB shall not pre-empt other E-RABs.";
        value 0;
      }
      enum MAY_TRIGGER_PREEMPTION {
        description "E-RAB may pre-empt other E-RABs.";
        value 1;
      }
    }
  }
  typedef enum-BandIndicator {
    type enumeration {
      enum DCS_1800 {
        value 0;
      }
      enum PCS_1900 {
        value 1;
      }
    }
  }
  typedef enum-MfbiFreqBandIndPrioExt {
    description "Current frequency band indicator status on external cell.\nThis attribute is set during X2_SETUP procedure and can change after ENB_CONFIGURATION_UPDATE.";
    type enumeration {
      enum NOT_BROADCASTED {
        description "External eNodeB supports freqBandIndicatorPriority at X2 handovers, but it is not broadcasted in SIB1 in this cell. Primary band has highest priority in this cell.";
        value 0;
      }
      enum BROADCASTED {
        description "External eNodeB supports freqBandIndicatorPriority at X2 handovers, and freqBandIndicatorPriority is broadcasted in SIB1 in this cell. Primary band has lowest priority in this cell if UE indicates freqBandPriorityAdjustment capability.";
        value 1;
      }
      enum NOT_SUPPORTED {
        description "External eNodeB does not support freqBandIndicatorPriority at X2 handovers. Primary band has highest priority in all cells in this eNodeB.";
        value 2;
      }
      enum UNDEFINED_VALUE {
        description "Default value when there is not yet X2 connection established to eNodeB hosting the cell.";
        value 1000;
      }
    }
  }
  typedef enum-CfiMode {
    type enumeration {
      enum CFI_STATIC_BY_BW {
        description "For FDD:\nControl region uses only CFI=1 for 15 and 20 MHz system bandwidth, and uses only CFI=2 otherwise.\nFor TDD:\nControl region uses only CFI=1 for 10 MHz and greater system bandwidth, and uses only CFI=2 otherwise.";
        value 0;
      }
      enum CFI_STATIC_1 {
        description "Control region uses only CFI=1.";
        value 1;
      }
      enum CFI_STATIC_2 {
        description "Control region uses only CFI=2.";
        value 2;
      }
      enum CFI_STATIC_3 {
        description "Control region uses only CFI=3.";
        value 3;
      }
      enum CFI_AUTO_MAXIMUM_2 {
        description "Control region dynamically adapts CFI up to the value of 2, depending on the actual load in each subframe.";
        value 4;
      }
      enum CFI_AUTO_MAXIMUM_3 {
        description "Control region dynamically adapts CFI up to the value of 3, depending on the actual load in each subframe.";
        value 5;
      }
    }
  }
  typedef enum-TracePmFileStatusEnum {
    type enumeration {
      enum INACTIVE {
        value 0;
      }
      enum ACTIVE {
        value 1;
      }
      enum FILECLOSED {
        description "Currently not used.";
        value 2;
      }
      enum LOAD_INHIBITED {
        description "Temporary turned off due to high load";
        value 3;
      }
    }
  }
  typedef enum-AltMmeInfo {
    type enumeration {
      enum DEFAULT_DCN {
        description "The MME that belongs to default dedicated core network.";
        value 0;
      }
      enum SENT_NAS_REQUEST {
        description "The MME that sent reroute NAS request message to eNodeB.";
        value 1;
      }
    }
  }
  typedef enum-CreatedByEutran {
    type enumeration {
      enum ANR {
        value 0;
      }
      enum X2 {
        value 1;
      }
      enum OPERATOR {
        value 2;
      }
    }
  }
  typedef enum-SchedulingAlgorithm {
    type enumeration {
      enum RESOURCE_FAIR {
        value 0;
      }
      enum EQUAL_RATE {
        value 1;
      }
      enum PROPORTIONAL_FAIR_HIGH {
        value 2;
      }
      enum PROPORTIONAL_FAIR_MEDIUM {
        value 3;
      }
      enum PROPORTIONAL_FAIR_LOW {
        value 4;
      }
      enum MAXIMUM_C_OVER_I {
        value 5;
      }
      enum DELAY_BASED {
        value 6;
      }
    }
  }
  typedef enum-LastModificationEutran {
    type enumeration {
      enum ANR_MODIFICATION {
        value 0;
      }
      enum X2_MODIFICATION {
        value 1;
      }
      enum OPERATOR_MODIFICATION {
        value 2;
      }
      enum ANR_DELETE {
        value 3;
      }
      enum X2_DELETE {
        value 4;
      }
      enum OPERATOR_DELETE {
        value 5;
      }
      enum NOT_MODIFIED {
        value 6;
      }
      enum MRO_MODIFICATION {
        value 7;
      }
      enum PCI_MODIFICATION {
        value 8;
      }
      enum MLB_MODIFICATION {
        value 9;
      }
      enum RACH_OPT_MODIFICATION {
        value 10;
      }
      enum LM_MODIFICATION {
        description "Load Management has modified the object.";
        value 11;
      }
    }
  }
  typedef enum-NbIotFrequencyOffset {
    type enumeration {
      enum V_10 {
        description "Offset of channel number to EARFCN.";
        value 0;
      }
      enum V_9 {
        description "Offset of channel number to EARFCN.";
        value 1;
      }
      enum V_8 {
        description "Offset of channel number to EARFCN.";
        value 2;
      }
      enum V_7 {
        description "Offset of channel number to EARFCN.";
        value 3;
      }
      enum V_6 {
        description "Offset of channel number to EARFCN.";
        value 4;
      }
      enum V_5 {
        description "Offset of channel number to EARFCN.";
        value 5;
      }
      enum V_4 {
        description "Offset of channel number to EARFCN.";
        value 6;
      }
      enum V_3 {
        description "Offset of channel number to EARFCN.";
        value 7;
      }
      enum V_2 {
        description "Offset of channel number to EARFCN.";
        value 8;
      }
      enum V_1 {
        description "Offset of channel number to EARFCN.";
        value 9;
      }
      enum V_05 {
        description "Offset of channel number to EARFCN.";
        value 10;
      }
      enum V0 {
        description "Offset of channel number to EARFCN.";
        value 11;
      }
      enum V05 {
        description "Offset of channel number to EARFCN.";
        status deprecated {
          yexte:status-information "Since 17.Q4. Planned to be removed.";
        }
        value 12;
      }
      enum V1 {
        description "Offset of channel number to EARFCN.";
        value 13;
      }
      enum V2 {
        description "Offset of channel number to EARFCN.";
        value 14;
      }
      enum V3 {
        description "Offset of channel number to EARFCN.";
        value 15;
      }
      enum V4 {
        description "Offset of channel number to EARFCN.";
        value 16;
      }
      enum V5 {
        description "Offset of channel number to EARFCN.";
        value 17;
      }
      enum V6 {
        description "Offset of channel number to EARFCN.";
        value 18;
      }
      enum V7 {
        description "Offset of channel number to EARFCN.";
        value 19;
      }
      enum V8 {
        description "Offset of channel number to EARFCN.";
        value 20;
      }
      enum V9 {
        description "Offset of channel number to EARFCN.";
        value 21;
      }
    }
  }
  typedef enum-PimMitigStatus {
    type enumeration {
      enum PIM_MITIG_STATUS_UNKNOWN {
        description "Initial PIM mitigation status, after cell creation, before receival of system's PIM mitigation capabilities.";
        value 0;
      }
      enum PIM_MITIG_STATUS_ACTIVE {
        description "PIM mitigation is activated on the enabled cell.";
        value 1;
      }
      enum PIM_MITIG_STATUS_FAILED {
        description "PIM mitigation activation failed due to no carriers supported with the PIM measurements in the radio unit.";
        value 2;
      }
      enum PIM_MITIG_STATUS_FINISHED {
        description "PIM mitigation has been deactivated on the cell.";
        value 3;
      }
    }
  }
  typedef enum-CellBarred {
    type enumeration {
      enum BARRED {
        value 0;
      }
      enum NOT_BARRED {
        value 1;
      }
    }
  }
  typedef enum-MbsfnSubframesForTm9 {
    type enumeration {
      enum DISABLED {
        description "No PDSCH data sent in MBSFN subframes to UEs in TM9. No subframes configured as MBSFN subframe for this.";
        value 0;
      }
      enum ENABLED_10_PERCENT {
        description "PDSCH data sent in MBSFN subframes to UEs in TM9. One subframe per frame configured as MBSFN subframe for this.";
        value 1;
      }
      enum ENABLED_20_PERCENT {
        description "PDSCH data sent in MBSFN subframes to UEs in TM9. Two subframes per frame configured as MBSFN subframe for this.";
        value 2;
      }
      enum ENABLED_30_PERCENT {
        description "PDSCH data sent in MBSFN subframes to UEs in TM9. Three subframes per frame configured as MBSFN subframe for this.";
        value 3;
      }
      enum ENABLED_40_PERCENT {
        description "PDSCH data sent in MBSFN subframes to UEs in TM9. Four subframes per frame configured as MBSFN subframe for this.";
        value 4;
      }
      enum ENABLED_50_PERCENT {
        description "PDSCH data sent in MBSFN subframes to UEs in TM9. Five subframes per frame configured as MBSFN subframe for this.";
        value 5;
      }
      enum ENABLED_60_PERCENT {
        description "PDSCH data sent in MBSFN subframes to UEs in TM9. Six subframes per frame configured as MBSFN subframe for this.";
        value 6;
      }
    }
  }
  typedef enum-DlPowerState {
    type enumeration {
      enum INVALID {
        description "Downlink output power state is not available.";
        value 0;
      }
      enum STABLE {
        description "Downlink output power is stable.";
        value 1;
      }
      enum CHANGING {
        description "Downlink output power is changing to reach dlPowerRatio.";
        value 2;
      }
    }
  }
  typedef enum-LastModificationUtran {
    type enumeration {
      enum ANR_MODIFICATION {
        description "ANR has modified the object.";
        value 0;
      }
      enum OPERATOR_MODIFICATION {
        description "Operator has modified the object.";
        value 1;
      }
      enum NOT_MODIFIED {
        description "Object has not been modified since creation of object.";
        value 2;
      }
      enum ANR_DELETE {
        description "ANR has deleted the object. ";
        value 3;
      }
      enum OPERATOR_DELETE {
        description "Operator has deleted the object. ";
        value 4;
      }
      enum LM_MODIFICATION {
        description "Load Management has modified the object.";
        value 5;
      }
    }
  }
  typedef enum-PositioningMethod {
    type enumeration {
      enum NONE {
        description "Positioning method is not activated.";
        value 0;
      }
      enum GNSS {
        description "GNSS is used for positioning method.";
        value 1;
      }
    }
  }
  typedef enum-PuschChannelEstWindowSize {
    type enumeration {
      enum NORMAL_SIZE {
        description "Normal Window Size for PUSCH filter channel estimation.";
        value 0;
      }
      enum LARGE_SIZE {
        description "Large Window Size for PUSCH filter channel estimation.";
        value 1;
      }
    }
  }
  typedef enum-TtiBundlingAtSetup {
    type enumeration {
      enum OFF {
        description "No change of TTI bundling activating method.";
        value 0;
      }
      enum ACT_TTIB_IMM {
        description "Activate TTI Bundling immediately at establishment of QCI1 bearer.";
        value 1;
      }
    }
  }
  typedef enum-RlcDlDeliveryFailAction {
    type enumeration {
      enum UE_CONTEXT_RELEASE {
        description "Trigger a UE Context Release whenever an RLC DL Delivery failure is detected on any of the DRBs in the connection.";
        value 0;
      }
      enum RETAIN_CONNECTION_IF_OTHER_DRB_WITH_HIGHER_ARP {
        description "When an RLC DL Delivery failure is detected on a DRB in the connection and there are other DRBs with higher ARP in the connection, mark the failing DRB as failed and continue with the other DRBs\nIf there is RLC Delivery failure on SRB or on the DRB used for IMS Signaling (indicated by ServiceType in QciProfileOperatorDefined/QciProfilePredefined), the design base behavior applies, that is, eNB triggers a UE Context Release regardless of the value of attribute rlcDlDeliveryFailureAction.";
        value 1;
      }
      enum RETAIN_CONNECTION_IF_OTHER_DRB_WITH_HIGHER_OR_EQUAL_ARP {
        description "When an RLC DL Delivery failure is detected on a DRB in the connection and there are other DRBs with higher or equal ARP in the connection, mark the failing DRB as failed and continue with the other DRBs.\nIf there is RLC Delivery failure on SRB or on the DRB used for IMS Signaling (indicated by ServiceType in QciProfileOperatorDefined/QciProfilePredefined), the design base behavior applies, that is, eNB triggers a UE Context Release regardless of the value of attribute rlcDlDeliveryFailureAction.";
        value 2;
      }
    }
  }
  typedef enum-CsiRsConfigTypeFDD {
    type enumeration {
      enum NZP_CSIRS {
        description "A set of NZP (Non-Zero-Power) CSI-RS (Channel State Information Reference Signal) configurations.";
        value 0;
      }
      enum NZP_ZP_CSIRS {
        description "A set of NZP (Non-Zero-Power) and ZP (Zero-Power) CSI-RS (Channel State Information Reference Signal) configurations. ZP CSI-RS reduces interference to the CSI-RS of neighboring cell.";
        value 1;
      }
    }
  }
  typedef enum-Ns05LBSchedMode {
    type enumeration {
      enum ALWAYS_PROHIBIT {
        description "NS_05 low band scheduling is prohibit.";
        value 0;
      }
      enum ALWAYS_AVAILABLE {
        description "NS_05 low band scheduling is always available for all regions.";
        value 1;
      }
      enum ADAPTIVE_AVAILABLE_BY_REPEATER_DETECTION {
        description "NS_05 low band scheduling is scheduled for repeaters in network.";
        value 2;
      }
    }
  }
  typedef enum-HoStatisticsStatus {
    type enumeration {
      enum OFF {
        description "The problematicCellPolicy is set to OFF.";
        value 0;
      }
      enum HIGH {
        description "Handover execution success rate is perceived as high.";
        value 1;
      }
      enum MEDIUM {
        description "Handover execution success rate is perceived as medium.";
        value 2;
      }
      enum LOW {
        description "Handover execution success rate is perceived as low.";
        value 3;
      }
    }
  }
  typedef enum-CeLevelNbIot {
    type enumeration {
      enum CE_0 {
        description "NbIot Coverage enhancement level 0";
        value 0;
      }
      enum CE_1 {
        description "NbIot Coverage enhancement level 1";
        value 1;
      }
      enum CE_2 {
        description "NbIot Coverage enhancement level 2";
        value 2;
      }
    }
  }
  typedef enum-RadioOperatingMode {
    type enumeration {
      enum DEFAULT {
        description "Radio is requested to be at the default operating mode.";
        value 0;
      }
      enum QAM_64_BOOST {
        description "Radio is requested to be at an operating mode to achieve good throughput performance when the highest modulation in DL is 64 QAM.";
        value 1;
      }
      enum QAM_256_BOOST {
        description "Radio is requested to be at an operating mode to achieve good throughput performance when the highest modulation in DL is 256 QAM.";
        value 2;
      }
      enum MAX_POWER_CLASS {
        description "Radio is requested to be at the highest power level of the power amplifier.";
        value 3;
      }
    }
  }
  typedef enum-ShortDrxCycle {
    description "Short DRX cycle in TS 36.321 [6]. Value in number of sub-frames. Value SF2 corresponds to 2 sub-frames, SF5 corresponds to 5 subframes and so on.";
    type enumeration {
      enum SF2 {
        description "Number of sub frames";
        value 0;
      }
      enum SF5 {
        description "Number of sub frames";
        value 1;
      }
      enum SF8 {
        description "Number of sub frames";
        value 2;
      }
      enum SF10 {
        description "Number of sub frames";
        value 3;
      }
      enum SF16 {
        description "Number of sub frames";
        value 4;
      }
      enum SF20 {
        description "Number of sub frames";
        value 5;
      }
      enum SF32 {
        description "Number of sub frames";
        value 6;
      }
      enum SF40 {
        description "Number of sub frames";
        value 7;
      }
      enum SF64 {
        description "Number of sub frames";
        value 8;
      }
      enum SF80 {
        description "Number of sub frames";
        value 9;
      }
      enum SF128 {
        description "Number of sub frames";
        value 10;
      }
      enum SF160 {
        description "Number of sub frames";
        value 11;
      }
      enum SF256 {
        description "Number of sub frames";
        value 12;
      }
      enum SF320 {
        description "Number of sub frames";
        value 13;
      }
      enum SF512 {
        description "Number of sub frames";
        value 14;
      }
      enum SF640 {
        description "Number of sub frames";
        value 15;
      }
    }
  }
  typedef enum-CreatedByIrat {
    type enumeration {
      enum OPERATOR {
        value 0;
      }
      enum ANR {
        value 1;
      }
    }
  }
  typedef enum-MdtReportingTrigger {
    type enumeration {
      enum PERIODICAL {
        description "Periodic MDT measurement reporting.";
        value 0;
      }
      enum EVENT_A2 {
        description "A2 event-triggered measurement reporting.";
        value 1;
      }
      enum EVENT_A2_PERIODIC {
        description "A2 event-triggered periodic measurement reporting.";
        value 2;
      }
    }
  }
  typedef enum-CdmaMsIdType {
    type enumeration {
      enum EMSIS_ESN {
        description "The type of MS identity is IMSI_S and ESN. This value is applicable only when TMSI is not supported";
        value 0;
      }
      enum IMSI_OR_TMSI {
        description "The type of MS identity is TMSI if the TMSI is supported and a TMSI is assigned to the MS, or  the type of MS identity will be IMSI";
        value 2;
      }
      enum IMSI_ESN_OR_TMSI {
        description "The type of MS identity is TMSI if the TMSI is  supported and a TMSI is assigned to the MS,  or  the type of MS identity is IMSI and ESN";
        value 3;
      }
    }
  }
  typedef enum-UnlicensedBandList {
    type enumeration {
      enum NONE {
        description "No band selected.";
        value 0;
      }
      enum BAND_46A {
        description "Band 46A: EARFCN 46890 - 47690.";
        value 1;
      }
      enum BAND_46B {
        description "Band 46B: EARFCN 47890 - 48690.";
        value 2;
      }
      enum BAND_46C {
        description "Band 46C: EARFCN 50090 - 52490.";
        value 3;
      }
      enum BAND_46D {
        description "Band 46D: EARFCN 52740 - 54340.";
        value 4;
      }
    }
  }
  typedef enum-HrpdBandClass {
    type enumeration {
      enum BAND_CLASS_0 {
        description "800 MHz cellular band";
        value 0;
      }
      enum BAND_CLASS_1 {
        description "1.8 to 2.0 GHz PCS band";
        value 1;
      }
      enum BAND_CLASS_2 {
        description "872 to 960 MHz TACS band";
        value 2;
      }
      enum BAND_CLASS_3 {
        description "832 to 925 MHz JTACS band";
        value 3;
      }
      enum BAND_CLASS_4 {
        description "1.75 to 1.87 GHz Korean PCS band";
        value 4;
      }
      enum BAND_CLASS_5 {
        description "450 MHz NMT band";
        value 5;
      }
      enum BAND_CLASS_6 {
        description "2 GHz IMT-2000 band";
        value 6;
      }
      enum BAND_CLASS_7 {
        description "700 MHz band";
        value 7;
      }
      enum BAND_CLASS_8 {
        description "1800 MHz band";
        value 8;
      }
      enum BAND_CLASS_9 {
        description "900 MHz band";
        value 9;
      }
      enum BAND_CLASS_10 {
        description "Secondary 800 MHz band";
        value 10;
      }
      enum BAND_CLASS_11 {
        description "400 MHz European PAMR band";
        value 11;
      }
      enum BAND_CLASS_12 {
        description "800 MHz PAMR band";
        value 12;
      }
      enum BAND_CLASS_13 {
        description "2.5 GHz IMT-2000 Extension Band";
        value 13;
      }
      enum BAND_CLASS_14 {
        description "US PCS 1.9GHz Band";
        value 14;
      }
      enum BAND_CLASS_15 {
        description "AWS Band";
        value 15;
      }
      enum BAND_CLASS_16 {
        description "US 2.5GHz Band";
        value 16;
      }
      enum BAND_CLASS_17 {
        description "US 2.5GHz Forward Link Only Band";
        value 17;
      }
      enum BAND_CLASS_18 {
        description "700 MHz Public Safety Band";
        value 18;
      }
      enum BAND_CLASS_19 {
        description "Lower 700 MHz Band";
        value 19;
      }
      enum BAND_CLASS_20 {
        description L-Band;
        value 20;
      }
      enum BAND_CLASS_21 {
        description S-Band;
        value 21;
      }
      enum UNDEFINED_VALUE {
        description "This value can never be used - either at create or modify of an MO.\nException: This value may be used in dummyCdmaBandClass in EUtranCellFDD/EUtranCellTDD with the effect that the configured cdmaBandClass in Cdma2000FreqBand will be sent in MobilityParametersCDMA2000 information element.";
        value 99;
      }
    }
  }
  typedef enum-DtmSupport {
    type enumeration {
      enum NO_DTM_SUPPORT {
        description "Dual Transfer Mode (DTM) is not supported by the cell.";
        value 0;
      }
      enum DTM_SUPPORT {
        description "Dual Transfer Mode (DTM) is supported by the cell.";
        value 1;
      }
    }
  }
  typedef enum-ExternalUlTrigHoSupport {
    type enumeration {
      enum NO_ULTRIG_HO {
        description "Uplink triggered handover is disabled.";
        value 0;
      }
      enum ULTRIG_HO_NO_UL_EVAL {
        description "Uplink triggered handover is enabled without uplink SINR evaluation.";
        value 1;
      }
    }
  }
  typedef enum-NbIotCellType {
    type enumeration {
      enum NBIOT_INBAND {
        description "Nb-Iot inband deployment, same PCI";
        value 1;
      }
      enum NBIOT_GUARDBAND {
        description "Nb-Iot guardband deployment";
        value 2;
      }
      enum NBIOT_STANDALONE {
        description "Nb-Iot standalone deployment";
        value 3;
      }
      enum NBIOT_INBAND_NOT_SAME_PCI {
        description "Nb-Iot inband deployment, not same PCI";
        value 4;
      }
    }
  }
  typedef enum-ExternalUlCompGroupAvail {
    type enumeration {
      enum DISABLED {
        description "Resource is inoperable.";
        value 0;
      }
      enum ENABLED {
        description "Resource is operable.";
        value 1;
      }
    }
  }
  typedef enum-NonPlannedPciTargetIdType {
    type enumeration {
      enum MACRO_ENODEB_ID {
        description "Macro eNB ID (20bit) used as Target eNB-ID to encode the message Handover Required for the Non-planned PCI.";
        value 0;
      }
      enum HOME_ENODEB_ID {
        description "Home eNB ID (28bit) used as Target eNB-ID to encode the message Handover Required for the Non-planned PCI.";
        value 1;
      }
    }
  }
  typedef enum-SrvccCapability {
    type enumeration {
      enum NOT_SUPPORTED {
        description "SRVCC is not supported";
        value 0;
      }
      enum CS_ONLY_SUPPORTED {
        description "SRVCC is supported for voice bearer(s) only (CS only)";
        value 1;
      }
      enum PS_AND_CS_SUPPORTED {
        description "SRVCC is supported for voice and PS bearers (PS and CS)";
        value 2;
      }
    }
  }
  typedef enum-TtiBundTriggerAlignment {
    type enumeration {
      enum OFF {
        description "No trigger alignment with other features.";
        value 0;
      }
      enum ULTRIG {
        description "Uplink quality measurements aligned with feature Uplink-Triggerd Inter-Frequency Mobility.";
        value 1;
      }
    }
  }
  typedef enum-ReportQuantity {
    type enumeration {
      enum SAME_AS_TRIGGER_QUANTITY {
        value 0;
      }
      enum BOTH {
        value 1;
      }
    }
  }
  typedef enum-ResourceType {
    type enumeration {
      enum NON_GBR {
        description "Indicates the resource type of a QCI is Non-GBR type.";
        value 0;
      }
      enum GBR {
        description "Indicates the resource type of a QCI is GBR type.";
        value 1;
      }
    }
  }
  typedef enum-AilgLoadType {
    type enumeration {
      enum PDSCH_NO_BF {
        description "Only PDSCH load without Beam Forming";
        value 0;
      }
      enum PDSCH_BF_TYPE1 {
        description "Only PDSCH load with Beam Forming Type 1.\nBeam Forming Type 1 emulates in total four predefined beams. One and the same beam per TTI is used during ailgChangePeriod, after which the beam is changed to another one according to a predefined order.";
        value 1;
      }
      enum PDSCH_NO_BF_AND_PDCCH {
        description "PDSCH load without Beam Forming, and PDCCH load";
        value 2;
      }
      enum PDSCH_BF_TYPE1_AND_PDCCH {
        description "PDSCH load with Beam Forming Type 1, and PDCCH load.\nBeam Forming Type 1 emulates in total four predefined beams. One and the same beam per TTI is used during ailgChangePeriod, after which the beam is changed to another one according to a predefined order.";
        value 3;
      }
      enum PDSCH_BF_TYPE2 {
        description "Only PDSCH load with Beam Forming Type 2.\nBeam Forming Type 2 emulates in total four predefined beams. Four beams per TTI are used during ailgChangePeriod, after which the PRB positions for each beam are changed according to a predefined order.";
        value 4;
      }
      enum PDSCH_BF_TYPE2_AND_PDCCH {
        description "PDSCH load with Beam Forming Type 2, and PDCCH load.\nBeam Forming Type 2 emulates in total four predefined beams. Four beams per TTI are used during ailgChangePeriod, after which the PRB positions for each beam are changed according to a predefined order.";
        value 5;
      }
      enum PDCCH_ONLY {
        description "Only PDCCH load";
        value 6;
      }
    }
  }
  typedef enum-B46ChannelUsage {
    description "Deprecated: Since 17.Q2. Planned to be removed.";
    type enumeration {
      enum CHANNEL_DISABLED {
        description "Channel disabled";
        status deprecated {
          yexte:status-information "Since 17.Q2. Has no functional behavior. Planned to be removed.";
        }
        value 0;
      }
      enum CHANNEL_ENABLED {
        description "Channel enabled";
        status deprecated {
          yexte:status-information "Since 17.Q2. Has no functional behavior. Planned to be removed.";
        }
        value 1;
      }
    }
  }
  typedef enum-PrbPatternModel {
    type enumeration {
      enum OCNG {
        description "OCNG FDD pattern as in 3GPP 36.133";
        value 0;
      }
      enum TRAFFIC_MODEL {
        description "Configured traffic model";
        value 1;
      }
      enum NO_HIGH_PRIO_LOAD {
        description "No high priority artificial load";
        value 2;
      }
    }
  }
  typedef enum-IuaIntervalSelection {
    type enumeration {
      enum LOAD_BASED_SELECTION {
        description "Semi-persistent scheduling interval in uplink. Value 0 means interval is selected based on load conditions.";
        value 0;
      }
      enum INTERVAL_1MS {
        description "Semi-persistent scheduling interval in uplink. Value 1 means 1ms interval is selected.";
        value 1;
      }
      enum INTERVAL_2MS {
        description "Semi-persistent scheduling interval in uplink. Value 2 means 2ms interval is selected.";
        value 2;
      }
      enum INTERVAL_4MS {
        description "Semi-persistent scheduling interval in uplink. Value 3 means 4ms interval is selected.";
        value 3;
      }
      enum INTERVAL_5MS {
        description "Semi-persistent scheduling interval in uplink. Value 4 means 5ms interval is selected.";
        value 4;
      }
    }
  }
  typedef enum-FeatureName {
    type enumeration {
      enum FEATURE_NAME1 {
        description "Feature Coverage-Triggered WCDMA IRAT Handover.";
        value 0;
      }
      enum FEATURE_NAME2 {
        description "Feature SRVCC Handover to UTRAN.";
        value 1;
      }
      enum FEATURE_NAME3 {
        description "Feature SRVCC Handover to GERAN.";
        value 2;
      }
      enum FEATURE_NAME4 {
        description "Feature TTI Bundling.";
        value 3;
      }
      enum FEATURE_NAME5 {
        description "Feature Ericsson Lean Carrier.";
        value 4;
      }
      enum FEATURE_NAME6 {
        description "Feature Carrier Aggregation.";
        value 5;
      }
      enum FEATURE_NAME7 {
        description "Feature Basic Intelligent Connectivity.";
        value 6;
      }
      enum FEATURE_NAME8 {
        description "Feature TM9 with AAS FDD.";
        value 7;
      }
      enum FEATURE_NAME9 {
        description "Spare, see UD Differentiated UE Handling.";
        value 8;
      }
      enum FEATURE_NAME10 {
        description "Spare, see UD Differentiated UE Handling.";
        value 9;
      }
    }
  }
  typedef enum-AQMMode {
    type enumeration {
      enum OFF {
        description "Turned off";
        value 0;
      }
      enum MODE1 {
        description "non-GBR mode";
        value 1;
      }
      enum MODE2 {
        description "GBR mode";
        value 2;
      }
    }
  }
  typedef enum-AcBarringModeEm {
    type enumeration {
      enum MANUAL {
        description "Access Class Barring for Emergency calls depends on manual settings.";
        value 0;
      }
      enum AUTO {
        description "Access Class Barring for Emergency calls is regulated by Progressive Barring for Special Access Classes.";
        value 1;
      }
    }
  }
  typedef enum-SupportedCoverage {
    type enumeration {
      enum NONE {
        description "There is no coverage relation (e.g. the cells only partially overlap).";
        value 0;
      }
      enum COVERS {
        description "The related cell covers the EUTRAN cell.";
        value 1;
      }
      enum OVERLAP {
        description "The related cell and the EUTRAN cell has approximately the same coverage area.";
        value 2;
      }
      enum CONTAINED_IN {
        description "The related cell is contained in the EUTRAN cell.";
        value 3;
      }
    }
  }
  typedef enum-ReasonIrat {
    type enumeration {
      enum NONE {
        description "Cell relation is not barred for mobility.";
        value 0;
      }
      enum PLMN_NOT_SUPPORTED {
        description "Cell relation is barred for mobility. Target PLMN is not supported.";
        value 1;
      }
    }
  }
  typedef enum-MappingInfo {
    type enumeration {
      enum NOT_MAPPED {
        description "The SIB designated in \"mappingInfoSIBx\"  is not mapped to any SI message and will not be broadcast.";
        value 0;
      }
      enum MAPPED_SI_1 {
        description "The SIB designated in \"mappingInfoSIBx\" shall be included in SI message 1";
        value 1;
      }
      enum MAPPED_SI_2 {
        description "The SIB designated in \"mappingInfoSIBx\" shall be included in SI message 2";
        value 2;
      }
      enum MAPPED_SI_3 {
        description "The SIB designated in \"mappingInfoSIBx\" shall be included in SI message 3";
        value 3;
      }
      enum MAPPED_SI_4 {
        description "The SIB designated in \"mappingInfoSIBx\" shall be included in SI message 4";
        value 4;
      }
      enum MAPPED_SI_5 {
        description "The SIB designated in \"mappingInfoSIBx\" shall be included in SI message 5";
        value 5;
      }
      enum MAPPED_SI_6 {
        description "The SIB designated in \"mappingInfoSIBx\" shall be included in SI message 6";
        value 6;
      }
      enum MAPPED_SI_7 {
        description "The SIB designated in \"mappingInfoSIBx\" shall be included in SI message 7";
        value 7;
      }
      enum MAPPED_SI_8 {
        description "The SIB designated in \"mappingInfoSIBx\" shall be included in SI message 8";
        value 8;
      }
      enum MAPPED_SI_9 {
        description "The SIB designated in \"mappingInfoSIBx\" shall be included in SI message 9";
        value 9;
      }
      enum MAPPED_SI_10 {
        description "The SIB designated in \"mappingInfoSIBx\" shall be included in SI message 10";
        value 10;
      }
    }
  }
  typedef enum-RIMAssociationStatus {
    type enumeration {
      enum RIM_ACTIVE {
        description "There is an active RIM association with this external cell";
        value 0;
      }
      enum RIM_INACTIVE {
        description "There is no active RIM association with this cell";
        value 1;
      }
      enum RIM_STOPPED {
        description "The RIM association with this cell has been stopped.";
        value 2;
      }
    }
  }
  typedef enum-ChannelCharacteristicList {
    type enumeration {
      enum CHANNEL_DISABLED {
        description "Channel disabled.";
        value 0;
      }
      enum CHANNEL_ENABLED {
        description "Channel enabled.";
        value 1;
      }
    }
  }
  typedef enum-UlPimCancellationMode {
    type enumeration {
      enum EXCLUDED {
        description "Excludes UL carriers from PIM cancellation calculations.";
        value 0;
      }
      enum DEACTIVATED {
        description "De-activates PIM cancellation for UL carriers.";
        value 1;
      }
      enum ACTIVATED {
        description "Activates PIM cancellation for UL carriers.";
        value 2;
      }
    }
  }
  typedef enum-AcBarringPlmnPriorityLevel {
    type enumeration {
      enum PRIORITY0 {
        description "PLMN priority level in PLMN-Specific Access Barring is 0.";
        value 0;
      }
      enum PRIORITY1 {
        description "PLMN priority level in PLMN-Specific Access Barring is 1.";
        value 1;
      }
      enum PRIORITY2 {
        description "PLMN priority level in PLMN-Specific Access Barring is 2.";
        value 2;
      }
    }
  }
  typedef enum-MobilityActionGeran {
    type enumeration {
      enum RELEASE_WITH_REDIRECT {
        description "Release with Redirect.";
        value 0;
      }
      enum RELEASE_WITH_REDIRECT_NACC {
        description "Release with Redirect including Network Assisted Cell Change (NACC) information.";
        value 1;
      }
    }
  }
  typedef enum-SrsAllocationStrategy {
    type enumeration {
      enum DEACTIVATED {
        description "Indicates the SRS allocation strategy is to have SRS disabled.";
        value 0;
      }
      enum ACTIVATED {
        description "Indicates the SRS allocation strategy is to have SRS enabled.";
        value 1;
      }
    }
  }
  typedef enum-EScellState {
    type enumeration {
      enum DISABLED {
        description "The resource is totally inoperable.";
        value 0;
      }
      enum ENABLED {
        description "The resource is partially or fully operable.";
        value 1;
      }
      enum NOT_APPLICABLE {
        description "This attribute does not apply because this cell is not external.";
        value 2;
      }
      enum ENABLED_ERAN {
        description "The resource is partially or fully operable and supporting elastic RAN CA.";
        value 3;
      }
      enum EANBLED_IENB {
        description "The resource is partially or fully operable and supporting IeNB CA.";
        status deprecated {
          yexte:status-information "Since 17.Q2. Replaced by ENABLED_IENB. Planned to be removed.";
        }
        value 4;
      }
      enum DISABLED_CELLSTATE {
        description "The resource is totally inoperable and the first root cause is that the ESCell cell state does not allow CA activity.";
        value 5;
      }
      enum DISABLED_LICENSE {
        description "The resource is totally inoperable and the first root cause is that there are license issues.";
        value 6;
      }
      enum DISABLED_BB_COMPATABILITY {
        description "The resource is totally inoperable and the first root cause is that the basebands between this eNodeB and the eNodeB hosting the ESCell are incompatible.";
        status deprecated {
          yexte:status-information "Since 17.Q2. Replaced by DISABLED_BB_COMPATIBILITY. Planned to be removed.";
        }
        value 7;
      }
      enum DISABLED_LINK {
        description "The resource is totally inoperable and the first root cause is that the baseband-to-baseband link between this eNodeB and the eNodeB hosting the ESCell is inoperable.";
        value 8;
      }
      enum DISABLED_MISMATCHED_MODE {
        description "The resource is totally inoperable and the first root cause is that the carrier aggregation mode used by the ESCell is not consistent with the carrier aggregation mode required by this eNodeB.";
        value 9;
      }
      enum ENABLED_IENB {
        description "The resource is partially or fully operable and supporting IeNB CA.";
        value 10;
      }
      enum DISABLED_BB_COMPATIBILITY {
        description "Resource is inoperable and root cause is that basebands are incompatible between this eNodeB and eNodeB hosting the ESCell.";
        value 11;
      }
    }
  }
  typedef enum-MobilityActionCsfbUtranFDD {
    type enumeration {
      enum RELEASE_WITH_REDIRECT {
        description "Release with Redirect.";
        value 0;
      }
      enum RELEASE_WITH_REDIRECT_NACC {
        description "Release with Redirect including Network Assisted Cell Change (NACC) information.";
        value 1;
      }
      enum HANDOVER {
        description Handover;
        value 2;
      }
    }
  }
  typedef enum-AcBarringPriorityLevel {
    type enumeration {
      enum PRIORITY0 {
        description "Priority level for Progressive Access Barring is 0.";
        value 0;
      }
      enum PRIORITY1 {
        description "Priority level for Progressive Access Barring is 1.";
        value 1;
      }
      enum PRIORITY2 {
        description "Priority level for Progressive Access Barring is 2.";
        value 2;
      }
      enum PRIORITY3 {
        description "Priority level for Progressive Access Barring is 3.";
        value 3;
      }
      enum PRIORITY4 {
        description "Priority level for Progressive Access Barring is 4.";
        value 4;
      }
    }
  }
  typedef enum-PeerStatus {
    type enumeration {
      enum UNKNOWN {
        description "Peer status is unknown.";
        value 0;
      }
      enum REACHABLE {
        description "Peer reachable, responds to GTP-U echo requests.";
        value 1;
      }
      enum UNREACHABLE {
        description "Peer unreachable, does not respond to GTP-U echo requests.";
        value 2;
      }
    }
  }
  typedef enum-Dl256QamSupport {
    type enumeration {
      enum NOT_SUPPORTED {
        description "256 QAM in DL cannot be supported in the cell.";
        value 0;
      }
      enum DEGRADED {
        description "256 QAM in DL can be supported in the cell, but the 256 QAM peak rate may not be achievable.";
        status deprecated {
          yexte:status-information "Since L17A. Planned to be removed.";
        }
        value 1;
      }
      enum SUPPORTED {
        description "256 QAM in DL can be supported in the cell.";
        value 2;
      }
    }
  }
  typedef enum-LastModificationGeran {
    type enumeration {
      enum ANR_MODIFICATION {
        description "ANR has modified the object. ";
        value 0;
      }
      enum OPERATOR_MODIFICATION {
        description "Operator has modified the object.";
        value 1;
      }
      enum NOT_MODIFIED {
        description "Object has not been modified since creation of object.";
        value 2;
      }
      enum ANR_DELETE {
        description "ANR has deleted the object. ";
        value 3;
      }
      enum OPERATOR_DELETE {
        description "Operator has deleted the object. ";
        value 4;
      }
    }
  }
  typedef enum-NetworkSignallingValue {
    type enumeration {
      enum NS_01 {
        description "Network Signalling value NS_01 according to TS 36.101, Table 6.2.4-1. This literal value corresponds to no additional spectrum emission requirements.";
        value 1;
      }
      enum NS_03 {
        description "Network Signalling value NS_03 according to TS 36.101, Table 6.2.4-1. This literal value corresponds to additional spectrum emission requirements on E-UTRA bands 2, 4, 10, 35 and 36 with channel bandwidths 3, 5, 10, 15 and 20 MHz.\n";
        value 3;
      }
      enum NS_04 {
        description "Network Signalling value NS_04 according to TS 36.101, Table 6.2.4-1.\n";
        value 4;
      }
      enum NS_05 {
        description "Network Signalling value NS_05 according to TS 36.101, Table 6.2.4-1. This literal value corresponds to additional spectrum emission requirements on E-UTRA band 1 with channel bandwidths 10, 15 and 20 MHz.\n";
        value 5;
      }
      enum NS_06 {
        description "Network Signalling value NS_06 according to TS 36.101, Table 6.2.4-1. ";
        value 6;
      }
      enum NS_07 {
        description "Network Signalling value NS_07 according to TS 36.101, Table 6.2.4-1. This literal value corresponds to additional spectrum emission requirements on E-UTRA band 13 with channel bandwidth 10 MHz.";
        value 7;
      }
      enum NS_08 {
        description "Network Signalling value NS_08 according to TS 36.101, Table 6.2.4-1. ";
        value 8;
      }
      enum NS_09 {
        description "Network Signalling value NS_09 according to TS 36.101, Table 6.2.4-1. ";
        value 9;
      }
      enum NS_10 {
        description "Network Signalling value NS_10 according to TS 36.101, Table 6.2.4-1. ";
        value 10;
      }
      enum NS_11 {
        description "Network Signalling value NS_11 according to TS 36.101, Table 6.2.4-1. ";
        value 11;
      }
      enum NS_12 {
        description "Network Signalling value NS_12 according to TS 36.101, Table 6.2.4-1. ";
        value 12;
      }
      enum NS_13 {
        description "Network Signalling value NS_13 according to TS 36.101, Table 6.2.4-1. ";
        value 13;
      }
      enum NS_14 {
        description "Network Signalling value NS_14 according to TS 36.101, Table 6.2.4-1. ";
        value 14;
      }
      enum NS_15 {
        description "Network Signalling value NS_15 according to TS 36.101, Table 6.2.4-1. ";
        value 15;
      }
      enum NS_16 {
        description "Network Signalling value NS_16 according to TS 36.101, Table 6.2.4-1. ";
        value 16;
      }
      enum NS_17 {
        description "Network Signalling value NS_17 according to TS 36.101, Table 6.2.4-1. ";
        value 17;
      }
      enum NS_18 {
        description "Network Signalling value NS_18 according to TS 36.101, Table 6.2.4-1. ";
        value 18;
      }
      enum NS_19 {
        description "Network Signalling value NS_19 according to TS 36.101, Table 6.2.4-1. ";
        value 19;
      }
      enum NS_20 {
        description "Network Signalling value NS_20 according to TS 36.101, Table 6.2.4-1. ";
        value 20;
      }
      enum NS_21 {
        description "Network Signalling value NS_21 according to TS 36.101, Table 6.2.4-1. ";
        value 21;
      }
      enum NS_22 {
        description "Network Signalling value NS_22 according to TS 36.101, Table 6.2.4-1. ";
        value 22;
      }
      enum NS_23 {
        description "Network Signalling value NS_23 according to TS 36.101, Table 6.2.4-1. ";
        value 23;
      }
      enum NS_24 {
        description "Network Signalling value NS_24 according to TS 36.101, Table 6.2.4-1. ";
        value 24;
      }
      enum NS_25 {
        description "Network Signalling value NS_25 according to TS 36.101, Table 6.2.4-1. ";
        value 25;
      }
      enum NS_26 {
        description "Network Signalling value NS_26 according to TS 36.101, Table 6.2.4-1. ";
        value 26;
      }
      enum NS_27 {
        description "Network Signalling value NS_27 according to TS 36.101, Table 6.2.4-1. ";
        value 27;
      }
      enum NS_28 {
        description "Network Signalling value NS_28 according to TS 36.101, Table 6.2.4-1. ";
        value 28;
      }
      enum NS_29 {
        description "Network Signalling value NS_29 according to TS 36.101, Table 6.2.4-1. ";
        value 29;
      }
      enum NS_30 {
        description "Network Signalling value NS_30 according to TS 36.101, Table 6.2.4-1. ";
        value 30;
      }
      enum NS_31 {
        description "Network Signalling value NS_31 according to TS 36.101, Table 6.2.4-1. ";
        value 31;
      }
      enum NS_32 {
        description "Network Signalling value NS_32 according to TS 36.101, Table 6.2.4-1. ";
        value 32;
      }
      enum NS_35 {
        description "Network Signalling value NS_35 according to TS 36.101, Table 6.2.4-1.";
        value 35;
      }
    }
  }
  typedef enum-NnsfModeVals {
    type enumeration {
      enum SPLMN {
        description "The function distributes all UEs which are not registered in any of the tracking areas of the cell (tries to reconnect if UE provides S-TMSI, thus registered in one of the tracking areas of the cell).";
        value 0;
      }
      enum RPLMN_IF_SAME_AS_SPLMN {
        description "The function distributes all UEs which are not registered in the PLMN they select (tries to reconnect if UE provides S-TMSI or if otherwise registered in the PLMN that it selects).";
        value 1;
      }
      enum RPLMN_IF_MME_SERVES_SPLMN {
        description "The function distributes all UEs which are registered in some PLMN which is not served by any MME which is connected to eNB (tries to reconnect if UE provides S-TMSI or is otherwise registered in an MME which serves the PLMN that it selects).";
        value 2;
      }
    }
  }
  typedef enum-Cdma2000SysTimeVals {
    type enumeration {
      enum NONE {
        value 0;
      }
      enum SYNCHRONOUS {
        value 1;
      }
      enum ASYNCHRONOUS {
        value 2;
      }
    }
  }
  typedef enum-DataModSchemes {
    type enumeration {
      enum QPSK_MOD_SCH {
        description "Quadrature Phase Shift Keying Modulation Scheme";
        value 0;
      }
      enum QAM_16_MOD_SCH {
        description "16 Quadrature Amplitude Modulation Scheme";
        value 1;
      }
      enum QAM_64_MOD_SCH {
        description "64 Quadrature Amplitude Modulation Scheme";
        value 2;
      }
    }
  }
  typedef enum-PciConflict {
    type enumeration {
      enum NO {
        description "A Cell was conflicting with another Cell but this has now been resolved.";
        value 0;
      }
      enum NO_CONFLICTING_CELL {
        description "A Cell was conflicting with another Cell but this has now been resolved.";
        value 1;
      }
      enum YES {
        description "A Cell conflicting with another Cell, this cell is defined in pciConflictCell.";
        value 2;
      }
      enum YES_CONFLICTING_CELL {
        description "A Cell conflicting with another Cell, this cell is defined in pciConflictCell.";
        value 3;
      }
    }
  }
  typedef enum-NBValueBr {
    type enumeration {
      enum NOT_PRESENT {
        description "Indicates that nbValueBr is not present.";
        value 0;
      }
      enum T1_64 {
        description "1/64 of defaultPagingCycle (T) is used.";
        value 1;
      }
      enum T1_128 {
        description "1/128 of defaultPagingCycle (T) is used.";
        value 2;
      }
      enum T1_256 {
        description "1/256 of defaultPagingCycle (T) is used.";
        value 3;
      }
      enum T {
        description "Undefined value.";
        value 4;
      }
      enum T1_2T {
        description "Undefined value.";
        value 5;
      }
      enum T1_4T {
        description "Undefined value.";
        value 6;
      }
      enum T1_8T {
        description "1/8 of defaultPagingCycle (T) is used.";
        value 7;
      }
      enum T1_16T {
        description "1/16 of defaultPagingCycle (T) is used.";
        value 8;
      }
      enum T1_32T {
        description "1/32 of defaultPagingCycle (T) is used.";
        value 9;
      }
    }
  }
  typedef enum-DlCalibrationStatus {
    type enumeration {
      enum INACTIVE {
        description "Downlink antenna calibration is not activated.";
        value 0;
      }
      enum CONVERGING {
        description "Downlink antenna calibration is converging.";
        value 1;
      }
      enum CALIBRATED {
        description "Downlink antenna calibration is finished with success.";
        value 2;
      }
      enum FAILED {
        description "Downlink antenna calibration has failed.";
        value 3;
      }
    }
  }
  typedef enum-CsiRsConfigType8TxTDD {
    type enumeration {
      enum NZP_CSIRS {
        description "A set of NZP (Non-Zero-Power) CSI-RS (Channel State Information Reference Signal)  configurations.";
        value 0;
      }
      enum NZP_ZP_CSIRS {
        description "A set of NZP (Non-Zero-Power) and ZP (Zero-Power) CSI-RS (Channel State Information Reference Signal) configurations. ZP CSI-RS reduces interference to the CSI-RS of neighboring cell. ";
        value 1;
      }
      enum NZP_CSIRS_TDD {
        description "A set of NZP (Non-Zero-Power) CSI-RS (Channel State Information Reference Signal) configurations to avoid collision with port 5. ";
        value 2;
      }
      enum NZP_ZP_CSIRS_TDD {
        description "A set of non-zero-power (NZP) and ZP (Zero-Power) CSI-RS (Channel State Information Reference Signal) configurations to avoid collision with port 5. ZP CSI-RS reduces interference to the CSI-RS of neighboring cell.";
        value 3;
      }
    }
  }
  typedef enum-DynamicCellStatusOutput {
    type enumeration {
      enum UNFORMATTED_TEXT {
        description "Output will be unformatted text, suitable for on-screen reading.";
        value 0;
      }
      enum FORMATTED_TEXT {
        description "Output will be formatted text, suitable for automated interpretation.";
        value 1;
      }
    }
  }
  typedef enum-UtranLbBnrPolicyVals {
    type enumeration {
      enum NOT_ALLOWED {
        value 0;
      }
      enum OFFLOAD_ONLY {
        value 3;
      }
    }
  }
  typedef enum-DlCalibrationMethod {
    type enumeration {
      enum NONE {
        description "No antenna calibration method.";
        value 0;
      }
      enum INTERNAL {
        description "Internal antenna calibration method.";
        value 1;
      }
    }
  }
  typedef enum-PreschedulingMode {
    type enumeration {
      enum NO_OVERRIDE {
        description "No override on Prescheduling configuration for the subscriber group.";
        value 0;
      }
      enum DISABLE_PRESCHEDULING {
        description "Unconditionally disable Prescheduling for the subscriber group.";
        value 1;
      }
      enum USE_SPECIFIC_PRESCHEDULING {
        description "Specific Prescheduling profile indicated by preschedProfileRef, which is used for the subscriber group.";
        value 2;
      }
    }
  }
  typedef enum-InterENodeBCAInteractionMode {
    type enumeration {
      enum NONE {
        description "No CA to be used together with the external eNodeB.";
        value 0;
      }
      enum ERAN {
        description "eRAN to be used for CA together with the external eNodeB.";
        value 1;
      }
      enum IENBCA {
        description "IeNB CA to be used for CA together with the external eNodeB.";
        value 2;
      }
    }
  }
  typedef enum-PtmCellType {
    description "PTM-related cell type.";
    type enumeration {
      enum PRIORITY {
        description "Enables IFO, ATO, Cell Reserved For Operator Use related actions, and sending Traffic Load States to neighboring cells.";
        value 0;
      }
      enum NON_PRIORITY {
        description "Enables evaluation of Traffic Load States and related IFLB, STM actions.";
        value 1;
      }
    }
  }
  typedef enum-LayerState {
    type enumeration {
      enum OFF {
        description "Layer State off.";
        value 0;
      }
      enum ON {
        description "Layer State on.";
        value 1;
      }
    }
  }
  typedef enum-ThpFilterDlVolume {
    type enumeration {
      enum FILTER_THRESH_0 {
        description "No Filter";
        status deprecated {
          yexte:status-information "Since 18.Q3. Has no functional behavior. Planned to be removed.";
        }
        value 0;
      }
      enum FILTER_THRESH_1 {
        description "Filter threshold is 1 bit for each burst.";
        status deprecated {
          yexte:status-information "Since 18.Q3. Has no functional behavior. Planned to be removed.";
        }
        value 1;
      }
      enum FILTER_THRESH_10 {
        description "Filter threshold is 10 bits for each burst.";
        status deprecated {
          yexte:status-information "Since 18.Q3. Has no functional behavior. Planned to be removed.";
        }
        value 2;
      }
      enum FILTER_THRESH_15 {
        description "Filter threshold is 15 bits for each burst.";
        status deprecated {
          yexte:status-information "Since 18.Q3. Has no functional behavior. Planned to be removed.";
        }
        value 3;
      }
      enum FILTER_THRESH_22 {
        description "Filter threshold is 22 bits for each burst.";
        status deprecated {
          yexte:status-information "Since 18.Q3. Has no functional behavior. Planned to be removed.";
        }
        value 4;
      }
      enum FILTER_THRESH_45 {
        description "Filter threshold is 45 bits for each burst.";
        status deprecated {
          yexte:status-information "Since 18.Q3. Has no functional behavior. Planned to be removed.";
        }
        value 5;
      }
      enum FILTER_THRESH_70 {
        description "Filter threshold is 70 bits for each burst.";
        status deprecated {
          yexte:status-information "Since 18.Q3. Has no functional behavior. Planned to be removed.";
        }
        value 6;
      }
      enum FILTER_THRESH_100 {
        description "Filter threshold is 100 bits for each burst.";
        status deprecated {
          yexte:status-information "Since 18.Q3. Has no functional behavior. Planned to be removed.";
        }
        value 7;
      }
      enum FILTER_THRESH_150 {
        description "Filter threshold is 150 bits for each burst.";
        status deprecated {
          yexte:status-information "Since 18.Q3. Has no functional behavior. Planned to be removed.";
        }
        value 8;
      }
      enum FILTER_THRESH_220 {
        description "Filter threshold is 220 bits for each burst.";
        status deprecated {
          yexte:status-information "Since 18.Q3. Has no functional behavior. Planned to be removed.";
        }
        value 9;
      }
      enum FILTER_THRESH_450 {
        description "Filter threshold is 450 bits for each burst.";
        status deprecated {
          yexte:status-information "Since 18.Q3. Has no functional behavior. Planned to be removed.";
        }
        value 10;
      }
      enum FILTER_THRESH_700 {
        description "Filter threshold is 700 bits for each burst.";
        status deprecated {
          yexte:status-information "Since 18.Q3. Has no functional behavior. Planned to be removed.";
        }
        value 11;
      }
      enum FILTER_THRESH_1000 {
        description "Filter threshold is 1000 bits for each burst.";
        status deprecated {
          yexte:status-information "Since 18.Q3. Has no functional behavior. Planned to be removed.";
        }
        value 12;
      }
      enum FILTER_THRESH_1500 {
        description "Filter threshold is 1500 bits for each burst.";
        status deprecated {
          yexte:status-information "Since 18.Q3. Has no functional behavior. Planned to be removed.";
        }
        value 13;
      }
      enum FILTER_THRESH_2200 {
        description "Filter threshold is 2200 bits for each burst.";
        status deprecated {
          yexte:status-information "Since 18.Q3. Has no functional behavior. Planned to be removed.";
        }
        value 14;
      }
      enum FILTER_THRESH_4500 {
        description "Filter threshold is 4500 bits for each burst.";
        status deprecated {
          yexte:status-information "Since 18.Q3. Has no functional behavior. Planned to be removed.";
        }
        value 15;
      }
      enum FILTER_THRESH_7000 {
        description "Filter threshold is 7000 bits for each burst.";
        status deprecated {
          yexte:status-information "Since 18.Q3. Has no functional behavior. Planned to be removed.";
        }
        value 16;
      }
      enum FILTER_THRESH_10000 {
        description "Filter threshold is 10000 bits for each burst.";
        status deprecated {
          yexte:status-information "Since 18.Q3. Has no functional behavior. Planned to be removed.";
        }
        value 17;
      }
      enum FILTER_THRESH_15000 {
        description "Filter threshold is 15000 bits for each burst.";
        status deprecated {
          yexte:status-information "Since 18.Q3. Has no functional behavior. Planned to be removed.";
        }
        value 18;
      }
      enum FILTER_THRESH_22000 {
        description "Filter threshold is 22000 bits for each burst.";
        status deprecated {
          yexte:status-information "Since 18.Q3. Has no functional behavior. Planned to be removed.";
        }
        value 19;
      }
      enum FILTER_THRESH_45000 {
        description "Filter threshold is 45000 bits for each burst.";
        status deprecated {
          yexte:status-information "Since 18.Q3. Has no functional behavior. Planned to be removed.";
        }
        value 20;
      }
      enum FILTER_THRESH_70000 {
        description "Filter threshold is 70000 bits for each burst.";
        status deprecated {
          yexte:status-information "Since 18.Q3. Has no functional behavior. Planned to be removed.";
        }
        value 21;
      }
      enum FILTER_THRESH_100000 {
        description "Filter threshold is 100000 bits for each burst.";
        status deprecated {
          yexte:status-information "Since 18.Q3. Has no functional behavior. Planned to be removed.";
        }
        value 22;
      }
      enum FILTER_THRESH_150000 {
        description "Filter threshold is 150000 bits for each burst.";
        status deprecated {
          yexte:status-information "Since 18.Q3. Has no functional behavior. Planned to be removed.";
        }
        value 23;
      }
      enum FILTER_THRESH_220000 {
        description "Filter threshold is 220000 bits for each burst.";
        status deprecated {
          yexte:status-information "Since 18.Q3. Has no functional behavior. Planned to be removed.";
        }
        value 24;
      }
      enum FILTER_THRESH_450000 {
        description "Filter threshold is 450000 bits for each burst.";
        status deprecated {
          yexte:status-information "Since 18.Q3. Has no functional behavior. Planned to be removed.";
        }
        value 25;
      }
    }
  }
  typedef enum-TtiBundlingModeAfterHandover {
    type enumeration {
      enum NO_TTI_BUNDLING {
        description "Not remain in TTI bundling mode after UE handover.";
        value 0;
      }
      enum TTI_BUNDLING_ALL_HO_CASES {
        description "Remain in TTI bundling mode for all handover cases.";
        value 1;
      }
      enum TTI_BUNDLING_INTRA_FREQ_HO_ONLY {
        description "Remain in TTI bundling mode only for intra-frequency handover case.";
        value 2;
      }
    }
  }
  typedef enum-NBValue {
    type enumeration {
      enum T4 {
        value 0;
      }
      enum T2 {
        value 1;
      }
      enum T {
        value 2;
      }
      enum T1_2 {
        value 3;
      }
      enum T1_4 {
        value 4;
      }
      enum T1_8 {
        value 5;
      }
      enum T1_16 {
        value 6;
      }
      enum T1_32 {
        value 7;
      }
    }
  }
  typedef enum-MeasSelectionEUtra {
    type enumeration {
      enum PERIODICAL {
        description "Periodical reporting.";
        value 0;
      }
      enum EVENT_A1 {
        description "Serving becomes better than absolute threshold.";
        value 1;
      }
      enum EVENT_A2 {
        description "Serving becomes worse than absolute threshold.";
        value 2;
      }
      enum EVENT_A3 {
        description "Neighbor becomes amount of offset better than serving.";
        value 3;
      }
      enum EVENT_A4 {
        description "Neighbor becomes better than absolute threshold.";
        value 4;
      }
      enum EVENT_A5 {
        description "Serving becomes worse than absolute threshold1 AND Neighbor becomes better than another absolute threshold2.";
        value 5;
      }
      enum EVENT_A6 {
        description "Neighbor becomes amount of offset better than SCell.";
        value 6;
      }
    }
  }
  typedef enum-PersistentStorage {
    type enumeration {
      enum OFF {
        description "Persistent storage of PWS data is turned OFF.";
        value 0;
      }
      enum ON {
        description "Persistent storage of PWS data is turned ON.";
        value 1;
      }
    }
  }
  typedef enum-NetworkSignallingValueCa {
    type enumeration {
      enum CA_NS_01 {
        description "CA Network Signalling value CA_NS_01 according to TS 36.101, Table 6.2.4A-1. This literal value corresponds to additional spectrum emission requirements for intra-band contiguous aggregation on E-UTRA band 1. ";
        value 1;
      }
      enum CA_NS_02 {
        description "CA Network Signalling value CA_NS_02 according to TS 36.101, Table 6.2.4A-1. This literal value corresponds to additional spectrum emission requirements for intra-band contiguous aggregation on E-UTRA band 1.";
        value 2;
      }
      enum CA_NS_03 {
        description "CA Network Signalling value CA_NS_03 according to TS 36.101, Table 6.2.4A-1. This literal value corresponds to additional spectrum emission requirements for intra-band contiguous aggregation on E-UTRA band 1.";
        value 3;
      }
      enum CA_NS_04 {
        description "CA Network Signalling value CA_NS_04 according to TS 36.101, Table 6.2.4A-1. This literal value corresponds to additional spectrum emission requirements for intra-band contiguous aggregation on E-UTRA band 41.";
        value 4;
      }
      enum CA_NS_05 {
        description "CA Network Signalling value CA_NS_05 according to TS 36.101, Table 6.2.4A-1. This literal value corresponds to additional spectrum emission requirements for intra-band contiguous aggregation on E-UTRA band 38.";
        value 5;
      }
      enum CA_NS_06 {
        description "CA Network Signalling value CA_NS_06 according to TS 36.101, Table 6.2.4A-1. This literal value corresponds to additional spectrum emission requirements for intra-band contiguous aggregation on E-UTRA band 7.";
        value 6;
      }
      enum CA_NS_07 {
        description "CA Network Signalling value CA_ NS_07 according to TS 36.101, Table 6.2.4A-1. This literal value corresponds to additional spectrum emission requirements for intra-band contiguous aggregation on E-UTRA band 39. ";
        value 7;
      }
      enum CA_NS_08 {
        description "CA Network Signalling value CA_NS_08 according to TS 36.101, Table 6.2.4A-1. This literal value corresponds to additional spectrum emission requirements for intra-band contiguous aggregation on E-UTRA band 42.";
        value 8;
      }
      enum CA_NS_31 {
        description "CA Network Signalling value CA_NS_31 according to TS 36.101, Table 6.2.4A-1. This literal value corresponds to no additional spectrum emission requirements.";
        value 31;
      }
    }
  }
  typedef enum-AnchorPowerBoostIndex {
    type enumeration {
      enum ANCHOR_POWER_RATIO_1_1 {
        description "Anchor carrier power is linear 1 times of average PRB power. Power ratio corresponds to 0dB.";
        value 0;
      }
      enum ANCHOR_POWER_RATIO_2_1 {
        description "Anchor carrier power is linear 2 times of average PRB power. Power ratio corresponds to 3 dB.";
        value 1;
      }
      enum ANCHOR_POWER_RATIO_3_1 {
        description "Anchor carrier power is linear 3 times of average PRB power. Power ratio corresponds to 4,77dB.";
        value 2;
      }
      enum ANCHOR_POWER_RATIO_4_1 {
        description "Anchor carrier power is linear 4 times of average PRB power. Power ratio corresponds to 6 dB.";
        value 3;
      }
    }
  }
  typedef enum-ValidityTime {
    type enumeration {
      enum VALIDITY_TIME_3H {
        description "Indicates system information validity timer is set to 3h";
        value 0;
      }
      enum VALIDITY_TIME_24H {
        description "Indicates system information validity timer is set to 24h";
        value 1;
      }
    }
  }
  typedef enum-CustomTriggerType {
    type enumeration {
      enum TRIGGER_NOT_USED {
        description "Trigger is not used for subscriber selection at all.";
        value 0;
      }
      enum TRIGGER_TYPE_1 {
        description "Trigger type.";
        value 1;
      }
      enum TRIGGER_TYPE_2 {
        description "Trigger type.";
        value 2;
      }
      enum TRIGGER_TYPE_3 {
        description "Trigger type.";
        value 3;
      }
      enum TRIGGER_TYPE_4 {
        description "Trigger type.";
        value 4;
      }
      enum TRIGGER_TYPE_5 {
        description "Trigger type.";
        value 5;
      }
      enum TRIGGER_TYPE_6 {
        description "Trigger type.";
        value 6;
      }
      enum TRIGGER_TYPE_7 {
        description "Trigger type.";
        value 7;
      }
      enum TRIGGER_TYPE_8 {
        description "Trigger type.";
        value 8;
      }
      enum TRIGGER_TYPE_9 {
        description "Trigger type.";
        value 9;
      }
      enum TRIGGER_TYPE_10 {
        description "Trigger type.";
        value 10;
      }
    }
  }
  typedef enum-DnsLookup {
    type enumeration {
      enum OFF {
        value 0;
      }
      enum ON {
        value 1;
      }
    }
  }
  typedef enum-AdvCellSupActions {
    type enumeration {
      enum NO_ACTION {
        description "No recovery action is allowed";
        value 0;
      }
      enum CELL_RESTART {
        description "Cell restart action is allowed";
        value 1;
      }
      enum CELL_AND_NODE_RESTART {
        description "Cell restart and Node restart actions are allowed.";
        value 2;
      }
    }
  }
  typedef enum-LicCapDistrMethod {
    type enumeration {
      enum SYSTEM {
        description "The RBS will distribute the licensed capacity evenly over the baseband processing resources.";
        value 0;
      }
      enum OPERATOR {
        description "The RBS will distribute the licensed capacity over the baseband processing resources based on the value set in licCapDistr.";
        value 1;
      }
    }
  }
  typedef enum-DrxRetransmissionTimer {
    description "Timer for DRX in TS 36.321 [6]. Value in number of PDCCH sub-frames. Value PSF1 corresponds to 1 PDCCH sub-frame, PSF2 corresponds to 2 PDCCH sub-frames and so on.";
    type enumeration {
      enum PSF1 {
        description "1 PDCCH sub frame.";
        value 0;
      }
      enum PSF2 {
        description "2 PDCCH sub frames.";
        value 1;
      }
      enum PSF4 {
        description "4 PDCCH sub frames.";
        value 2;
      }
      enum PSF6 {
        description "6 PDCCH sub frames.";
        value 3;
      }
      enum PSF8 {
        description "8 PDCCH sub frames.";
        value 4;
      }
      enum PSF16 {
        description "16 PDCCH sub frames.";
        value 5;
      }
      enum PSF24 {
        description "24 PDCCH sub frames.";
        value 6;
      }
      enum PSF33 {
        description "33 PDCCH sub frames.";
        value 7;
      }
    }
  }
  typedef enum-MimoSleepStatus {
    type enumeration {
      enum OFF {
        description "MIMO Sleep Mode function is disabled.";
        value 0;
      }
      enum DETECTION {
        description "MIMO Sleep Mode function is enabled in detection-only mode.";
        value 1;
      }
      enum SOFT_SWITCH {
        description "MIMO Sleep Mode function is enabled to perform detection and soft switching. Soft switching performs a cell shutdown before it locks the cell for reconfiguration.";
        value 2;
      }
      enum SWITCH {
        description "MIMO Sleep Mode function is enabled to perform detection and switching. The cell is immediately locked to perform cell reconfiguration.";
        value 3;
      }
      enum ADVANCED_SWITCH {
        description "MIMO Sleep Mode function is enabled to perform detection and switching. The cell deactivates antennas without cell reconfiguration.";
        value 4;
      }
    }
  }
  typedef enum-MobilityActionUtran {
    type enumeration {
      enum RELEASE_WITH_REDIRECT {
        description "Release with Redirect.";
        value 0;
      }
      enum RELEASE_WITH_REDIRECT_NACC {
        description "Release with Redirect including Network Assisted Cell Change (NACC) information.";
        value 1;
      }
      enum HANDOVER {
        description Handover;
        value 2;
      }
    }
  }
  typedef enum-ServOrPrioTriggeredErabActionType {
    type enumeration {
      enum SETUP_ALWAYS {
        description "Setup the bearer when no valid target frequencies exist.";
        status deprecated {
          yexte:status-information "Since L16A. Replaced by enum value SETUP. Planned to be removed.";
        }
        value 0;
      }
      enum SETUP_TEMPORARY {
        description "Do not setup the bearer when no valid target frequencies exist.";
        status deprecated {
          yexte:status-information "Since L16A. Replaced by enum value REJECT. Planned to be removed.";
        }
        value 1;
      }
      enum SETUP {
        description "Setup the bearer when no valid target frequencies exist.";
        value 2;
      }
      enum REJECT {
        description "Do not setup the bearer when no valid target frequencies exist.";
        value 3;
      }
    }
  }
  typedef enum-DcnType {
    type enumeration {
      enum DEFAULT {
        description "Default dedicated core network. During NAS node selection, eNodeB selects an MME that belongs to default dedicated core network.";
        value 0;
      }
      enum SPECIFIC {
        description "Specific dedicated core network. During NAS node selection, eNodeB does not select an MME that belongs to specific dedicated core network.";
        value 1;
      }
    }
  }
  typedef enum-AdmState {
    description "Administrative state of a resource.";
    type enumeration {
      enum LOCKED {
        description "The resource is administratively prohibited from performing services for its users.";
        value 0;
      }
      enum UNLOCKED {
        description "The resource is administratively permitted to perform services for its users.\nThis is independent of its inherent operability.";
        value 1;
      }
      enum SHUTTINGDOWN {
        description "Use of the resource is administratively permitted to existing instances of use only.\nWhile the system remains in the shutting down state the manager may at any time cause the managed object to revert to the locked state.";
        value 2;
      }
    }
  }
  typedef enum-HoNotAllowedMpLoadLevel {
    type enumeration {
      enum NOT_HIGH_LOAD {
        description "Release inactive UEs at handover when MP load level is at least NOT_HIGH.";
        value 0;
      }
      enum HIGH_LOAD {
        description "Release inactive UEs at handover when MP load level is at least HIGH.";
        value 1;
      }
      enum VERY_HIGH_LOAD {
        description "Release inactive UEs at handover when MP load level is at least VERY_HIGH.";
        value 2;
      }
    }
  }
  typedef enum-DrxInactivityTimer {
    description "Timer for DRX in TS 36.321 [6]. Value in number of PDCCH sub-frames. Value PSF1 corresponds to 1 PDCCH sub-frame, PSF2 corresponds to 2 PDCCH sub-frames and so on.";
    type enumeration {
      enum PSF1 {
        description "Number of PDCCH sub frames";
        value 0;
      }
      enum PSF2 {
        description "Number of PDCCH sub frames";
        value 1;
      }
      enum PSF3 {
        description "Number of PDCCH sub frames";
        value 2;
      }
      enum PSF4 {
        description "Number of PDCCH sub frames";
        value 3;
      }
      enum PSF5 {
        description "Number of PDCCH sub frames";
        value 4;
      }
      enum PSF6 {
        description "Number of PDCCH sub frames";
        value 5;
      }
      enum PSF8 {
        description "Number of PDCCH sub frames";
        value 6;
      }
      enum PSF10 {
        description "Number of PDCCH sub frames";
        value 7;
      }
      enum PSF20 {
        description "Number of PDCCH sub frames";
        value 8;
      }
      enum PSF30 {
        description "Number of PDCCH sub frames";
        value 9;
      }
      enum PSF40 {
        description "Number of PDCCH sub frames";
        value 10;
      }
      enum PSF50 {
        description "Number of PDCCH sub frames";
        value 11;
      }
      enum PSF60 {
        description "Number of PDCCH sub frames";
        value 12;
      }
      enum PSF80 {
        description "Number of PDCCH sub frames";
        value 13;
      }
      enum PSF100 {
        description "Number of PDCCH sub frames";
        value 14;
      }
      enum PSF200 {
        description "Number of PDCCH sub frames";
        value 15;
      }
      enum PSF300 {
        description "Number of PDCCH sub frames";
        value 16;
      }
      enum PSF500 {
        description "Number of PDCCH sub frames";
        value 17;
      }
      enum PSF750 {
        description "Number of PDCCH sub frames";
        value 18;
      }
      enum PSF1280 {
        description "Number of PDCCH sub frames";
        value 19;
      }
      enum PSF1920 {
        description "Number of PDCCH sub frames";
        value 20;
      }
      enum PSF2560 {
        description "Number of PDCCH sub frames";
        value 21;
      }
      enum PSF0 {
        description "Number of PDCCH sub frames";
        value 22;
      }
    }
  }
  typedef enum-SCellHandlingWithVolte {
    type enumeration {
      enum KEEP_SCELLS {
        description "No change of SCell handling.";
        value 0;
      }
      enum DECONF_SCELLS {
        description "Deconfigure SCells during VoLTE calls.";
        value 1;
      }
      enum DECONF_UL_SUPPRESS_DL_SCELLS {
        description "Deconfigure UL SCells, suppress DL SCell selection during VoLTE calls.";
        value 2;
      }
      enum DECONF_UL_SCELLS {
        description "Deconfigure UL SCells, do not change DL SCell handling during VoLTE calls.";
        value 3;
      }
    }
  }
  typedef enum-InterEnbSwCompatibilityState {
    type enumeration {
      enum UNKNOWN {
        description "Termination point resource inter-eNodeB capability is not known.";
        value 0;
      }
      enum COMPATIBLE {
        description "Termination point resource is compatible and can set up inter-eNodeB GTP-U tunnels.";
        value 1;
      }
      enum INCOMPATIBLE {
        description "Termination point resource is incompatible and unable to setup inter-eNodeB GTP-U tunnels.";
        value 2;
      }
    }
  }
  typedef enum-TtiBundlingModeAfterReestablishment {
    type enumeration {
      enum NO_TTI_BUNDLING {
        description "Not remain in TTI bundling mode after UE reestablishment.";
        value 0;
      }
      enum TTI_BUNDLING_ALL_REEST_CASES {
        description "Remain in TTI bundling mode for all reestablishment cases.";
        value 1;
      }
      enum TTI_BUNDLING_SOURCE_REEST_ONLY {
        description "Remain in TTI bundling mode only for source cell reestablishment case.";
        value 2;
      }
    }
  }
  typedef enum-Reason {
    type enumeration {
      enum NONE {
        description "The cell relation is not barred for mobility.";
        value 0;
      }
      enum PROBLEMATIC_CELL {
        description "The cell relation is barred for mobility.";
        value 1;
      }
      enum PLMN_NOT_SUPPORTED {
        description "Cell relation is barred for mobility. PLMN on target side is not supported.";
        value 2;
      }
    }
  }
  typedef enum-CauseCodeOffload {
    type enumeration {
      enum REDUCE_LOAD_IN_SERVING_CELL {
        description "Reduce Load in Serving Cell";
        value 0;
      }
      enum RESOURCE_OPTIMSATION_HANDOVER {
        description "Resource Optimisation Handover";
        value 1;
      }
      enum LOAD_BALANCING {
        description "Load Balancing";
        value 2;
      }
      enum TEMPORARY1 {
        description "Value for Future Use";
        value 98;
      }
      enum TEMPORARY2 {
        description "Value for Future Use";
        value 99;
      }
    }
  }
  typedef enum-GtpuEchoEnable {
    type enumeration {
      enum DISABLED {
        description "Monitoring is disabled.";
        value 0;
      }
      enum PERIODIC {
        description "Monitoring is enabled with a periodic interval.";
        value 1;
      }
    }
  }
  typedef enum-CovCellCandidate {
    type enumeration {
      enum NOT_ALLOWED {
        description "The cell indicated by the value of parameter cell relation must not be used as coverage cell for cell sleep mode support.";
        value 0;
      }
      enum ALLOWED {
        description "Value of parameter cell relation must be used as coverage cell for cell sleep mode support when coverage cell discovery function is not activated. The cell can be used as coverage cell, if selected by coverage cell discovery function when it is activated.";
        value 1;
      }
      enum AUTO {
        description "Value of parameter cell relation can be used as coverage cell for cell sleep mode support, if selected by function coverage cell discovery, in feature Cell Sleep Mode.";
        value 2;
      }
    }
  }
  typedef enum-MobilityActionCsfbGeran {
    type enumeration {
      enum RELEASE_WITH_REDIRECT {
        description "Release with Redirect.";
        value 0;
      }
      enum RELEASE_WITH_REDIRECT_NACC {
        description "Release with Redirect including Network Assisted Cell Change (NACC) information.";
        value 1;
      }
    }
  }
  typedef enum-EranExternalUlCompGroupAvail {
    type enumeration {
      enum DISABLED {
        description "Resource is inoperable.";
        value 0;
      }
      enum ENABLED {
        description "Resource is operable.";
        value 1;
      }
    }
  }
  typedef enum-RequestedBandCombCompression {
    type enumeration {
      enum OFF {
        description "No usage of any shortening of the UE band combinations.";
        value 0;
      }
      enum R11_REQUESTED_BAND_COMBO {
        description "Enable using requestedFrequencyBands-r11 IE when querying UE band combinations.";
        value 1;
      }
      enum R13_BAND_COMPRESSION {
        description "Enable using requestedFrequencyBands-r11 IE, requestReducedFormat-r13 IE, skipFallbackCombinations-r13 IE and requestReducedIntNonContComb-r13 IE when querying UE band combinations.";
        value 2;
      }
    }
  }
  typedef enum-IntegrityProtectionAlgorithmID {
    type enumeration {
      enum EIA1 {
        description "This refers to the algorithm 128-EIA1 (based on SNOW 3G)";
        value 1;
      }
      enum EIA2 {
        description "This refers to the algorithm 128-EIA2 (based on AES). ";
        value 2;
      }
      enum EIA3 {
        description "This refers to the algorithm 128-EIA3 (based on ZUC).";
        value 3;
      }
    }
  }
  typedef enum-GtpuEchoFailureAction {
    type enumeration {
      enum NONE {
        description "No action when S1 peer is unreachable.";
        value 0;
      }
      enum RESET {
        description "S1-AP reset action when S1 peer is unreachable.";
        value 1;
      }
    }
  }
  typedef enum-PreemptionVulnerability {
    type enumeration {
      enum NOT_PREEMPTABLE {
        description "E-RAB shall not be pre-empted by other E-RABs.";
        value 0;
      }
      enum PREEMPTABLE {
        description "E-RAB may be pre-empted by other RABs.";
        value 1;
      }
    }
  }
  typedef enum-RlcBufferStatus {
    type enumeration {
      enum HALF_BUFFER {
        description "The RLC buffer is at 50% of its capacity";
        value 0;
      }
      enum FULL_BUFFER {
        description "The RLC buffer is full";
        value 1;
      }
    }
  }
  typedef enum-PrioHpueCapability {
    type enumeration {
      enum NO_PRIORITIZATION {
        description "No prioritization. Preserve high power UE capability as long as possible but in case of special circumstances give precedence to other functionality and disregard the high power UE capability.";
        value 0;
      }
      enum PRIORITIZE_IN_CA {
        description "For high power UE that has limitations in terms of simultaneous high power and CA configuration, prioritize high power UE capability over CA UE capability.";
        value 1;
      }
    }
  }
  typedef enum-TriggerQuantityGUtra {
    description "Specify type of trigger quantity used to evaluate the triggering conditions.";
    type enumeration {
      enum SS_RSRP {
        description "NR synchronization signals reference signal received power.";
        value 0;
      }
      enum SS_RSRQ {
        description "NR synchronization signal reference signal received quality.";
        value 1;
      }
    }
  }
  typedef enum-CeLevel {
    type enumeration {
      enum CE_LEVEL_0 {
        description "CE Level 0";
        value 0;
      }
      enum CE_LEVEL_1 {
        description "CE Level 1";
        value 1;
      }
      enum CE_LEVEL_2 {
        description "CE Level 2";
        value 2;
      }
      enum CE_LEVEL_3 {
        description "CE Level 3";
        value 3;
      }
    }
  }
  typedef enum-AtoQciProfileHandling {
    type enumeration {
      enum ALLOWED {
        description "If a QCI profile is configured as ALLOWED then a UE may use it (but does not have to) in order to qualify for admission-triggered offload to the target frequency. ";
        value 0;
      }
      enum FORBIDDEN {
        description "If a QCI profile is configured as FORBIDDEN then UEs using it are not qualified for admission-triggered offload to the target frequency. ";
        value 1;
      }
    }
  }
  typedef enum-MeasGapShareScheme {
    type enumeration {
      enum SCHEME_ZERO {
        description "All frequencies, including intra-frequency have same opportunity.";
        value 0;
      }
      enum SCHEME_ONE {
        description "40% for intra-frequency and 60% for all inter-frequency.";
        value 1;
      }
      enum SCHEME_TWO {
        description "50% for intra-frequency and 50% for all inter-frequency.";
        value 2;
      }
      enum SCHEME_THREE {
        description "60% for intra-frequency and 40% for all inter-frequency.";
        value 3;
      }
    }
  }
  typedef enum-LiteMcsReductionMode {
    type enumeration {
      enum OFF {
        description "LiteMcsReduction function is disabled.";
        value 0;
      }
      enum ON {
        description "LiteMcsReduction function is enabled.";
        value 1;
      }
      enum ON_WHEN_NO_ELC {
        description "LiteMcsReduction function is enabled except when ELC feature is active.";
        value 2;
      }
    }
  }
  typedef enum-UlCalibrationStatus {
    type enumeration {
      enum INACTIVE {
        description "UL antenna calibration is not activated.";
        value 0;
      }
      enum CONVERGING {
        description "UL antenna calibration is converging.";
        value 1;
      }
      enum CALIBRATED {
        description "UL antenna calibration succeeded.";
        value 2;
      }
      enum FAILED {
        description "UL antenna calibration failed.";
        value 3;
      }
    }
  }
  typedef enum-TransmissionMode {
    type enumeration {
      enum TRANSMISSION_MODE_2 {
        description "Transmit diversity";
        value 2;
      }
      enum TRANSMISSION_MODE_3 {
        description "Transmit Diversity and Large delay CDD (depending on rank), also called Open-Loop Spatial Multiplexing";
        value 3;
      }
      enum TRANSMISSION_MODE_4 {
        description "Closed-Loop Spatial Multiplexing";
        value 4;
      }
      enum TRANSMISSION_MODE_7 {
        description "Single-Layer Beamforming with UE specific reference signal on Antenna Port 5.";
        value 7;
      }
      enum TRANSMISSION_MODE_8 {
        description "Dual-Layer Beamforming with UE specific reference signals on Antenna Port 7 and 8.";
        value 8;
      }
      enum TRANSMISSION_MODE_9 {
        description "Multiple-Layer Beamforming with UE specific reference signals on Antenna Port 7 and 8.";
        value 9;
      }
    }
  }
  typedef enum-CipheringAlgorithmID {
    type enumeration {
      enum EEA0 {
        description "EEA0 means that no ciphering is applied. ";
        value 0;
      }
      enum EEA1 {
        description "This refers to the ciphering algorithm 128-EEA1 (based on SNOW 3G).";
        value 1;
      }
      enum EEA2 {
        description "This refers to the ciphering algorithm 128-EEA2 (based on AES). ";
        value 2;
      }
      enum EEA3 {
        description "This refers to 128-EEA3 (based on ZUC).";
        value 3;
      }
    }
  }
  typedef enum-TimePhaseMaxDeviationTddIndex {
    type enumeration {
      enum TIME_PHASE_MAX_DEVIATION_TDD_IDX0 {
        description "Index of max allowed time and phase deviation for time and phase synchronization of TDD cell. It refers timePhaseMaxDeviationTdd in ENodeBFunction.";
        value 0;
      }
      enum TIME_PHASE_MAX_DEVIATION_TDD_IDX1 {
        description "Index of max allowed time and phase deviation for time and phase synchronization of TDD cell. It refers timePhaseMaxDeviationTdd1 in ENodeBFunction.";
        value 1;
      }
      enum TIME_PHASE_MAX_DEVIATION_TDD_IDX2 {
        description "Index of max allowed time and phase deviation for time and phase synchronization of TDD cell. It refers timePhaseMaxDeviationTdd2 in ENodeBFunction.";
        value 2;
      }
      enum TIME_PHASE_MAX_DEVIATION_TDD_IDX3 {
        description "Index of max allowed time and phase deviation for time and phase synchronization of TDD cell. It refers timePhaseMaxDeviationTdd3 in ENodeBFunction.";
        value 3;
      }
      enum TIME_PHASE_MAX_DEVIATION_TDD_IDX4 {
        description "Index of max allowed time and phase deviation for time and phase synchronization of TDD cell. It refers timePhaseMaxDeviationTdd4 in ENodeBFunction.";
        value 4;
      }
      enum TIME_PHASE_MAX_DEVIATION_TDD_IDX5 {
        description "Index of max allowed time and phase deviation for time and phase synchronization of TDD cell. It refers timePhaseMaxDeviationTdd5 in ENodeBFunction.";
        value 5;
      }
      enum TIME_PHASE_MAX_DEVIATION_TDD_IDX6 {
        description "Index of max allowed time and phase deviation for time and phase synchronization of TDD cell. It refers timePhaseMaxDeviationTdd6 in ENodeBFunction.";
        value 6;
      }
      enum TIME_PHASE_MAX_DEVIATION_TDD_IDX7 {
        description "Index of max allowed time and phase deviation for time and phase synchronization of TDD cell. It refers timePhaseMaxDeviationTdd7 in ENodeBFunction.";
        value 7;
      }
    }
  }
  typedef enum-MobilityActionEUtran {
    type enumeration {
      enum RELEASE_WITH_REDIRECT {
        value 0;
      }
      enum HANDOVER {
        value 1;
      }
    }
  }
  typedef enum-MobilityActionCsfbUtranTDD {
    type enumeration {
      enum RELEASE_WITH_REDIRECT {
        value 0;
      }
      enum RELEASE_WITH_REDIRECT_NACC {
        value 1;
      }
      enum HANDOVER {
        value 2;
      }
    }
  }
  typedef enum-ParameterChangeState {
    type enumeration {
      enum INITIAL {
        description "The structure is created, but has not yet got valid values.";
        value 0;
      }
      enum PENDING {
        description "The change request is pending decision from the operator.";
        value 1;
      }
      enum APPROVED {
        description "The change request is approved by the operator.";
        value 2;
      }
      enum REJECTED {
        description "The change request is rejected by the operator.";
        value 3;
      }
      enum CANCELLED {
        description "The change request is cancelled by the eNodeB.";
        value 4;
      }
    }
  }
  typedef enum-ResourceAllocationStrategy {
    type enumeration {
      enum RESOURCE_FAIR {
        description "Indicates that the resource allocation strategy is resource fair in frequency.";
        value 0;
      }
      enum FREQUENCY_SELECTIVE {
        description "Indicates that the resource allocation strategy is frequency selective.";
        value 1;
      }
    }
  }
  typedef enum-NbValueNbIot {
    type enumeration {
      enum T4 {
        description "4T. Used to calculate the number and position of NbIot Paging Occasions (PO) and NbIot Paging Frames (PF).";
        status deprecated {
          yexte:status-information "Since 17.Q2. Planned to be removed.";
        }
        value 0;
      }
      enum T2 {
        description "2T. Used to calculate the number and position of NbIot Paging Occasions (PO) and NbIot Paging Frames (PF).";
        status deprecated {
          yexte:status-information "Since 17.Q2. Planned to be removed.";
        }
        value 1;
      }
      enum T {
        description "T. Used to calculate the number and position of NbIot Paging Occasions (PO) and NbIot Paging Frames (PF).";
        value 2;
      }
      enum T1_2 {
        description "T/2. Used to calculate the number and position of NbIot Paging Occasions (PO) and NbIot Paging Frames (PF).";
        value 3;
      }
      enum T1_4 {
        description "T/4. Used to calculate the number and position of NbIot Paging Occasions (PO) and NbIot Paging Frames (PF).";
        value 4;
      }
      enum T1_8 {
        description "T/8. Used to calculate the number and position of NbIot Paging Occasions (PO) and NbIot Paging Frames (PF).";
        value 5;
      }
      enum T1_16 {
        description "T/16. Used to calculate the number and position of NbIot Paging Occasions (PO) and NbIot Paging Frames (PF).";
        value 6;
      }
      enum T1_32 {
        description "T/32. Used to calculate the number and position of NbIot Paging Occasions (PO) and NbIot Paging Frames (PF).";
        value 7;
      }
      enum T1_64 {
        description "T/64. Used to calculate the number and position of NbIot Paging Occasions (PO) and NbIot Paging Frames (PF).";
        value 8;
      }
      enum T1_128 {
        description "T/128. Used to calculate the number and position of NbIot Paging Occasions (PO) and NbIot Paging Frames (PF).";
        value 9;
      }
      enum T1_256 {
        description "T/256. Used to calculate the number and position of NbIot Paging Occasions (PO) and NbIot Paging Frames (PF).";
        value 10;
      }
      enum T1_512 {
        description "T/512. Used to calculate the number and position of NbIot Paging Occasions (PO) and NbIot Paging Frames (PF).";
        value 11;
      }
      enum T1_1024 {
        description "T/1024. Used to calculate the number and position of NbIot Paging Occasions (PO) and NbIot Paging Frames (PF).";
        value 12;
      }
    }
  }
  typedef enum-ActivationVals {
    description "Possible states set by operator for licensed feature.";
    type enumeration {
      enum ACTIVATED {
        description "Operator allows usage of the feature.";
        value 1;
      }
      enum DEACTIVATED {
        description "Operator does not allow usage of the feature.";
        value 0;
      }
    }
  }
  typedef enum-LbQciProfileHandling {
    type enumeration {
      enum ALLOWED {
        description "If a QCI profile is configured as ALLOWED then a UE may use it (but does not have to) in order to qualify for load balancing to the target frequency.";
        value 0;
      }
      enum FORBIDDEN {
        description "If a QCI profile is configured as FORBIDDEN then UEs using it are not qualified for load balancing to the target frequency.";
        value 1;
      }
      enum REQUIRED {
        description "If one or more QCI profiles are configured as REQUIRED then only UEs using one or more of them are qualified for load balancing to the target frequency.";
        value 2;
      }
    }
  }
  typedef enum-TriggerQuantity {
    type enumeration {
      enum RSRP {
        value 0;
      }
      enum RSRQ {
        value 1;
      }
    }
  }
  typedef enum-UeCategory {
    type enumeration {
      enum UE_CATEGORY_DL_M1_UL_M1 {
        description "DL Category M1 and UL Category M1";
        value 0;
      }
      enum UE_CATEGORY_DL_0_UL_0 {
        description "DL Category 0 and UL Category 0";
        value 1;
      }
      enum UE_CATEGORY_1 {
        description "UE Category 1";
        value 2;
      }
      enum UE_CATEGORY_2 {
        description "UE Category 2";
        value 3;
      }
      enum UE_CATEGORY_3 {
        description "UE Category 3";
        value 4;
      }
      enum UE_CATEGORY_4 {
        description "UE Category 4";
        value 5;
      }
      enum UE_CATEGORY_5 {
        description "UE Category 5";
        value 6;
      }
      enum UE_CATEGORY_6 {
        description "UE Category 6";
        value 7;
      }
      enum UE_CATEGORY_7 {
        description "UE Category 7";
        value 8;
      }
      enum UE_CATEGORY_8 {
        description "UE Category 8";
        value 9;
      }
      enum UE_CATEGORY_9 {
        description "UE Category 9";
        value 10;
      }
      enum UE_CATEGORY_10 {
        description "UE Category 10";
        value 11;
      }
      enum UE_CATEGORY_11 {
        description "UE Category 11";
        value 12;
      }
      enum UE_CATEGORY_12 {
        description "UE Category 12";
        value 13;
      }
      enum UE_CATEGORY_DL_6_UL_5 {
        description "DL Category 6 and UL Category 5";
        value 14;
      }
      enum UE_CATEGORY_DL_7_UL_13 {
        description "DL Category 7 and UL Category 13";
        value 15;
      }
      enum UE_CATEGORY_DL_9_UL_5 {
        description "DL Category 9 and UL Category 5";
        value 16;
      }
      enum UE_CATEGORY_DL_10_UL_13 {
        description "DL Category 10 and UL Category 13";
        value 17;
      }
      enum UE_CATEGORY_DL_11_UL_5 {
        description "DL Category 11 and UL Category 5";
        value 18;
      }
      enum UE_CATEGORY_DL_12_UL_13 {
        description "DL Category 12 and UL Category 13";
        value 19;
      }
      enum UE_CATEGORY_DL_13_UL_3 {
        description "DL Category 13 and UL Category 3";
        value 20;
      }
      enum UE_CATEGORY_DL_13_UL_5 {
        description "DL Category 13 and UL Category 5";
        value 21;
      }
      enum UE_CATEGORY_DL_13_UL_7 {
        description "DL Category 13 and UL Category 7";
        value 22;
      }
      enum UE_CATEGORY_DL_13_UL_13 {
        description "DL Category 13 and UL Category 13";
        value 23;
      }
      enum UE_CATEGORY_DL_14_UL_8 {
        description "DL Category 14 and UL Category 8";
        value 24;
      }
      enum UE_CATEGORY_DL_15_UL_3 {
        description "DL Category 15 and UL Category 3";
        value 25;
      }
      enum UE_CATEGORY_DL_15_UL_5 {
        description "DL Category 15 and UL Category 5";
        value 26;
      }
      enum UE_CATEGORY_DL_15_UL_7 {
        description "DL Category 15 and UL Category 7";
        value 27;
      }
      enum UE_CATEGORY_DL_15_UL_13 {
        description "DL Category 15 and UL Category 13";
        value 28;
      }
      enum UE_CATEGORY_DL_16_UL_3 {
        description "DL Category 16 and UL Category 3";
        value 29;
      }
      enum UE_CATEGORY_DL_16_UL_5 {
        description "DL Category 16 and UL Category 5";
        value 30;
      }
      enum UE_CATEGORY_DL_16_UL_7 {
        description "DL Category 16 and UL Category 7";
        value 31;
      }
      enum UE_CATEGORY_DL_16_UL_13 {
        description "DL Category 16 and UL Category 13";
        value 32;
      }
      enum UE_CATEGORY_DL_17_UL_14 {
        description "DL Category 17 and UL Category 14";
        value 33;
      }
      enum UE_CATEGORY_DL_18_UL_3 {
        description "DL Category 18 and UL Category 3";
        value 34;
      }
      enum UE_CATEGORY_DL_18_UL_5 {
        description "DL Category 18 and UL Category 5";
        value 35;
      }
      enum UE_CATEGORY_DL_18_UL_7 {
        description "DL Category 18 and UL Category 7";
        value 36;
      }
      enum UE_CATEGORY_DL_18_UL_13 {
        description "DL Category 18 and UL Category 13";
        value 37;
      }
      enum UE_CATEGORY_DL_19_UL_3 {
        description "DL Category 19 and UL Category 3";
        value 38;
      }
      enum UE_CATEGORY_DL_19_UL_5 {
        description "DL Category 19 and UL Category 5";
        value 39;
      }
      enum UE_CATEGORY_DL_19_UL_7 {
        description "DL Category 19 and UL Category 7";
        value 40;
      }
      enum UE_CATEGORY_DL_19_UL_13 {
        description "DL Category 19 and UL Category 13";
        value 41;
      }
      enum UE_CATEGORY_DL_20_UL_3 {
        description "DL Category 20 and UL Category 3";
        value 42;
      }
      enum UE_CATEGORY_DL_20_UL_5 {
        description "DL Category 20 and UL Category 5";
        value 43;
      }
      enum UE_CATEGORY_DL_20_UL_7 {
        description "DL Category 20 and UL Category 7";
        value 44;
      }
      enum UE_CATEGORY_DL_20_UL_13 {
        description "DL Category 20 and UL Category 13";
        value 45;
      }
    }
  }
  typedef enum-SrProcessingLevel {
    type enumeration {
      enum NO_ADDITIONAL_SR_NEEDED {
        description "No additional SR needed before eNodeB further processes the SR for the UE.";
        value 0;
      }
      enum TWO_SR_FOR_LOW_THRESHOLD_SR_PROCESSING {
        description "Two SRs needed in a row before eNodeB further processes the SR for the UE, if SR is detected with SINR lower than high SR detection threshold.";
        value 1;
      }
      enum TWO_SR_FOR_ALL_SR_PROCESSING {
        description "Two SRs needed in a row before eNodeB further processes the SR for the UE, whether SR is detected with high or low SINR.";
        value 2;
      }
    }
  }
  typedef enum-ElcLongDrxCycle {
    type enumeration {
      enum SF40 {
        description "Number of sub frames.";
        value 0;
      }
      enum SF320 {
        description "Number of sub frames.";
        value 3;
      }
    }
  }
  typedef enum-ParameterChangeCause {
    type enumeration {
      enum INITIAL {
        description "The parameter has not been changed.";
        value 0;
      }
      enum MRO {
        description "The Mobility Robustness Optimization function requests the change.";
        value 1;
      }
      enum MLB {
        description "The Mobility Load Balancing Function function requests the change.";
        value 2;
      }
      enum RACH {
        description "The RACH Optimization function requests the change.";
        value 3;
      }
    }
  }
  typedef enum-NoOfSubframesVals {
    type enumeration {
      enum SF1 {
        description "SF1 denotes one subframe.";
        value 0;
      }
      enum SF2 {
        description "SF2 denotes two consecutive subframes.";
        value 1;
      }
      enum SF4 {
        description "SF4 denotes four consecutive subframes.";
        value 2;
      }
      enum SF6 {
        description "SF6 denotes six consecutive subframes.";
        value 3;
      }
    }
  }
  typedef enum-ChannelSelectionType {
    type enumeration {
      enum STATIC_CHANNEL_SELECTION {
        description "Use static channel selection for unlicensed carriers.";
        value 0;
      }
      enum DYNAMIC_CHANNEL_SELECTION {
        description "Use dynamic channel selection for unlicensed carriers.";
        value 1;
      }
    }
  }
  typedef enum-SCellSelectionMode {
    type enumeration {
      enum ACK_SEQUENTIAL_SCELL_SELECTION {
        description "A1 measurement configured at selection of SCell. Configures one SCell at a time.";
        value 0;
      }
      enum UN_ACK_SIMULTANEOUS_SCELL_SELECTION {
        description "No A1 measurement configured at selection of SCell. Configures one or more SCells at a time at initial configuration.";
        value 1;
      }
      enum ACK_SIMULTANEOUS_SCELL_SELECTION {
        description "A1 measurement configured at selection of SCell. Configures one or more SCells at a time at initial configuration.";
        value 2;
      }
    }
  }
  typedef ddt-Lrat_WhiteListPlmnIdentity_mncLength {
    type int32 {
      range 2..3;
    }
  }
  typedef ddt-Lrat_NbIotCell_dlNonAnchPrbNum {
    type int32 {
      range 0..7;
    }
  }
  typedef ddt-Lrat_NbIotCell_sInterSearchThreshold {
    type int32 {
      range 0..62;
    }
  }
  typedef ddt-Lrat_Cdma20001xRttFreqRelation_voicePrio {
    type int32 {
      range -1..7;
    }
  }
  typedef ddt-Lrat_EUtranFreqRelation_voicePrio {
    type int32 {
      range -1..7;
    }
  }
  typedef ddt-Lrat_EUtranCellFDD_puschMaxNrOfPrbsPerUe {
    type int32 {
      range 1..100;
    }
  }
  typedef ddt-Lrat_QciProfilePredefined_dlMinBitRate {
    type int32 {
      range 0..150000;
    }
  }
  typedef ddt-Lrat_NbIotCell_qQualMin {
    type int32 {
      range "-34..-3 | 0..0";
    }
  }
  typedef ddt-Lrat_PmFlexCounterFilter_spidFilterMin {
    type int32 {
      range 1..256;
    }
  }
  typedef ddt-Lrat_ENodeBFunction_csmMinHighHitThreshold {
    type int32 {
      range 50..100;
    }
  }
  typedef ddt-Lrat_MbsfnSubframeConfigRO_subframeAllocation {
    type int32 {
      range "1..1 | 4..4";
    }
  }
  typedef ddt-Lrat_MeasReportConfigParams_a5Threshold2RsrpOffset {
    type int32 {
      range -100..100;
    }
  }
  typedef ddt-Lrat_ENodeBFunction_tRelocOverall {
    type int32 {
      range 1..20;
    }
  }
  typedef ddt-Lrat_QciProfilePredefined_priority {
    type int32 {
      range 0..14;
    }
  }
  typedef ddt-Lrat_EranInterMeLink_linkLatency24hrsHWM {
    type int32 {
      range -1..1000000;
    }
  }
  typedef ddt-Lrat_QciProfilePredefined_userLabel {
    type string {
      length 1..128;
    }
  }
  typedef ddt-Lrat_EUtranCellFDD_cellDownlinkCaCapacity {
    type int32 {
      range 0..1000000;
    }
  }
  typedef ddt-Lrat_EUtranCellTDD_hoOptAdjThresholdAbsQci1 {
    type int32 {
      range 0..32767;
    }
  }
  typedef ddt-Lrat_EUtranCellTDD_bsrThreshold {
    type int32 {
      range 0..32767;
    }
  }
  typedef ddt-Lrat_EUtranCellTDD_primaryPsdOffset {
    type int32 {
      range 0..31;
    }
  }
  typedef ddt-Lrat_MbsfnArea_userLabel {
    type string {
      length 1..128;
    }
  }
  typedef ddt-Lrat_QciProfilePredefined_dlMaxHARQTxQci {
    type int32 {
      range "1..1 | 2..2 | 3..3 | 4..4 | 5..5 | 6..6 | 7..7 | 8..8 | 10..10 | 12..12 | 16..16 | 20..20 | 24..24 | 28..28";
    }
  }
  typedef ddt-Lrat_EUtranCellTDD_measuredMaxNoOfUsersInCell {
    type int32 {
      range 0..32768;
    }
  }
  typedef ddt-Lrat_EUtranCellFDD_ulPsdLoadThresholdSinrClpc {
    type int32 {
      range -126..24;
    }
  }
  typedef ddt-Lrat_EUtranCellRelation_sCellPriority {
    type int32 {
      range -1..7;
    }
  }
  typedef ddt-Lrat_EUtranCellTDD_modificationPeriodCoeff {
    type int32 {
      range "2..2 | 4..4 | 8..8 | 16..16";
    }
  }
  typedef ddt-Lrat_EUtranFreqRelation_a5Thr2RsrqFreqOffset {
    type int32 {
      range -240..240;
    }
  }
  typedef ddt-Lrat_EUtranCellTDD_puschPwrOffset64qam {
    type int32 {
      range 0..8;
    }
  }
  typedef ddt-Lrat_Band46UnlicensedProfile_b46B48290MaxPower {
    type int32 {
      range 0..30;
    }
  }
  typedef ddt-Lrat_EUtranCellTDD_loadBasedBarringFactor {
    type int32 {
      range 0..100;
    }
  }
  typedef ddt-Lrat_ReportConfigEUtraIFBestCell_hysteresisA3RsrqOffset {
    type int32 {
      range -150..150;
    }
  }
  typedef ddt-Lrat_ReportConfigCsg_timeToTriggerA5AltCsg {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_BandClassPrioCDMA2000_connectedModeMobilityPrio {
    type int32 {
      range "-1000..-1000 | -1..7";
    }
  }
  typedef ddt-Lrat_EUtranCellTDD_noOfPucchFormat2PrbPairsPerFrame {
    type int32 {
      range 0..1000;
    }
  }
  typedef ddt-Lrat_A5PCOffsetMCPC_a5Thr2RsrqPCOffset {
    type int32 {
      range -240..240;
    }
  }
  typedef ddt-Lrat_Band46UnlicensedProfile_b46C51290MaxPower {
    type int32 {
      range 0..30;
    }
  }
  typedef ddt-Lrat_EUtranCellTDD_dlDynUeAdmCtrlOverloadThr {
    type int32 {
      range 0..1000;
    }
  }
  typedef ddt-Lrat_ReportConfigA1Prim_a1ThrRsrpPrimOffsetCeABr {
    type int32 {
      range -100..100;
    }
  }
  typedef ddt-Lrat_EUtranFreqRelation_a5Thr1RsrqFreqOffset {
    type int32 {
      range -240..240;
    }
  }
  typedef ddt-Lrat_EUtranCellFDD_pdcchLaGinrMargin {
    type int32 {
      range -50..150;
    }
  }
  typedef ddt-Lrat_ReportConfigB1GUtra_hysteresisB1 {
    type int32 {
      range 0..30;
    }
  }
  typedef ddt-Lrat_QciProfilePredefined_rlfPriority {
    type int32 {
      range 0..100;
    }
  }
  typedef ddt-Lrat_GlobalEnbId_mncLength {
    type int32 {
      range 2..3;
    }
  }
  typedef ddt-Lrat_UtranTDDFreqRelation_threshXHigh {
    type int32 {
      range 0..62;
    }
  }
  typedef ddt-Lrat_SubscriberGroupProfile_customTriggerList {
    type int32 {
      range 0..65535;
    }
  }
  typedef ddt-Lrat_ReportConfigA4_timeToTriggerA4 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_NbIotCell_earfcnul {
    type int32 {
      range "-1..-1 | 0..0 | 18000..35999 | 46590..262143";
    }
  }
  typedef ddt-Lrat_CsfbRegParams1xRtt_registrationPeriod {
    type int32 {
      range "0..0 | 29..85";
    }
  }
  typedef ddt-Lrat_Rrc_tRrcConnectionReconfiguration {
    type int32 {
      range 1..20;
    }
  }
  typedef ddt-Lrat_UtranCellRelation_timeOfLastModification {
    type string {
      length 0..19;
    }
  }
  typedef ddt-Lrat_SectorCarrier_configuredMaxTxPower {
    type int32 {
      range 0..10000000;
    }
  }
  typedef ddt-Lrat_SIB3_sNonIntraSearchP {
    type int32 {
      range 0..62;
    }
  }
  typedef ddt-Lrat_UtranFreqRelation_csFallbackPrio {
    type int32 {
      range -1..7;
    }
  }
  typedef ddt-Lrat_SIB3_sNonIntraSearchQ {
    type int32 {
      range 0..31;
    }
  }
  typedef ddt-Lrat_Cdma2000FreqRelQciB2ThrOffsets_b2Thr1RsrpCdma2000FreqQciOffset {
    type int32 {
      range -100..100;
    }
  }
  typedef ddt-Lrat_SpectrumEmissionReqMapping_freqBand {
    type int32 {
      range 1..256;
    }
  }
  typedef ddt-Lrat_UeMeasControl_a3SuspendCsgTimer {
    type int32 {
      range 0..120000;
    }
  }
  typedef ddt-Lrat_ENodeBFunction_dnsLookupTimer {
    type int32 {
      range 0..1000;
    }
  }
  typedef ddt-Lrat_LoadBalancingFunction_lbHitRateEUtranAddThreshold {
    type int32 {
      range 1..100;
    }
  }
  typedef ddt-Lrat_ENodeBFunction_timePhaseMaxDeviationEdrx {
    type int32 {
      range 1..200;
    }
  }
  typedef ddt-Lrat_MultipleNSPmaxReqMapping_additionalPMax {
    type int32 {
      range "-30..33 | 1000..1000";
    }
  }
  typedef ddt-Lrat_TimerProfile_tWaitForRrcConnReest {
    type int32 {
      range 1..20;
    }
  }
  typedef ddt-Lrat_EUtranCellTDD_physicalLayerCellId {
    type int32 {
      range 0..503;
    }
  }
  typedef ddt-Lrat_ExternalUtranCellFDD_masterUtranCellId {
    type string {
      length 0..128;
    }
  }
  typedef ddt-Lrat_EUtranCellFDD_maxSentCrsAssistCells {
    type int32 {
      range 0..8;
    }
  }
  typedef ddt-Lrat_ReportConfigCsg_hysteresisA5AltCsg {
    type int32 {
      range 0..150;
    }
  }
  typedef ddt-Lrat_Band46UnlicensedProfile_b46A46890MaxPower {
    type int32 {
      range 0..30;
    }
  }
  typedef ddt-Lrat_FreqGroupPrioGERAN_cellReselectionPriority {
    type int32 {
      range "-1000..-1000 | 0..7";
    }
  }
  typedef ddt-Lrat_ReportConfigSearch_hysteresisA2UlCritical {
    type int32 {
      range 0..150;
    }
  }
  typedef ddt-Lrat_EUtranCellTDD_qQualMinOffset {
    type int32 {
      range 0..8;
    }
  }
  typedef ddt-Lrat_ExternalEUtranCellFDD_tac {
    type int32 {
      range 0..65535;
    }
  }
  typedef ddt-Lrat_TermPointToMme_mmeCodeListLTERelated {
    type int32 {
      range -1..255;
    }
  }
  typedef ddt-Lrat_SciProfile_sci {
    type int32 {
      range 0..18;
    }
  }
  typedef ddt-Lrat_ReportConfigSearch_timeToTriggerA1Search {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_validDlBrSubframes {
    type int32 {
      range 0..1023;
    }
  }
  typedef ddt-Lrat_CandNeighborRelInfoRO_physicalLayerSubCellId {
    type int32 {
      range 0..2;
    }
  }
  typedef ddt-Lrat_AnrFunctionEUtran_cellAddRsrpThresholdEutran {
    type int32 {
      range -1440..0;
    }
  }
  typedef ddt-Lrat_EUtranCellFDD_lbabThreshTimeHigh {
    type int32 {
      range 0..4095;
    }
  }
  typedef ddt-Lrat_EUtranCellTDD_cellId {
    type int32 {
      range 0..255;
    }
  }
  typedef ddt-Lrat_ExternalGeranCell_cellIdentity {
    type int32 {
      range 0..65535;
    }
  }
  typedef ddt-Lrat_PrefTrafficMgmt_plmnResOpUseMsrUsageThreshold {
    type int32 {
      range 0..100;
    }
  }
  typedef ddt-Lrat_AnrFunction_removeNcellTime {
    type int32 {
      range 0..1000;
    }
  }
  typedef ddt-Lrat_EUtranCellTDD_pdcchOuterLoopUpStep {
    type int32 {
      range 0..100;
    }
  }
  typedef ddt-Lrat_AdmissionControl_paArpOverride {
    type int32 {
      range 0..15;
    }
  }
  typedef ddt-Lrat_EUtranCellTDD_initialBufferSizeDefault {
    type int32 {
      range 1..10000;
    }
  }
  typedef ddt-Lrat_EUtranFreqRelation_qQualMin {
    type int32 {
      range "-34..-3 | 0..0";
    }
  }
  typedef ddt-Lrat_ReportConfigB2Cdma20001xRtt_hysteresisB2 {
    type int32 {
      range 0..150;
    }
  }
  typedef ddt-Lrat_ReportConfigB2GeranUlTrig_timeToTriggerB2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_MbsfnArea_mcchOffset {
    type int32 {
      range 0..10;
    }
  }
  typedef ddt-Lrat_ReportConfigB2CdmaRttUlTrig_b2Threshold2Cdma20001xRtt {
    type int32 {
      range -315..0;
    }
  }
  typedef ddt-Lrat_Paging_pagingDiscardTimerEdrxNb {
    type int32 {
      range 1..52;
    }
  }
  typedef ddt-Lrat_EUtranCellTDD_nonCaF3SelectionThreshold {
    type int32 {
      range 1..6000;
    }
  }
  typedef ddt-Lrat_SignalingRadioBearer_tPollRetransmitUl {
    type int32 {
      range "5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500";
    }
  }
  typedef ddt-Lrat_AnrFunctionEUtran_anrEutranInterFMeasReportMin {
    type int32 {
      range 0..1000;
    }
  }
  typedef ddt-Lrat_ENodeBFunction_licConnectedUsersPercentileConf {
    type int32 {
      range 1..100;
    }
  }
  typedef ddt-Lrat_EUtranFreqRelation_qRxLevMinCe {
    type int32 {
      range -140..-44;
    }
  }
  typedef ddt-Lrat_ExternalEUtranCellTDD_masterEUtranCellTDDId {
    type string {
      length 0..128;
    }
  }
  typedef ddt-Lrat_NotificationConfig_notificationOffset {
    type int32 {
      range 0..10;
    }
  }
  typedef ddt-Lrat_PmFlexCounterFilter_spidFilterMax {
    type int32 {
      range 1..256;
    }
  }
  typedef ddt-Lrat_EUtranCellTDD_nrOfPreallocatedSrRes {
    type int32 {
      range -1..20;
    }
  }
  typedef ddt-Lrat_EUtranCellFDD_pZeroNominalPucch {
    type int32 {
      range -127..-96;
    }
  }
  typedef ddt-Lrat_ReportConfigEUtraIFA3UlTrig_a3Offset {
    type int32 {
      range -150..150;
    }
  }
  typedef ddt-Lrat_InstantUplinkAccess_iuaTargetBufferEmptyTime {
    type int32 {
      range 1..10;
    }
  }
  typedef ddt-Lrat_PmFlexCounterFilter_lcgFilterMin {
    type int32 {
      range 0..3;
    }
  }
  typedef ddt-Lrat_EUtranCellFDD_dlPowerRampUpInitRatio {
    type int32 {
      range 40..100;
    }
  }
  typedef ddt-Lrat_ReportConfigEUtraBestCell_hysteresisA3 {
    type int32 {
      range 0..150;
    }
  }
  typedef ddt-Lrat_UtranFreqRelation_altCsfbTargetPrioEc {
    type int32 {
      range -1..7;
    }
  }
  typedef ddt-Lrat_InstantUplinkAccess_iuaDeactTimer {
    type int32 {
      range 0..500;
    }
  }
  typedef ddt-Lrat_MdtConfiguration_maxReportCellsA2Mdt {
    type int32 {
      range 1..8;
    }
  }
  typedef ddt-Lrat_NbIotCell_physicalLayerCellIdGroup {
    type int32 {
      range 0..167;
    }
  }
  typedef ddt-Lrat_SubscriberGroupProfile_profileIndex {
    type int32 {
      range 0..4;
    }
  }
  typedef ddt-Lrat_GlobalEnbId_mcc {
    type int32 {
      range 0..999;
    }
  }
  typedef ddt-Lrat_ExternalENodeBFunction_timeOfLastModification {
    type string {
      length 0..19;
    }
  }
  typedef ddt-Lrat_EUtranCellTDD_lbabMinBarringFactor {
    type int32 {
      range 0..100;
    }
  }
  typedef ddt-Lrat_PmchMch_qci {
    type int32 {
      range 0..255;
    }
  }
  typedef ddt-Lrat_ReportConfigB1GUtra_timeToTriggerB1 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_NbIotCell_physicalLayerCellId {
    type int32 {
      range 0..503;
    }
  }
  typedef ddt-Lrat_ENodeBFunction_licDlPrbPercentileConf {
    type int32 {
      range 1..100;
    }
  }
  typedef ddt-Lrat_CellSleepNodeFunction_csmEutranInterFMeasReportIncr {
    type int32 {
      range 0..1000;
    }
  }
  typedef ddt-Lrat_SIB3_qHyst {
    type int32 {
      range "0..0 | 1..1 | 2..2 | 3..3 | 4..4 | 5..5 | 6..6 | 8..8 | 10..10 | 12..12 | 14..14 | 16..16 | 18..18 | 20..20 | 22..22 | 24..24";
    }
  }
  typedef ddt-Lrat_UtranFreqRelation_b2Thr2RscpUtraFreqOffset {
    type int32 {
      range -24..24;
    }
  }
  typedef ddt-Lrat_MobilityParams1xRtt_mcc {
    type int32 {
      range 0..1023;
    }
  }
  typedef ddt-Lrat_ReportConfigEUtraBadCovSec_hysteresisA2Sec {
    type int32 {
      range 0..150;
    }
  }
  typedef ddt-Lrat_EUtranCellFDD_noOfCrsPorts {
    type int32 {
      range "-1..-1 | 1..1 | 2..2 | 4..4";
    }
  }
  typedef ddt-Lrat_Rrc_t301Br {
    type int32 {
      range "0..0 | 2500..2500 | 3000..3000 | 3500..3500 | 4000..4000 | 5000..5000 | 6000..6000 | 8000..8000 | 10000..10000";
    }
  }
  typedef ddt-Lrat_EUtranCellFDD_pdcchOuterLoopUpStepVolte {
    type int32 {
      range 0..100;
    }
  }
  typedef ddt-Lrat_CellSleepFunction_covCellUeLostWakeUpThr {
    type int32 {
      range 0..100;
    }
  }
  typedef ddt-Lrat_ReportConfigB2Cdma20001xRtt_timeToTriggerB2Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_QciProfilePredefined_harqPriority {
    type int32 {
      range 0..99;
    }
  }
  typedef ddt-Lrat_EUtranCellFDD_ulConfigurableFrequencyStart {
    type int32 {
      range 0..100;
    }
  }
  typedef ddt-Lrat_AnrFunctionEUtran_anrEutranInterFMeasReportMax {
    type int32 {
      range 0..1000;
    }
  }
  typedef ddt-Lrat_EUtranCellFDD_beamWeightSet16Tr {
    type int32 {
      range 0..128;
    }
  }
  typedef ddt-Lrat_EUtranCellFDD_cioUpperLimitAdjBySon {
    type int32 {
      range 0..24;
    }
  }
  typedef ddt-Lrat_MimoSleepFunction_switchUpRrcConnThreshold {
    type int32 {
      range 0..500;
    }
  }
  typedef ddt-Lrat_EUtranCellTDD_lbEUtranTriggerOffloadThreshold {
    type int32 {
      range 0..1600;
    }
  }
  typedef ddt-Lrat_ReportConfigB2Cdma20001xRtt_b2Threshold2Cdma20001xRtt {
    type int32 {
      range -315..0;
    }
  }
  typedef ddt-Lrat_EUtranCellTDD_qQualMinRsrqCe {
    type int32 {
      range "-34..-3 | 0..0";
    }
  }
  typedef ddt-Lrat_EUtranCellTDD_caPrioThreshold {
    type int32 {
      range 0..65535;
    }
  }
  typedef ddt-Lrat_SignalingRadioBearer_tReorderingUl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-Lrat_UeMeasControl_maxMeasEUtraOther {
    type int32 {
      range 1..5;
    }
  }
  typedef ddt-Lrat_MbmsService_logicalChannelIdentity {
    type int32 {
      range 1..28;
    }
  }
  typedef ddt-Lrat_EndcProfilePredefined_meNbS1TermReqArpLev {
    type int32 {
      range 0..15;
    }
  }
  typedef ddt-ExternalUtranCellFDD_changeFrequency_arfcnValueUtranDl {
    type int32 {
      range 0..16383;
    }
  }
  typedef ddt-Lrat_LoadBalancingFunction_ocdMaxNoHighHitRateCells {
    type int32 {
      range 1..10;
    }
  }
  typedef ddt-Lrat_MACConfiguration_ulMaxHARQTx {
    type int32 {
      range "1..1 | 2..2 | 3..3 | 4..4 | 5..5 | 6..6 | 7..7";
    }
  }
  typedef ddt-Lrat_Paging_pagingDiscardTimerEdrx {
    type int32 {
      range 1..31;
    }
  }
  typedef ddt-Lrat_EUtranFrequency_arfcnValueEUtranDl {
    type int32 {
      range "0..17999 | 36000..262143";
    }
  }
  typedef ddt-Lrat_NbIotCell_gbPrbIndexUl {
    type int32 {
      range "-6..-1 | 1..6";
    }
  }
  typedef ddt-Lrat_ReportConfigB1Utra_timeToTriggerB1 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_GlobalEnbId_mnc {
    type int32 {
      range 0..999;
    }
  }
  typedef ddt-Lrat_EUtranCellTDD_iuaInterval {
    type int32 {
      range 0..5;
    }
  }
  typedef ddt-Lrat_CarrierAggregationFunction_sCellDeactOutOfCoverageTimer {
    type int32 {
      range -1..5000;
    }
  }
  typedef ddt-Lrat_EUtranCellFDD_maxQciLatencyMeas {
    type int32 {
      range 0..255;
    }
  }
  typedef ddt-Lrat_TermPointToMme_usedIpAddress {
    type string {
      length 2..39;
    }
  }
  typedef ddt-Lrat_SIB3_tEvaluation {
    type int32 {
      range "30..30 | 60..60 | 120..120 | 180..180 | 240..240";
    }
  }
  typedef ddt-Lrat_EUtranCellFDD_noOfPucchSrUsers {
    type int32 {
      range 0..4000;
    }
  }
  typedef ddt-Lrat_ExternalCdma20001xRttCell_sid {
    type int32 {
      range 0..32768;
    }
  }
  typedef ddt-Lrat_GeraNetwork_userLabel {
    type string {
      length 1..128;
    }
  }
  typedef ddt-Lrat_AnrFunctionUtran_anrUtranMeasReportIncr {
    type int32 {
      range 0..1000;
    }
  }
  typedef ddt-Lrat_ReportConfigA1A2Br_hysteresisA1A2UlIntraFSearch {
    type int32 {
      range 0..150;
    }
  }
  typedef ddt-Lrat_EUtranCellTDD_ulSCellPriority {
    type int32 {
      range 0..5;
    }
  }
  typedef ddt-Lrat_MobilityParams1xRtt_fchFchInitSetupRc3 {
    type int32 {
      range 8..255;
    }
  }
  typedef ddt-Lrat_MobilityParams1xRtt_fchFchInitSetupRc4 {
    type int32 {
      range 8..255;
    }
  }
  typedef ddt-Lrat_EUtranCellTDD_harqOffsetUl {
    type int32 {
      range -20..20;
    }
  }
  typedef ddt-Lrat_MobilityParams1xRtt_fchFchInitSetupRc5 {
    type int32 {
      range 8..255;
    }
  }
  typedef ddt-Lrat_MobilityParams1xRtt_localTimeOffset {
    type int32 {
      range -24..23;
    }
  }
  typedef ddt-Lrat_EUtranCellTDD_uncertAltitude {
    type int32 {
      range 0..127;
    }
  }
  typedef ddt-Lrat_EUtranCellFDD_lbTpNonQualFraction {
    type int32 {
      range "0..0 | 20..80";
    }
  }
  typedef ddt-Lrat_ExternalEUtranCellTDD_freqBand {
    type int32 {
      range 1..256;
    }
  }
  typedef ddt-Lrat_ReportConfigEUtraBadCovPrim_hysteresisA2Prim {
    type int32 {
      range 0..150;
    }
  }
  typedef ddt-Lrat_Mbms_userLabel {
    type string {
      length 1..128;
    }
  }
  typedef ddt-Lrat_SIRepetitionNB_siRepetitionSI14 {
    type int32 {
      range "2..2 | 4..4 | 8..8 | 16..16";
    }
  }
  typedef ddt-Lrat_ENodeBFunction_timePhaseMaxDeviationTdd7 {
    type int32 {
      range 9..100;
    }
  }
  typedef ddt-Lrat_EUtranCellFDD_lbTpRankThreshMin {
    type int32 {
      range "-100..-100 | -60..60";
    }
  }
  typedef ddt-Lrat_EUtranCellRelation_qOffsetCellEUtran {
    type int32 {
      range "-24..-24 | -22..-22 | -20..-20 | -18..-18 | -16..-16 | -14..-14 | -12..-12 | -10..-10 | -8..-8 | -6..-6 | -5..-5 | -4..-4 | -3..-3 | -2..-2 | -1..-1 | 0..0 | 1..1 | 2..2 | 3..3 | 4..4 | 5..5 | 6..6 | 8..8 | 10..10 | 12..12 | 14..14 | 16..16 | 18..18 | 20..20 | 22..22 | 24..24";
    }
  }
  typedef ddt-Lrat_ENodeBFunction_timePhaseMaxDeviationTdd3 {
    type int32 {
      range 9..100;
    }
  }
  typedef ddt-Lrat_ENodeBFunction_timePhaseMaxDeviationTdd4 {
    type int32 {
      range 9..100;
    }
  }
  typedef ddt-Lrat_NbIotFrequencyInfo_pMax {
    type int32 {
      range "-30..33 | 1000..1000";
    }
  }
  typedef ddt-Lrat_ENodeBFunction_timePhaseMaxDeviationTdd5 {
    type int32 {
      range 9..100;
    }
  }
  typedef ddt-Lrat_ENodeBFunction_timePhaseMaxDeviationTdd6 {
    type int32 {
      range 9..100;
    }
  }
  typedef ddt-Lrat_ENodeBFunction_timePhaseMaxDeviationTdd1 {
    type int32 {
      range 9..100;
    }
  }
  typedef ddt-Lrat_ENodeBFunction_timePhaseMaxDeviationTdd2 {
    type int32 {
      range 9..100;
    }
  }
  typedef ddt-Lrat_ReportConfigEUtraBadCovPrim_a2ThresholdRsrpPrim {
    type int32 {
      range -140..-44;
    }
  }
  typedef ddt-Lrat_ReportConfigInterRatPm_b2Threshold2RscpUtraPm {
    type int32 {
      range -120..-24;
    }
  }
  typedef ddt-Lrat_EUtranFreqRelation_tReselectionEutra {
    type int32 {
      range 0..7;
    }
  }
  typedef ddt-Lrat_UnlicensedAccessFunction_laaMasterCarrierTimer {
    type int32 {
      range 1..60;
    }
  }
  typedef ddt-Lrat_NbIotCell_qHyst {
    type int32 {
      range 0..24;
    }
  }
  typedef ddt-Lrat_GeranFreqGroupRelation_threshXLow {
    type int32 {
      range 0..62;
    }
  }
  typedef ddt-Lrat_PlmnIdentity_mcc {
    type int32 {
      range 0..999;
    }
  }
  typedef ddt-Lrat_EUtranFreqToQciProfileRelation_a3RsrpFreqQciOffsetAdjustment {
    type int32 {
      range -150..150;
    }
  }
  typedef ddt-Lrat_Paging_maxNoOfPagingRecords {
    type int32 {
      range 1..16;
    }
  }
  typedef ddt-Lrat_EUtranCellTDD_filterUeDlThpVolThr {
    type int32 {
      range 0..4000;
    }
  }
  typedef ddt-Lrat_EUtranFreqRelation_tReselectionEutraSfMedium {
    type int32 {
      range 25..100;
    }
  }
  typedef ddt-Lrat_ReportConfigEUtraInterFreqPm_hysteresisPm {
    type int32 {
      range 0..150;
    }
  }
  typedef ddt-Lrat_SIB3_qHystSfHigh {
    type int32 {
      range -6..0;
    }
  }
  typedef ddt-Lrat_ExternalGeranCell_bcc {
    type int32 {
      range 0..7;
    }
  }
  typedef ddt-Lrat_ExternalENodeBFunction_timeOfCreation {
    type string {
      length 0..19;
    }
  }
  typedef ddt-Lrat_ENodeBFunction_ulMaxWaitingTimeGlobal {
    type int32 {
      range 0..500;
    }
  }
  typedef ddt-Lrat_EUtranFreqRelation_nonPlannedPhysCellIdRange {
    type int32 {
      range 1..504;
    }
  }
  typedef ddt-Lrat_MbsfnArea_sfAllocInfo {
    type string {
      length 6..6;
    }
  }
  typedef ddt-Lrat_SIRepetitionNB_siRepetitionSI16 {
    type int32 {
      range "2..2 | 4..4 | 8..8 | 16..16";
    }
  }
  typedef ddt-Lrat_QciProfileOperatorDefined_tReorderingUl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 100..100 | 110..110 | 120..120 | 130..130 | 140..140 | 150..150 | 160..160 | 170..170 | 180..180 | 190..190 | 200..200";
    }
  }
  typedef ddt-Lrat_CandNeighborRelInfoRO_cellId {
    type int32 {
      range 0..255;
    }
  }
  typedef ddt-Lrat_EUtranFreqRelation_lbActivationThreshold {
    type int32 {
      range 0..1000;
    }
  }
  typedef ddt-Lrat_MimoSleepFunction_sleepEndTime {
    type string {
      length 5..5;
    }
  }
  typedef ddt-Lrat_CandNeighborRelInfoRO_enbId {
    type int32 {
      range 0..1048575;
    }
  }
  typedef ddt-Lrat_GeranCellRelation_timeOfLastModification {
    type string {
      length 0..19;
    }
  }
  typedef ddt-Lrat_PmFlexCounterFilter_lcgFilterMax {
    type int32 {
      range 0..3;
    }
  }
  typedef ddt-Lrat_ReportConfigSearch_a2CriticalThrQci1RsrpOffset {
    type int32 {
      range -100..100;
    }
  }
  typedef ddt-Lrat_GtpPath_remoteIpAddress {
    type string {
      length 2..39;
    }
  }
  typedef ddt-Lrat_ReportConfigEUtraInterFreqPm_timeToTriggerPm {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_AdmissionControl_dlMbmsGbrRatio {
    type int32 {
      range 0..1000;
    }
  }
  typedef ddt-Lrat_OcngPrbSerie_prbLast {
    type int32 {
      range 0..99;
    }
  }
  typedef ddt-Lrat_EUtranCellTDD_hpueCaSwitchTimeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_PeriodicitySI_siPeriodicitySI7 {
    type int32 {
      range "8..8 | 16..16 | 32..32 | 64..64 | 128..128 | 256..256 | 512..512";
    }
  }
  typedef ddt-Lrat_PeriodicitySI_siPeriodicitySI8 {
    type int32 {
      range "8..8 | 16..16 | 32..32 | 64..64 | 128..128 | 256..256 | 512..512";
    }
  }
  typedef ddt-Lrat_PeriodicitySI_siPeriodicitySI9 {
    type int32 {
      range "8..8 | 16..16 | 32..32 | 64..64 | 128..128 | 256..256 | 512..512";
    }
  }
  typedef ddt-Lrat_ENodeBFunction_x2GtpuEchoDscp {
    type int32 {
      range 0..63;
    }
  }
  typedef ddt-Lrat_EUtranCellFDD_srDetectHighThres {
    type int32 {
      range 0..300;
    }
  }
  typedef ddt-Lrat_NbIotCell_siWindowLength {
    type int32 {
      range "160..160 | 320..320 | 480..480 | 640..640 | 960..960 | 1280..1280 | 1600..1600";
    }
  }
  typedef ddt-Lrat_Paging_pagingDiscardTimerDrx {
    type int32 {
      range 1..15;
    }
  }
  typedef ddt-Lrat_EUtranCellTDD_commonSrPeriodicity {
    type int32 {
      range "5..5 | 10..10 | 20..20";
    }
  }
  typedef ddt-ExternalUtranCellTDD_changeFrequency_arfcnValueUtranDl {
    type int32 {
      range 0..16383;
    }
  }
  typedef ddt-Lrat_MimoSleepFunction_switchDownMonitorDurTimer {
    type int32 {
      range 5..120;
    }
  }
  typedef ddt-Lrat_UeMeasControl_filterCoefficientEUtraRsrq {
    type int32 {
      range "0..0 | 1..1 | 2..2 | 3..3 | 4..4 | 5..5 | 6..6 | 7..7 | 8..8 | 9..9 | 11..11 | 13..13 | 15..15 | 17..17 | 19..19";
    }
  }
  typedef ddt-Lrat_ReportConfigInterRatLb_utranHysteresisB1 {
    type int32 {
      range 0..150;
    }
  }
  typedef ddt-Lrat_UeMeasControl_filterCoefficientEUtraRsrp {
    type int32 {
      range "0..0 | 1..1 | 2..2 | 3..3 | 4..4 | 5..5 | 6..6 | 7..7 | 8..8 | 9..9 | 11..11 | 13..13 | 15..15 | 17..17 | 19..19";
    }
  }
  typedef ddt-Lrat_LoadBalancingFunction_lbHitRateEUtranMeasUeIntensity {
    type int32 {
      range 1..100;
    }
  }
  typedef ddt-Lrat_LoadBalancingFunction_lbCaThreshold {
    type int32 {
      range 0..16000;
    }
  }
  typedef ddt-Lrat_ReportConfigB1Utra_b1ThresholdEcNoUtra {
    type int32 {
      range -245..0;
    }
  }
  typedef ddt-Lrat_GUtraNetwork_userLabel {
    type string {
      length 1..128;
    }
  }
  typedef ddt-Lrat_ReportConfigEUtraInterFreqPm_a1ThresholdRsrpPm {
    type int32 {
      range -140..-44;
    }
  }
  typedef ddt-Lrat_ExternalEUtranCellFDD_ulChannelBandwidth {
    type int32 {
      range "0..0 | 1400..1400 | 3000..3000 | 5000..5000 | 10000..10000 | 15000..15000 | 20000..20000";
    }
  }
  typedef ddt-Lrat_EUtranCellFDD_hpueCaSwitchTimeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_LoadBalancingFunction_ocdMinHighHitThresh {
    type int32 {
      range 1..100;
    }
  }
  typedef ddt-Lrat_EUtranCellTDD_pucchOverdimensioning {
    type int32 {
      range 0..49;
    }
  }
  typedef ddt-Lrat_EUtranCellFDD_loadBasedBarringFactor {
    type int32 {
      range 0..100;
    }
  }
  typedef ddt-Lrat_UeMeasControl_maxMeasUtraFdd {
    type int32 {
      range 1..5;
    }
  }
  typedef ddt-Lrat_MobilityParams1xRtt_gcsnaL2AckTimer {
    type int32 {
      range 1..255;
    }
  }
  typedef ddt-Lrat_ExternalGNodeBFunction_gNodeBId {
    type int64 {
      range 0..4294967295;
    }
  }
  typedef ddt-Lrat_EUtranCellTDD_cellDownlinkCaCapacity {
    type int32 {
      range 0..1000000;
    }
  }
  typedef ddt-Lrat_Band46UnlicensedProfile_b46A47690MaxPower {
    type int32 {
      range 0..30;
    }
  }
  typedef ddt-Lrat_Rrc_t304 {
    type int32 {
      range "50..50 | 100..100 | 150..150 | 200..200 | 500..500 | 1000..1000 | 2000..2000";
    }
  }
  typedef ddt-Lrat_Rrc_t300 {
    type int32 {
      range "100..100 | 200..200 | 300..300 | 400..400 | 600..600 | 1000..1000 | 1500..1500 | 2000..2000";
    }
  }
  typedef ddt-Lrat_AnrFunction_probCellDetectLowHoSuccThres {
    type int32 {
      range 1..99;
    }
  }
  typedef ddt-Lrat_Rrc_t301 {
    type int32 {
      range "100..100 | 200..200 | 300..300 | 400..400 | 600..600 | 1000..1000 | 1500..1500 | 2000..2000";
    }
  }
  typedef ddt-Lrat_ExternalEUtranCellTDD_physicalLayerCellId {
    type int32 {
      range 0..503;
    }
  }
  typedef ddt-Lrat_EUtranFreqRelation_connectedModeMobilityPrioBr {
    type int32 {
      range -1..7;
    }
  }
  typedef ddt-Lrat_Band46UnlicensedProfile_b46C50490MaxPower {
    type int32 {
      range 0..30;
    }
  }
  typedef ddt-Lrat_EUtranCellFDD_qRxLevMinOffset {
    type int32 {
      range "2..16 | 1000..1000";
    }
  }
  typedef ddt-Lrat_EUtranCellFDD_primaryPsdOffset {
    type int32 {
      range 0..31;
    }
  }
  typedef ddt-Lrat_ReportConfigSearch_a2OuterSearchThrRsrqOffset {
    type int32 {
      range -240..0;
    }
  }
  typedef ddt-Lrat_UeMeasControl_filterCoefficientEUtraNI {
    type int32 {
      range 0..31;
    }
  }
  typedef ddt-Lrat_ReportConfigB2UtraUlTrig_b2Threshold2RscpUtra {
    type int32 {
      range -120..-24;
    }
  }
  typedef ddt-Lrat_MeasReportConfigParams_a2ThresholdRsrqSecOffset {
    type int32 {
      range -240..240;
    }
  }
  typedef ddt-Lrat_ENodeBFunction_endcPowerOffsetLte {
    type int32 {
      range "0..0 | 3..3";
    }
  }
  typedef ddt-Lrat_ReportConfigCsfbUtra_hysteresis {
    type int32 {
      range 0..150;
    }
  }
  typedef ddt-Lrat_EUtranCellTDD_lbabIncr {
    type int32 {
      range 5..100;
    }
  }
  typedef ddt-Lrat_EUtranCellTDD_lbTpRankThreshMin {
    type int32 {
      range "-100..-100 | -60..60";
    }
  }
  typedef ddt-Lrat_PmEventService_ueTraceFileSize {
    type int32 {
      range 100..1000;
    }
  }
  typedef ddt-Lrat_ReportConfigA4_a4ThresholdRsrq {
    type int32 {
      range -195..-30;
    }
  }
  typedef ddt-Lrat_NbIotFrequencyInfo_carrierFreq {
    type int32 {
      range 0..262143;
    }
  }
  typedef ddt-Lrat_EUtranCellTDD_expectedMaxNoOfUsersInCell {
    type int32 {
      range -1..32768;
    }
  }
  typedef ddt-Lrat_EUtranCellFDD_lbUtranOffloadThreshold {
    type int32 {
      range 0..1600;
    }
  }
  typedef ddt-Lrat_EUtranCellFDD_lbabIncr {
    type int32 {
      range 5..100;
    }
  }
  typedef ddt-Lrat_EUtranCellTDD_pMaxServingCell {
    type int32 {
      range "-30..33 | 1000..1000";
    }
  }
  typedef ddt-Lrat_ReportConfigA4_a4ThresholdRsrp {
    type int32 {
      range -140..-44;
    }
  }
  typedef ddt-Lrat_EUtranCellFDD_filterUeDlThpTimeThr {
    type int32 {
      range 0..200;
    }
  }
  typedef ddt-Lrat_ReportConfigB2Cdma20001xRtt_b2Threshold1Rsrq {
    type int32 {
      range -195..-30;
    }
  }
  typedef ddt-Lrat_ReportConfigB2Cdma20001xRtt_b2Threshold1Rsrp {
    type int32 {
      range -140..-44;
    }
  }
  typedef ddt-Lrat_EUtranFreqToQciProfileRelation_timeToTriggerA3 {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_SubscriberGroupProfile_spidTriggerList {
    type int32 {
      range 0..256;
    }
  }
  typedef ddt-Lrat_EUtranCellTDD_confidence {
    type int32 {
      range 0..100;
    }
  }
  typedef ddt-Lrat_CarrierAggregationFunction_caUsageLimit {
    type int32 {
      range 0..65535;
    }
  }
  typedef ddt-Lrat_InstantUplinkAccess_iuaTargetBufferSize {
    type int32 {
      range 1..5000;
    }
  }
  typedef ddt-Lrat_TrafficModelPrb_qciDistSinrMedium {
    type int32 {
      range 0..100;
    }
  }
  typedef ddt-Lrat_Paging_noOfDefPagCyclPrim {
    type int32 {
      range 1..16;
    }
  }
  typedef ddt-Lrat_EUtranCellFDD_activeServiceAreaId {
    type int32 {
      range 0..65535;
    }
  }
  typedef ddt-Lrat_SubscriberGroupProfile_subGroupConfiguration5 {
    type int32 {
      range 0..65535;
    }
  }
  typedef ddt-Lrat_FreqPrioEUTRA_cellReselectionPriority {
    type int32 {
      range "-1000..-1000 | 0..7";
    }
  }
  typedef ddt-Lrat_SubscriberGroupProfile_subGroupConfiguration4 {
    type int32 {
      range 0..65535;
    }
  }
  typedef ddt-Lrat_SubscriberGroupProfile_subGroupConfiguration7 {
    type int32 {
      range -200..2147483647;
    }
  }
  typedef ddt-Lrat_SubscriberGroupProfile_subGroupConfiguration6 {
    type int32 {
      range 0..65535;
    }
  }
  typedef ddt-Lrat_ReportConfigCsfbUtra_thresholdRscp {
    type int32 {
      range -120..-24;
    }
  }
  typedef ddt-Lrat_SubscriberGroupProfile_subGroupConfiguration1 {
    type int32 {
      range 0..65535;
    }
  }
  typedef ddt-Lrat_ReportConfigB2GeranUlTrig_b2Threshold2Geran {
    type int32 {
      range -110..-47;
    }
  }
  typedef ddt-Lrat_SubscriberGroupProfile_subGroupConfiguration3 {
    type int32 {
      range 0..65535;
    }
  }
  typedef ddt-Lrat_CellPortion_longitude {
    type int32 {
      range -180000000..180000000;
    }
  }
  typedef ddt-Lrat_SubscriberGroupProfile_subGroupConfiguration2 {
    type int32 {
      range 0..65535;
    }
  }
  typedef ddt-Lrat_IdleModePrioAtRelease_highLoadThreshold {
    type int32 {
      range 0..16000;
    }
  }
  typedef ddt-Lrat_UnlicensedAccessFunction_laaSCellActDeactDataThres {
    type int32 {
      range -1..5000;
    }
  }
  typedef ddt-Lrat_UeMeasControl_ulSinrOffset {
    type int32 {
      range -150..150;
    }
  }
  typedef ddt-Lrat_TermPointToENB_timeOfLastModification {
    type string {
      length 0..19;
    }
  }
  typedef ddt-Lrat_MeasReportConfigParams_b2Threshold1RsrpGeranOffset {
    type int32 {
      range -100..100;
    }
  }
  typedef ddt-Lrat_GeranFreqGroupRelation_csFallbackPrioEC {
    type int32 {
      range -1..7;
    }
  }
  typedef ddt-Lrat_SubFrameConfig_radioframeAllocationOffset {
    type int32 {
      range 0..7;
    }
  }
  typedef ddt-Lrat_EUtranFreqRelation_cellReselectionPriority {
    type int32 {
      range 0..7;
    }
  }
  typedef ddt-Lrat_ReportConfigInterRatPm_b2Threshold2GeranPm {
    type int32 {
      range -110..-47;
    }
  }
  typedef ddt-Lrat_UeMeasControl_maxMeasInterFreqEUtra {
    type int32 {
      range 1..7;
    }
  }
  typedef ddt-Lrat_MeasReportConfigParams_a2ThresholdRsrpSecOffset {
    type int32 {
      range -100..100;
    }
  }
  typedef ddt-Lrat_BandCombCompression_requestedFreqBandsFiltered {
    type int32 {
      range 0..1024;
    }
  }
  typedef ddt-Lrat_GtpPath_localIpAddress {
    type string {
      length 2..39;
    }
  }
  typedef ddt-Lrat_ReportConfigSearch_timeToTriggerA2SearchRsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_dlChannelBandwidth {
    type int32 {
      range "1400..1400 | 3000..3000 | 5000..5000 | 10000..10000 | 15000..15000 | 20000..20000";
    }
  }
  typedef ddt-Lrat_ReportConfigEUtraInterFreqLb_a5Threshold2Rsrp {
    type int32 {
      range -140..44;
    }
  }
  typedef ddt-Lrat_EUtranCellTDD_prioAdditionalFreqBandList {
    type int32 {
      range 1..256;
    }
  }
  typedef ddt-Lrat_ReportConfigEUtraInterFreqLb_a5Threshold2Rsrq {
    type int32 {
      range -195..-30;
    }
  }
  typedef ddt-Lrat_SignalingRadioBearer_ulMaxRetxThreshold {
    type int32 {
      range "1..1 | 2..2 | 3..3 | 4..4 | 6..6 | 8..8 | 16..16 | 32..32";
    }
  }
  typedef ddt-Lrat_AcBarringConfig1xRtt_acBarring10R9 {
    type int32 {
      range 0..7;
    }
  }
  typedef ddt-Lrat_EUtranCellTDD_srvccDelayTimer {
    type int32 {
      range 0..30000;
    }
  }
  typedef ddt-Lrat_EUtranCellTDD_physicalLayerCellIdGroup {
    type int32 {
      range 0..167;
    }
  }
  typedef ddt-Lrat_EUtranCellTDD_longitude {
    type int32 {
      range -180000000..180000000;
    }
  }
  typedef ddt-Lrat_MimoSleepFunction_switchUpPrbThreshold {
    type int32 {
      range 1..90;
    }
  }
  typedef ddt-Lrat_EUtranCellTDD_channelBandwidth {
    type int32 {
      range "5000..5000 | 10000..10000 | 15000..15000 | 20000..20000";
    }
  }
  typedef ddt-Lrat_Rrc_t320 {
    type int32 {
      range "5..5 | 10..10 | 20..20 | 30..30 | 60..60 | 120..120 | 180..180";
    }
  }
  typedef ddt-Lrat_EUtranCellTDD_lbabMinBarringFactorPrio3 {
    type int32 {
      range 0..100;
    }
  }
  typedef ddt-Lrat_EUtranCellTDD_lbabMinBarringFactorPrio4 {
    type int32 {
      range 0..100;
    }
  }
  typedef ddt-MacAddressStr {
    description "MAC address string, controlled by a regular expression.\n\nAddress should be specified in colon separated hexadecimal notation as described in IEEE 802.\nMAC addresses shall have 17 characters.\nValid characters: 0123456789abcdefABCDEF\n\nExample: 00:12:34:56:78:9A";
    type string {
      length 17..17;
    }
  }
  typedef ddt-Lrat_EUtranCellTDD_lbabMinBarringFactorPrio1 {
    type int32 {
      range 0..100;
    }
  }
  typedef ddt-Lrat_EUtranCellTDD_lbabMinBarringFactorPrio2 {
    type int32 {
      range 0..100;
    }
  }
  typedef ddt-Lrat_GeranFreqGroupRelation_voicePrio {
    type int32 {
      range -1..7;
    }
  }
  typedef ddt-Lrat_EUtranCellTDD_ulMaxMuMimoLayers {
    type int32 {
      range "0..0 | 2..2 | 4..4 | 8..8";
    }
  }
  typedef ddt-Lrat_PmEventService_cellTraceHighPrioReserve {
    type int32 {
      range 0..80;
    }
  }
  typedef ddt-Lrat_ReportConfigB2Cdma2000_b2Threshold1Rsrq {
    type int32 {
      range -195..-30;
    }
  }
  typedef ddt-Lrat_ReportConfigB2Cdma2000_b2Threshold1Rsrp {
    type int32 {
      range -140..-44;
    }
  }
  typedef ddt-Lrat_ReportConfigEUtraInterFreqPm_a5Threshold2RsrpPm {
    type int32 {
      range -140..-44;
    }
  }
  typedef ddt-Lrat_ReportConfigEUtraIFA3UlTrig_timeToTriggerA3 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_advCellSupSensitivity {
    type int32 {
      range 0..100;
    }
  }
  typedef ddt-Lrat_EUtranFreqRelation_a5Thr2RsrpFreqOffset {
    type int32 {
      range -100..100;
    }
  }
  typedef ddt-Lrat_EUtranCellFDD_lbabThreshTimeLow {
    type int32 {
      range 0..4095;
    }
  }
  typedef ddt-Lrat_EUtranCellFDD_lbabThreshRejectRateLow {
    type int32 {
      range 0..1000;
    }
  }
  typedef ddt-Lrat_Rrc_t311 {
    type int32 {
      range "1000..1000 | 3000..3000 | 5000..5000 | 10000..10000 | 15000..15000 | 20000..20000 | 30000..30000";
    }
  }
  typedef ddt-Lrat_EUtranCellFDD_hoOptAdjThresholdPerc {
    type int32 {
      range 0..1000;
    }
  }
  typedef ddt-Lrat_EUtranCellTDD_freqBand {
    type int32 {
      range 1..256;
    }
  }
  typedef ddt-Lrat_EUtranCellFDD_longitude {
    type int32 {
      range -180000000..180000000;
    }
  }
  typedef ddt-Lrat_ReportConfigEUtraIntraFreqPm_a4ThresholdRsrqPm {
    type int32 {
      range -195..-30;
    }
  }
  typedef ddt-Lrat_EUtranCellFDD_lbEUtranTriggerOffloadThreshold {
    type int32 {
      range 0..1600;
    }
  }
  typedef ddt-Lrat_EUtranCellTDD_noOfPucchFormat3PrbPairsPerFrame {
    type int32 {
      range 0..1000;
    }
  }
  typedef ddt-Lrat_EUtranCellFDD_qQualMinRsrqCe {
    type int32 {
      range "-34..-3 | 0..0";
    }
  }
  typedef ddt-Lrat_EUtranCellRelation_covCellRrcConnWakeUpThreshold {
    type int32 {
      range 0..3000;
    }
  }
  typedef ddt-Lrat_ReportConfigCsfbCdma2000_timeToTrigger {
    type int32 {
      range "0..0 | 40..40 | 64..64 | 80..80 | 100..100 | 128..128 | 160..160 | 256..256 | 320..320 | 480..480 | 640..640 | 1024..1024 | 1280..1280 | 2560..2560 | 5120..5120";
    }
  }
  typedef ddt-Lrat_Rcs_tInactivityTimer {
    type int32 {
      range "0..0 | 10..86400";
    }
  }
  typedef ddt-Lrat_CarrierAggregationFunction_caRateAdjustCoeff {
    type int32 {
      range 0..10;
    }
  }
  typedef ddt-Lrat_ReportConfigEUtraBestCellAnr_hysteresisA3 {
    type int32 {
      range 0..150;
    }
  }
  typedef ddt-Lrat_ExternalUtranCellTDD_rac {
    type int32 {
      range -1..255;
    }
  }
  typedef ddt-Lrat_ENodeBFunction_s1RetryTimer {
    type int32 {
      range 1..300;
    }
  }
  typedef ddt-Lrat_EUtranCellFDD_qQualMinOffset {
    type int32 {
      range 0..8;
    }
  }
  typedef ddt-Lrat_SIB3_tHystNormal {
    type int32 {
      range "30..30 | 60..60 | 120..120 | 180..180 | 240..240";
    }
  }
  typedef ddt-Lrat_ExternalCdma2000Cell_pnOffset {
    type int32 {
      range 0..511;
    }
  }
  typedef ddt-Lrat_EUtranCellTDD_noOfPucchFormat3PrbPairs {
    type int32 {
      range 0..3;
    }
  }
  typedef ddt-Lrat_EUtranCellFDD_physicalLayerCellId {
    type int32 {
      range 0..503;
    }
  }
  typedef ddt-Lrat_Band46UnlicensedProfile_b46D53340MaxPower {
    type int32 {
      range 0..30;
    }
  }
  typedef ddt-Lrat_EUtranCellTDD_emergencyAreaId {
    type int32 {
      range -1..16777215;
    }
  }
  typedef ddt-Lrat_ExternalCdma20001xRttCell_userLabel {
    type string {
      length 1..128;
    }
  }
  typedef ddt-Lrat_ENodeBFunction_maxRandc {
    type int32 {
      range 2..255;
    }
  }
  typedef ddt-Lrat_ReportConfigEUtraIFBestCell_timeToTriggerA3 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_channelSelectionSetSize {
    type int32 {
      range 1..2;
    }
  }
  typedef ddt-Lrat_InterNodalProtocolVerRO_commonProtVerRelMinus3 {
    type int32 {
      range -1..2147483647;
    }
  }
  typedef ddt-Lrat_ENodeBFunction_timePhaseMaxDeviationTdd {
    type int32 {
      range 9..100;
    }
  }
  typedef ddt-Lrat_Band46UnlicensedProfile_b46A47090MaxPower {
    type int32 {
      range 0..30;
    }
  }
  typedef ddt-Lrat_TermPointToGNB_domainName {
    type string {
      length 0..255;
    }
  }
  typedef ddt-Lrat_InterNodalProtocolVerRO_commonProtVerRelMinus2 {
    type int32 {
      range -1..2147483647;
    }
  }
  typedef ddt-Lrat_EUtranCellTDD_hpueCaSwitchThres {
    type int32 {
      range -150..450;
    }
  }
  typedef ddt-Lrat_InterNodalProtocolVerRO_commonProtVerRelMinus1 {
    type int32 {
      range -1..2147483647;
    }
  }
  typedef ddt-Lrat_EUtranCellFDD_ttiBundlingSwitchThresHyst {
    type int32 {
      range 0..50;
    }
  }
  typedef ddt-Lrat_ExternalUtranCellTDD_physicalCellIdentity {
    type int32 {
      range 0..127;
    }
  }
  typedef ddt-Lrat_CarrierAggregationFunction_caPreemptionThreshold {
    type int32 {
      range 0..100;
    }
  }
  typedef ddt-Lrat_ParameterChangeRequestRO_attributeName {
    type string {
      length 0..32;
    }
  }
  typedef ddt-Lrat_NbIotFrequencyInfo_qRxLevMin {
    type int32 {
      range -156..-44;
    }
  }
  typedef ddt-Lrat_LoadBalancingFunction_lbEUtranOffloadBackoffTime {
    type int32 {
      range 30..600;
    }
  }
  typedef ddt-Lrat_ReportConfigElcA1A2_a1a2ThresholdRsrp {
    type int32 {
      range -140..-44;
    }
  }
  typedef ddt-Lrat_EUtranFreqRelation_timeOfLastModification {
    type string {
      length 0..19;
    }
  }
  typedef ddt-Lrat_PtmStmConfig_inhibitImpInterval {
    type int32 {
      range 15..3600;
    }
  }
  typedef ddt-Lrat_EUtranCellFDD_ulFrequencyAllocationProportion {
    type int32 {
      range 0..100;
    }
  }
  typedef ddt-Lrat_ReportConfigB2UtraUlTrig_b2Threshold2EcNoUtra {
    type int32 {
      range -240..0;
    }
  }
  typedef ddt-Lrat_CellSleepFunction_covCellRrcReestWakeUpThr {
    type int32 {
      range 0..100;
    }
  }
  typedef ddt-Lrat_CarrierAggregationFunction_sCellActDeactUlDataThresh {
    type int32 {
      range 0..5000;
    }
  }
  typedef ddt-Lrat_CandNeighborRelInfoRO_mncLength {
    type int32 {
      range 2..3;
    }
  }
  typedef ddt-Lrat_EUtranCellFDD_qRxLevMin {
    type int32 {
      range -140..-44;
    }
  }
  typedef ddt-Lrat_EUtranCellTDD_alpha {
    type int32 {
      range "0..0 | 4..4 | 5..5 | 6..6 | 7..7 | 8..8 | 9..9 | 10..10";
    }
  }
  typedef ddt-Lrat_EUtranCellFDD_dynUeAdmCtrlFilterConst {
    type int32 {
      range 0..10000;
    }
  }
  typedef ddt-Lrat_EUtranCellTDD_cellCapMinCellSubCap {
    type int32 {
      range 0..1000000;
    }
  }
  typedef ddt-Lrat_UtranFreqRelation_userLabel {
    type string {
      length 1..128;
    }
  }
  typedef ddt-Lrat_SignalingRadioBearer_tReorderingDl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-Lrat_InstantUplinkAccess_iuaDuration {
    type int32 {
      range 5..10000;
    }
  }
  typedef ddt-Lrat_B2UtranPCOffsetMCPC_b2Thr1RsrqUtranPCOffset {
    type int32 {
      range -240..240;
    }
  }
  typedef ddt-Lrat_SectorCarrier_maximumTransmissionPower {
    type int32 {
      range -1..1200;
    }
  }
  typedef ddt-Lrat_EUtranCellFDD_puschFrequencyAllocationBr {
    type int32 {
      range 0..1;
    }
  }
  typedef ddt-Lrat_ExternalGeranCell_ncc {
    type int32 {
      range 0..7;
    }
  }
  typedef ddt-Lrat_EUtranFreqToQciProfileRelation_a5Thr2RsrqFreqQciOffset {
    type int32 {
      range -240..240;
    }
  }
  typedef ddt-Lrat_EUtranCellFDD_prsPowerBoosting {
    type int32 {
      range 0..3;
    }
  }
  typedef ddt-Lrat_ExternalCdma2000Cell_userLabel {
    type string {
      length 1..128;
    }
  }
  typedef ddt-Lrat_EUtranCellTDD_pdcchOuterLoopInitialAdjPCell {
    type int32 {
      range -200..200;
    }
  }
  typedef ddt-Lrat_EUtranCellTDD_hoOptAdjThresholdPercQci1 {
    type int32 {
      range 0..1000;
    }
  }
  typedef ddt-Lrat_LoadBalancingFunction_lbRateOffsetCoefficient {
    type int32 {
      range 0..1000;
    }
  }
  typedef ddt-Lrat_Cdma20001xRttFreqRelation_qOffsetFreq {
    type int32 {
      range -15..15;
    }
  }
  typedef ddt-Lrat_EUtranCellFDD_timeOfLastModification {
    type string {
      length 0..19;
    }
  }
  typedef ddt-Lrat_EUtranCellTDD_hpueCaSwitchHyst {
    type int32 {
      range 0..150;
    }
  }
  typedef ddt-Lrat_EUtranCellFDD_pdcchOuterLoopInitialAdjVolte {
    type int32 {
      range -200..200;
    }
  }
  typedef ddt-Lrat_EUtranCellTDD_eranUlCompUserSelSinrThr {
    type int32 {
      range -150..400;
    }
  }
  typedef ddt-Lrat_CarrierAggregationFunction_waitForBlindSelSCellRepLessTtt {
    type int32 {
      range 0..10000;
    }
  }
  typedef ddt-Lrat_ENodeBFunction_x2retryTimerMaxAuto {
    type int32 {
      range 0..60000;
    }
  }
  typedef ddt-Lrat_ReportConfigA5SoftLock_a5Threshold2Rsrp {
    type int32 {
      range -140..-44;
    }
  }
  typedef ddt-Lrat_EUtranCellFDD_rachRootSequence {
    type int32 {
      range 0..837;
    }
  }
  typedef ddt-Lrat_EUtranCellTDD_dlMaxMuMimoLayers {
    type int32 {
      range "0..0 | 2..2 | 4..4 | 6..6 | 8..8 | 10..10 | 12..12 | 14..14 | 16..16";
    }
  }
  typedef ddt-Lrat_AdmissionControl_nrOfRbReservationsPerPaConn {
    type int32 {
      range 0..10;
    }
  }
  typedef ddt-Lrat_ExternalEUtranCellTDD_activeServiceAreaId {
    type int32 {
      range 0..65535;
    }
  }
  typedef ddt-Lrat_ENodeBFunction_softLockRwRWaitTimerOperator {
    type int32 {
      range 20..80;
    }
  }
  typedef ddt-Lrat_B2GeranPCOffsetMCPC_b2Thr1RsrpGeranPCOffset {
    type int32 {
      range -100..100;
    }
  }
  typedef ddt-Lrat_NbIotCell_gbPrbIndexDl {
    type int32 {
      range "-1..-1 | 1..1";
    }
  }
  typedef ddt-Lrat_EUtranCellTDD_harqOffsetDl {
    type int32 {
      range -20..20;
    }
  }
  typedef ddt-Lrat_AnrFunctionGeran_anrGeranMeasReportIncr {
    type int32 {
      range 0..1000;
    }
  }
  typedef ddt-Lrat_ENodeBFunction_s1GtpuEchoDscp {
    type int32 {
      range 0..63;
    }
  }
  typedef ddt-Lrat_MdtConfiguration_hysteresisA2Mdt {
    type int32 {
      range 0..150;
    }
  }
  typedef ddt-Lrat_CandNeighborRelInfoRO_physicalLayerCellIdGroup {
    type int32 {
      range 0..167;
    }
  }
  typedef ddt-Lrat_EUtranCellFDD_ulInternalChannelBandwidth {
    type int32 {
      range "0..0 | 4200..4200 | 4400..4400 | 4600..4600 | 4800..4800 | 9000..9000";
    }
  }
  typedef ddt-Lrat_AnrFunctionUtran_anrUtranMeasReportAcIncr {
    type int32 {
      range 0..1000;
    }
  }
  typedef ddt-Lrat_BandCombCompression_requestMaxCCsUL {
    type int32 {
      range 0..32;
    }
  }
  typedef ddt-Lrat_ExternalUtranCellFDD_timeOfCreation {
    type string {
      length 0..19;
    }
  }
  typedef ddt-Lrat_EUtranCellFDD_pucchOverdimensioning {
    type int32 {
      range 0..49;
    }
  }
  typedef ddt-Lrat_ReportConfigEUtraBestCell_timeToTriggerA3 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_harqOffsetDl {
    type int32 {
      range -20..20;
    }
  }
  typedef ddt-Lrat_CarrierAggregationFunction_sCellActDeactProhibitTimer {
    type int32 {
      range 0..5000;
    }
  }
  typedef ddt-Lrat_PrefTrafficMgmt_plmnResOpUseSRatioThreshold {
    type int32 {
      range 0..1600;
    }
  }
  typedef ddt-Lrat_EUtranCellTDD_pZeroNominalPucch {
    type int32 {
      range -127..-96;
    }
  }
  typedef ddt-Lrat_CarrierAggregationFunction_laaSCellActDeactProhibitTimer {
    type int32 {
      range 0..5000;
    }
  }
  typedef ddt-Lrat_MeasCellGroup_groupPrbUnit {
    type int32 {
      range 1..600;
    }
  }
  typedef ddt-Lrat_ExternalUtranCellFDD_lac {
    type int32 {
      range "0..65533 | 65535..65535";
    }
  }
  typedef ddt-Lrat_EUtranCellTDD_ulConfigurableFrequencyStart {
    type int32 {
      range 0..100;
    }
  }
  typedef ddt-Lrat_PmchMch_syncSequenceLength {
    type int32 {
      range "8..8 | 16..16 | 32..32 | 64..64 | 128..128 | 256..256 | 512..512 | 1024..1024";
    }
  }
  typedef ddt-Lrat_Tmgi_serviceId {
    type int32 {
      range 0..16777215;
    }
  }
  typedef ddt-Lrat_ExternalEUtranCellFDD_activeServiceAreaId {
    type int32 {
      range 0..65535;
    }
  }
  typedef ddt-Lrat_EUtranFreqRelationUnlicensed_caFreqProportion {
    type int32 {
      range 0..100;
    }
  }
  typedef ddt-Lrat_SIB8_tReselectionCdmaHrpdSfMedium {
    type int32 {
      range 25..100;
    }
  }
  typedef ddt-Lrat_ExternalGeranCell_timeOfLastModification {
    type string {
      length 0..19;
    }
  }
  typedef ddt-Lrat_EUtranFreqRelation_connectedModeMobilityPrio {
    type int32 {
      range -1..7;
    }
  }
  typedef ddt-Lrat_GUGroupIdRO_mcc {
    type int32 {
      range 0..999;
    }
  }
  typedef ddt-Lrat_EUtranFreqRelation_tReselectionEutraCe {
    type int32 {
      range 0..15;
    }
  }
  typedef ddt-Lrat_EutranCellArea_posCellBearing {
    type int32 {
      range -1..3599;
    }
  }
  typedef ddt-Lrat_NbIotCell_qRxLevMin {
    type int32 {
      range -156..-44;
    }
  }
  typedef ddt-Lrat_AirIfLoadProfile_dlPrbLoadLevel {
    type int32 {
      range 0..100;
    }
  }
  typedef ddt-Lrat_Band46UnlicensedProfile_b46C50290MaxPower {
    type int32 {
      range 0..30;
    }
  }
  typedef ddt-Lrat_AcBarringConfig1xRtt_acBarring14R9 {
    type int32 {
      range 0..7;
    }
  }
  typedef ddt-Lrat_CellSleepFunction_sleepStartTime {
    type string {
      length 5..5;
    }
  }
  typedef ddt-Lrat_Cdma2000FreqRelQciB2ThrOffsets_b2Thr2Cdma2000FreqQciOffset {
    type int32 {
      range -250..250;
    }
  }
  typedef ddt-Lrat_SIB8_tReselectionCdmaHrpd {
    type int32 {
      range 0..7;
    }
  }
  typedef ddt-Lrat_EUtranCellTDD_hoOptAdjThresholdPerc {
    type int32 {
      range 0..1000;
    }
  }
  typedef ddt-Lrat_TermPointToSGW_timeOfCreation {
    type string {
      length 0..19;
    }
  }
  typedef ddt-Lrat_LoadBalancingFunction_lbThreshold {
    type int32 {
      range 0..1000;
    }
  }
  typedef ddt-Lrat_EUtranCellFDD_noOfUlImprovedUe {
    type int32 {
      range 0..5;
    }
  }
  typedef ddt-Lrat_EUtranCellFDD_noOfChannelSelectionSets {
    type int32 {
      range "0..0 | 4..12";
    }
  }
  typedef ddt-Lrat_MultipleNSPmaxReqMapping_additionalFreqBand {
    type int32 {
      range 1..256;
    }
  }
  typedef ddt-Lrat_ReportConfigCsfbCdma2000_thresholdCdma20001xRtt {
    type int32 {
      range -315..0;
    }
  }
  typedef ddt-Lrat_PtmIflbConfig_stopIncomingIflbThreshold {
    type int32 {
      range 0..1600;
    }
  }
  typedef ddt-Lrat_MbsfnSubframeConfigRO_subframeAllocationFourFrame {
    type string {
      length 24..24;
    }
  }
  typedef ddt-Lrat_BandClassPrioCDMA2000_cellReselectionPriority {
    type int32 {
      range "-1000..-1000 | 0..7";
    }
  }
  typedef ddt-Lrat_AdmissionControl_admNrRbDifferentiationThr {
    type int32 {
      range 0..1000;
    }
  }
  typedef ddt-Lrat_EUtranCellFDD_noOfPucchCqiUsers {
    type int32 {
      range 0..4000;
    }
  }
  typedef ddt-Lrat_EUtranCellTDD_prsMutingPattern {
    type string {
      length 1..16;
    }
  }
  typedef ddt-Lrat_LoadBasedCaMsrThr_dlPrbUtilThreshLow {
    type int32 {
      range 0..100;
    }
  }
  typedef ddt-Lrat_UtranFreqRelation_csFallbackPrioEC {
    type int32 {
      range -1..7;
    }
  }
  typedef ddt-Lrat_ENodeBFunction_ulBbCapacityNet {
    type int32 {
      range "-1..-1 | 0..65535";
    }
  }
  typedef ddt-Lrat_CellSleepFunction_covCellUeCtxtRelMin {
    type int32 {
      range 0..100000;
    }
  }
  typedef ddt-Lrat_ExternalENodeBFunction_userLabel {
    type string {
      length 1..128;
    }
  }
  typedef ddt-Lrat_PreschedulingProfile_preschedulingDataSize {
    type int32 {
      range 1..5000;
    }
  }
  typedef ddt-Lrat_GeranFrequency_userLabel {
    type string {
      length 1..128;
    }
  }
  typedef ddt-Lrat_Cdma2000FreqRelQciB2ThrOffsets_b2Thr1RsrqCdma2000FreqQciOffset {
    type int32 {
      range -240..240;
    }
  }
  typedef ddt-Lrat_Rrc_t311NbIot {
    type int32 {
      range "1000..1000 | 3000..3000 | 5000..5000 | 10000..10000 | 15000..15000 | 20000..20000 | 30000..30000";
    }
  }
  typedef ddt-Lrat_UtranTDDFreqRelation_threshXLow {
    type int32 {
      range 0..62;
    }
  }
  typedef ddt-Lrat_EUtranCellFDD_rtpTimeout {
    type int32 {
      range 1..15;
    }
  }
  typedef ddt-Lrat_SciProfile_ulRelativePriority {
    type int32 {
      range 1..65535;
    }
  }
  typedef ddt-Lrat_ReportConfigEUtraIntraFreqPm_reportAmountPm {
    type int32 {
      range "0..0 | 1..1 | 2..2 | 4..4 | 8..8 | 16..16 | 32..32 | 64..64";
    }
  }
  typedef ddt-Lrat_ExternalENodeBFunction_eSCellCapacityScaling {
    type int32 {
      range 0..100;
    }
  }
  typedef ddt-Lrat_PrefTrafficMgmt_plmnUnresOpUseMsrUsageThreshold {
    type int32 {
      range 0..100;
    }
  }
  typedef ddt-Lrat_EUtranCellFDD_dlPowerRatio {
    type int32 {
      range 10..100;
    }
  }
  typedef ddt-Lrat_ExternalEUtranCellTDD_physicalLayerCellIdGroup {
    type int32 {
      range 0..167;
    }
  }
  typedef ddt-Lrat_LoadBalancingFunction_lbCeiling {
    type int32 {
      range 10..2000;
    }
  }
  typedef ddt-Lrat_PmEventService_totalEventStorageSize {
    type int32 {
      range 0..266000;
    }
  }
  typedef ddt-Lrat_EUtranCellTDD_ns05PathlossOffsetThres {
    type int32 {
      range 0..1000;
    }
  }
  typedef ddt-Lrat_PreschedProfile_preschedulingDataSize {
    type int32 {
      range 1..5000;
    }
  }
  typedef ddt-Lrat_BearerTriggerElement_qci {
    type int32 {
      range 0..9;
    }
  }
  typedef ddt-Lrat_GUtranSyncSignalFrequency_arfcn {
    type int32 {
      range 0..3279165;
    }
  }
  typedef ddt-Lrat_UtranTDDFreqRelation_userLabel {
    type string {
      length 1..128;
    }
  }
  typedef ddt-Lrat_EUtranCellFDD_commonSrPeriodicity {
    type int32 {
      range "5..5 | 10..10 | 20..20";
    }
  }
  typedef ddt-Lrat_SubFrameConfigRO_subframeAllocation {
    type int32 {
      range "1..1 | 4..4";
    }
  }
  typedef ddt-Lrat_EUtranCellTDD_uncertSemiMajor {
    type int32 {
      range 0..127;
    }
  }
  typedef ddt-Lrat_ReportConfigA5UlTrig_hysteresisA5 {
    type int32 {
      range 0..150;
    }
  }
  typedef ddt-Lrat_ExternalEUtranCellFDD_userLabel {
    type string {
      length 1..128;
    }
  }
  typedef ddt-Lrat_EUtranCellTDD_preambleInitialReceivedTargetPower {
    type int32 {
      range -120..-90;
    }
  }
  typedef ddt-Lrat_PmFlexCounterFilter_qciFilterMax {
    type int32 {
      range 0..255;
    }
  }
  typedef ddt-Lrat_FreqPrioEUTRA_arpPrio {
    type int32 {
      range -1..7;
    }
  }
  typedef ddt-Lrat_AnrFunctionEUtran_anrUesEUtraIntraFMax {
    type int32 {
      range 0..100;
    }
  }
  typedef ddt-Lrat_ReportConfigEUtraIFBestCell_a3offset {
    type int32 {
      range -150..150;
    }
  }
  typedef ddt-Lrat_ReportConfigB2Utra_timeToTriggerB2Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_catmMbmsDlSubframes {
    type int32 {
      range 0..2;
    }
  }
  typedef ddt-Lrat_EUtranCellFDD_emergencyAreaId {
    type int32 {
      range -1..16777215;
    }
  }
  typedef ddt-Lrat_SubscriberGroupProfile_pZeroNominalPucchOffset {
    type int32 {
      range -10..20;
    }
  }
  typedef ddt-Lrat_Paging_pagingDiscardTimerNb {
    type int32 {
      range 1..60;
    }
  }
  typedef ddt-Lrat_TacSvAndSnRange_tac {
    type int32 {
      range "-1..-1 | 0..99999999";
    }
  }
  typedef ddt-Lrat_EUtranCellTDD_specialSubframePattern {
    type int32 {
      range 5..7;
    }
  }
  typedef ddt-Lrat_Cdma2000FreqBandRelation_threshXLowHrpd {
    type int32 {
      range 0..63;
    }
  }
  typedef ddt-Lrat_ReportConfigCsfbGeran_hysteresis {
    type int32 {
      range 0..150;
    }
  }
  typedef ddt-Lrat_EUtranCellFDD_prioAdditionalFreqBandList {
    type int32 {
      range 1..256;
    }
  }
  typedef ddt-Lrat_Cdma20001xRttFreqRelation_b2Thr2Cdma20001xFreqOffset {
    type int32 {
      range -250..250;
    }
  }
  typedef ddt-Lrat_CellSleepNodeFunction_csmMinHitRateForCovCell {
    type int32 {
      range 0..50;
    }
  }
  typedef ddt-Lrat_AirIfLoadProfile_noOfOcngPrbSeries {
    type int32 {
      range 1..10;
    }
  }
  typedef ddt-Lrat_EUtranCellFDD_hoOptAdjThresholdAbsQci1 {
    type int32 {
      range 0..32767;
    }
  }
  typedef ddt-Lrat_QciProfileOperatorDefined_userLabel {
    type string {
      length 1..128;
    }
  }
  typedef ddt-Lrat_InstantUplinkAccess_iuaLoadThreshold {
    type int32 {
      range 1..100;
    }
  }
  typedef ddt-Lrat_NbIotIntraFrequencyInfo_qQualMin {
    type int32 {
      range "-34..-3 | 0..0";
    }
  }
  typedef ddt-Lrat_AcBarringConfig1xRtt_acBarringRegR9 {
    type int32 {
      range 0..7;
    }
  }
  typedef ddt-Lrat_CandNeighborRelInfoRO_tac {
    type int32 {
      range 0..65535;
    }
  }
  typedef ddt-Lrat_QciProfileOperatorDefined_priority {
    type int32 {
      range 0..14;
    }
  }
  typedef ddt-Lrat_CellPortion_latitude {
    type int32 {
      range -90000000..90000000;
    }
  }
  typedef ddt-Lrat_EUtranCellRelation_covCellWakeupMonitorDurTimer {
    type int32 {
      range 5..120;
    }
  }
  typedef ddt-Lrat_Band46UnlicensedProfile_b46B48490MaxPower {
    type int32 {
      range 0..30;
    }
  }
  typedef ddt-Lrat_EUtranCellTDD_lbEUtranAcceptOffloadThreshold {
    type int32 {
      range 0..1600;
    }
  }
  typedef ddt-Lrat_EUtranCellTDD_deallocTimerPucchFormat1 {
    type int32 {
      range 0..36000;
    }
  }
  typedef ddt-ExternalEUtranCellTDD_changeFrequency_earfcn {
    type int32 {
      range 36000..262143;
    }
  }
  typedef ddt-Lrat_ENodeBFunction_licUlPrbPercentileConf {
    type int32 {
      range 1..100;
    }
  }
  typedef ddt-Lrat_CellSleepFunction_capCellMobReasNotSleepThr {
    type int32 {
      range -1..10000;
    }
  }
  typedef ddt-Lrat_AnrFunction_prioTime {
    type int32 {
      range 0..100;
    }
  }
  typedef ddt-Lrat_EUtranCellFDD_dlPowerRampUpRate {
    type int32 {
      range 1..10;
    }
  }
  typedef ddt-Lrat_EUtranCellTDD_pdcchOuterLoopUpStepPCell {
    type int32 {
      range 0..100;
    }
  }
  typedef ddt-Lrat_ExternalEUtranCellFDD_dlChannelBandwidth {
    type int32 {
      range "0..0 | 1400..1400 | 3000..3000 | 5000..5000 | 10000..10000 | 15000..15000 | 20000..20000";
    }
  }
  typedef ddt-Lrat_UnlicensedAccessFunction_laaLbtSuccessRateThreshold {
    type int32 {
      range 10..90;
    }
  }
  typedef ddt-Lrat_PtmResOpUseConfig_resMsrUsageThreshold {
    type int32 {
      range 0..100;
    }
  }
  typedef ddt-Lrat_DataRadioBearer_tPollRetransmitDl {
    type int32 {
      range "5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500";
    }
  }
  typedef ddt-Lrat_EUtranCellFDD_initialBufferSizeDefault {
    type int32 {
      range 1..10000;
    }
  }
  typedef ddt-Lrat_EUtranCellFDD_pdcchTargetBlerPCell {
    type int32 {
      range 1..200;
    }
  }
  typedef ddt-Lrat_LoadBasedCaMsrThr_dlSeUtilThreshHigh {
    type int32 {
      range 0..100;
    }
  }
  typedef ddt-Lrat_EUtranCellRelation_cellIndividualOffsetEUtranQci1 {
    type int32 {
      range "-24..-24 | -22..-22 | -20..-20 | -18..-18 | -16..-16 | -14..-14 | -12..-12 | -10..-10 | -8..-8 | -6..-6 | -5..-5 | -4..-4 | -3..-3 | -2..-2 | -1..-1 | 0..0 | 1..1 | 2..2 | 3..3 | 4..4 | 5..5 | 6..6 | 8..8 | 10..10 | 12..12 | 14..14 | 16..16 | 18..18 | 20..20 | 22..22 | 24..24";
    }
  }
  typedef ddt-Lrat_ExternalEUtranCellTDD_localCellId {
    type int32 {
      range 0..255;
    }
  }
  typedef ddt-Lrat_NbIotCell_modificationPeriodCoeff {
    type int32 {
      range "16..16 | 32..32 | 64..64 | 128..128";
    }
  }
  typedef ddt-Lrat_UeMeasControl_filterCoefficientRscpUtra {
    type int32 {
      range "0..0 | 1..1 | 2..2 | 3..3 | 4..4 | 5..5 | 6..6 | 7..7 | 8..8 | 9..9 | 11..11 | 13..13 | 15..15 | 17..17 | 19..19";
    }
  }
  typedef ddt-Lrat_ReportConfigCsg_a5Thr2RsrpAltCsgOffset {
    type int32 {
      range -100..100;
    }
  }
  typedef ddt-Lrat_GUtranSyncSignalFrequency_gscn {
    type int32 {
      range 1..28557;
    }
  }
  typedef ddt-Lrat_ENodeBFunction_ulBbCapacityMaxLimit {
    type int32 {
      range "-1..-1 | 0..65535";
    }
  }
  typedef ddt-Lrat_ReportConfigEUtraIntraFreqPm_a3OffsetPm {
    type int32 {
      range -150..150;
    }
  }
  typedef ddt-Lrat_MimoSleepFunction_switchDownRrcConnThreshold {
    type int32 {
      range 0..500;
    }
  }
  typedef ddt-Lrat_Cdma2000Freq_userLabel {
    type string {
      length 1..128;
    }
  }
  typedef ddt-Lrat_ExternalEUtranCellFDD_additionalFreqBandList {
    type int32 {
      range 1..256;
    }
  }
  typedef ddt-Lrat_EUtranCellTDD_altitude {
    type int32 {
      range -32768..32767;
    }
  }
  typedef ddt-Lrat_AnrFunctionEUtran_lbCellOffloadCapacityPolicy {
    type int32 {
      range 0..1000000;
    }
  }
  typedef ddt-Lrat_NbIotCell_sIntraSearchThreshold {
    type int32 {
      range 0..62;
    }
  }
  typedef ddt-Lrat_ReportConfigSearch_a2CriticalThresholdRsrq {
    type int32 {
      range -195..-30;
    }
  }
  typedef ddt-Lrat_EUtranCellTDD_subframeAssignment {
    type int32 {
      range "1..1 | 2..2";
    }
  }
  typedef ddt-Lrat_BandClassPrioCdma1xRtt_freqCdma {
    type int32 {
      range "-1000..-1000 | 0..2047";
    }
  }
  typedef ddt-Lrat_Rrc_tRrcConnReest {
    type int32 {
      range 1..20;
    }
  }
  typedef ddt-Lrat_PmFlexCounterFilter_subscriberGroupFilterMax {
    type int32 {
      range 0..4;
    }
  }
  typedef ddt-Lrat_CarrierAggregationFunction_sCellScheduleSinrThres {
    type int32 {
      range -200..300;
    }
  }
  typedef ddt-Lrat_EUtranCellTDD_hoOptStatNumQci1 {
    type int32 {
      range 1..32767;
    }
  }
  typedef ddt-Lrat_BbLink_vlanId {
    type int32 {
      range 1..4094;
    }
  }
  typedef ddt-Lrat_BandClassPrioCDMA2000_freqCdma {
    type int32 {
      range "-1000..-1000 | 0..2047";
    }
  }
  typedef ddt-Lrat_EUtranCellFDD_cellId {
    type int32 {
      range 0..255;
    }
  }
  typedef ddt-Lrat_ReportConfigSearch_a2CriticalThresholdRsrp {
    type int32 {
      range -140..-44;
    }
  }
  typedef ddt-Lrat_SignalingRadioBearer_dlMaxRetxThreshold {
    type int32 {
      range "1..1 | 2..2 | 3..3 | 4..4 | 6..6 | 8..8 | 16..16 | 32..32";
    }
  }
  typedef ddt-Lrat_ReportConfigSearch_hysteresisA2CriticalRsrq {
    type int32 {
      range 0..150;
    }
  }
  typedef ddt-Lrat_ReportConfigSearch_hysteresisA2CriticalRsrp {
    type int32 {
      range 0..150;
    }
  }
  typedef ddt-Lrat_QciProfilePredefined_tReorderingUl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-Lrat_Cdma2000FreqBandRelation_threshXHighHrpd {
    type int32 {
      range 0..63;
    }
  }
  typedef ddt-Lrat_ReportConfigB2UtraUlTrig_hysteresisB2 {
    type int32 {
      range 0..150;
    }
  }
  typedef ddt-Lrat_Mbms_synchPeriodLength {
    type int32 {
      range 0..593920;
    }
  }
  typedef ddt-Lrat_PrefTrafficMgmt_inhibitSpidList {
    type int32 {
      range 1..256;
    }
  }
  typedef ddt-Lrat_SIPeriodicityNB_siPeriodicitySI2 {
    type int32 {
      range "64..64 | 128..128 | 256..256 | 512..512 | 1024..1024 | 2048..2048 | 4096..4096";
    }
  }
  typedef ddt-Lrat_LoadBalancingFunction_lbHitRateUtranMeasUeThreshold {
    type int32 {
      range 1..1000;
    }
  }
  typedef ddt-Lrat_MeasReportConfigParams_b2Threshold2RscpUtraOffset {
    type int32 {
      range -24..24;
    }
  }
  typedef ddt-Lrat_SIPeriodicityNB_siPeriodicitySI1 {
    type int32 {
      range "64..64 | 128..128 | 256..256 | 512..512 | 1024..1024 | 2048..2048 | 4096..4096";
    }
  }
  typedef ddt-Lrat_AnrFunctionEUtran_anrUesThreshInterFDecr {
    type int32 {
      range 0..1000;
    }
  }
  typedef ddt-Lrat_TermPointToENB_eRanCaProtVerActive {
    type int32 {
      range -1..2147483647;
    }
  }
  typedef ddt-Lrat_SIPeriodicityNB_siPeriodicitySI6 {
    type int32 {
      range "64..64 | 128..128 | 256..256 | 512..512 | 1024..1024 | 2048..2048 | 4096..4096";
    }
  }
  typedef ddt-Lrat_ReportConfigA5Anr_a5Threshold1RsrqAnrDelta {
    type int32 {
      range -10..10;
    }
  }
  typedef ddt-Lrat_SIPeriodicityNB_siPeriodicitySI5 {
    type int32 {
      range "64..64 | 128..128 | 256..256 | 512..512 | 1024..1024 | 2048..2048 | 4096..4096";
    }
  }
  typedef ddt-Lrat_EUtranCellRelation_crsAssistanceInfoPriority {
    type int32 {
      range 0..100;
    }
  }
  typedef ddt-Lrat_SIPeriodicityNB_siPeriodicitySI4 {
    type int32 {
      range "64..64 | 128..128 | 256..256 | 512..512 | 1024..1024 | 2048..2048 | 4096..4096";
    }
  }
  typedef ddt-Lrat_SIPeriodicityNB_siPeriodicitySI3 {
    type int32 {
      range "64..64 | 128..128 | 256..256 | 512..512 | 1024..1024 | 2048..2048 | 4096..4096";
    }
  }
  typedef ddt-Lrat_CellResource_spidList {
    type int32 {
      range 0..256;
    }
  }
  typedef ddt-Lrat_UnlicensedAccessFunction_laaChannelEvaluationTimer {
    type int32 {
      range 1..1500;
    }
  }
  typedef ddt-Lrat_CellIdentityUtra_rncId {
    type int32 {
      range 1..4095;
    }
  }
  typedef ddt-Lrat_SIPeriodicityNB_siPeriodicitySI7 {
    type int32 {
      range "64..64 | 128..128 | 256..256 | 512..512 | 1024..1024 | 2048..2048 | 4096..4096";
    }
  }
  typedef ddt-Lrat_MeasReportConfigParams_timeToTriggerIntraA3 {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_ReportConfigEUtraInterFreqPm_a4ThresholdRsrpPm {
    type int32 {
      range -140..-44;
    }
  }
  typedef ddt-Lrat_UeMeasControl_targetA2UlSearchOffset {
    type int32 {
      range -150..150;
    }
  }
  typedef ddt-Lrat_EndcProfile_userLabel {
    type string {
      length 1..128;
    }
  }
  typedef ddt-Lrat_EUtranCellTDD_dynCellSubscrCap {
    type int32 {
      range 0..1000000;
    }
  }
  typedef ddt-Lrat_UtranFreqRelation_qRxLevMin {
    type int32 {
      range -119..-25;
    }
  }
  typedef ddt-Lrat_EUtranCellFDD_confidence {
    type int32 {
      range 0..100;
    }
  }
  typedef ddt-Lrat_EUtranCellTDD_cbrsTxExpireTime {
    type string {
      length 0..31;
    }
  }
  typedef ddt-Lrat_EUtranCellFDD_cceDynUeAdmCtrlRetDiffThr {
    type int32 {
      range 0..1000;
    }
  }
  typedef ddt-Lrat_EUtranCellTDD_noOfCrsPorts {
    type int32 {
      range "-1..-1 | 1..1 | 2..2 | 4..4";
    }
  }
  typedef ddt-Lrat_SubFrameConfig_sfAllocationOneFrame {
    type int32 {
      range 0..63;
    }
  }
  typedef ddt-Lrat_EUtranCellTDD_hoOptAdjThresholdAbs {
    type int32 {
      range 0..32767;
    }
  }
  typedef ddt-Lrat_GeranFreqGroupRelation_connectedModeMobilityPrio {
    type int32 {
      range -1..7;
    }
  }
  typedef ddt-Lrat_MSCid_switchNumber {
    type int32 {
      range 0..255;
    }
  }
  typedef ddt-Lrat_ReportConfigSCellA4_hysteresisA4 {
    type int32 {
      range 0..150;
    }
  }
  typedef ddt-Lrat_ExternalEUtranCellFDD_timeOfCreation {
    type string {
      length 0..19;
    }
  }
  typedef ddt-Lrat_EUtranCellFDD_dlPowerRampUpInitialRatio {
    type int32 {
      range 10..100;
    }
  }
  typedef ddt-Lrat_ParameterChangeRequestRO_causeString {
    type string {
      length 0..100;
    }
  }
  typedef ddt-Lrat_EUtranCellTDD_deallocThrPucchFormat1 {
    type int32 {
      range 0..2000;
    }
  }
  typedef ddt-Lrat_AdmissionControl_nrOfPaConnReservationsPerCell {
    type int32 {
      range 0..20;
    }
  }
  typedef ddt-Lrat_PtmResOpUseConfig_unresMsrUsageThreshold {
    type int32 {
      range 0..100;
    }
  }
  typedef ddt-Lrat_EUtranCellTDD_latitude {
    type int32 {
      range -90000000..90000000;
    }
  }
  typedef ddt-Lrat_QciProfilePredefined_pdbMeasurementDelta {
    type int32 {
      range -80..100;
    }
  }
  typedef ddt-Lrat_CellSleepFunction_wakeUpWaitTimer {
    type int32 {
      range 0..120000;
    }
  }
  typedef ddt-Lrat_UserProfile_spidList {
    type int32 {
      range 1..256;
    }
  }
  typedef ddt-Lrat_UeMeasControl_maxMeasGeran {
    type int32 {
      range 1..5;
    }
  }
  typedef ddt-Lrat_CellSleepFunction_wakeUpLastHoTime {
    type int32 {
      range 1..1000;
    }
  }
  typedef ddt-Lrat_FreqGroupPrioGERAN_altCsfbTargetPrioEc {
    type int32 {
      range "-1000..-1000 | -1..7";
    }
  }
  typedef ddt-Lrat_ENodeBFunction_timePhaseMaxDeviationMbms {
    type int32 {
      range 9..100;
    }
  }
  typedef ddt-Lrat_LoadBasedCaMsrThr_ulPrbUtilThreshLow {
    type int32 {
      range 0..100;
    }
  }
  typedef ddt-Lrat_ReportConfigEUtraBadCovSec_a2ThrRsrpSecOffsetCeABr {
    type int32 {
      range -100..100;
    }
  }
  typedef ddt-Lrat_ExternalEUtranCellTDD_specialSubframePattern {
    type int32 {
      range "-1..-1 | 0..8";
    }
  }
  typedef ddt-Lrat_UeMeasControl_filterCoefficientEUtraUlSinrMax {
    type int32 {
      range "0..0 | 1..1 | 2..2 | 3..3 | 4..4 | 5..5 | 6..6 | 7..7 | 8..8 | 9..9 | 11..11 | 13..13 | 15..15 | 17..17 | 19..19";
    }
  }
  typedef ddt-Lrat_ReportConfigA1Sec_hysteresisA1Sec {
    type int32 {
      range 0..150;
    }
  }
  typedef ddt-Lrat_ExternalGNodeBFunction_gNodeBIdLength {
    type int32 {
      range 22..32;
    }
  }
  typedef ddt-Lrat_SubFrameConfigRO_radioframeAllocationOffset {
    type int32 {
      range 0..7;
    }
  }
  typedef ddt-Lrat_GUGroupIdRO_mnc {
    type int32 {
      range 0..999;
    }
  }
  typedef ddt-Lrat_AdmissionControl_limitSrNonPa {
    type int32 {
      range 0..20;
    }
  }
  typedef ddt-Lrat_EUtranCellTDD_pdcchTargetBlerVolte {
    type int32 {
      range 1..200;
    }
  }
  typedef ddt-Lrat_NbIotIntraFrequencyInfo_qRxLevMin {
    type int32 {
      range -156..-44;
    }
  }
  typedef ddt-Lrat_ReportConfigA1Sec_a1ThrRsrpSecOffsetCeABr {
    type int32 {
      range -100..100;
    }
  }
  typedef ddt-Lrat_EUtranCellFDD_lbabThreshRejectRateHigh {
    type int32 {
      range 0..1000;
    }
  }
  typedef ddt-Lrat_SubFrameConfigRO_radioframeAllocationPeriod {
    type int32 {
      range "1..1 | 2..2 | 4..4 | 8..8 | 16..16 | 32..32";
    }
  }
  typedef ddt-Lrat_ExternalEUtranCellTDD_additionalFreqBandList {
    type int32 {
      range 1..256;
    }
  }
  typedef ddt-Lrat_A2CriticalPCOffsetMCPC_a2CriticalThrRsrqPCOffset {
    type int32 {
      range -240..240;
    }
  }
  typedef ddt-Lrat_EUtranCellTDD_qRxLevMin {
    type int32 {
      range -140..-44;
    }
  }
  typedef ddt-Lrat_Mbms_tMbmsAuditTimer {
    type int32 {
      range 60..86400;
    }
  }
  typedef ddt-Lrat_MbsfnArea_mcchRepetitionPeriod {
    type int32 {
      range "32..32 | 64..64 | 128..128 | 256..256";
    }
  }
  typedef ddt-Lrat_ExternalGeranCell_rac {
    type int32 {
      range -1..255;
    }
  }
  typedef ddt-Lrat_ENodeBFunction_timePhaseMaxDeviation {
    type int32 {
      range 9..100;
    }
  }
  typedef ddt-Lrat_UtranFreqRelation_b2Thr1RsrpUtraFreqOffset {
    type int32 {
      range -100..100;
    }
  }
  typedef ddt-Lrat_AnrFunctionGeran_anrGeranMeasReportRacIncr {
    type int32 {
      range 0..1000;
    }
  }
  typedef ddt-Lrat_ReportConfigA5Anr_hysteresisA5 {
    type int32 {
      range 0..150;
    }
  }
  typedef ddt-Lrat_SIB6_tReselectionUtra {
    type int32 {
      range 0..7;
    }
  }
  typedef ddt-Lrat_MobilityParams1xRtt_minProtocolRev {
    type int32 {
      range 0..255;
    }
  }
  typedef ddt-Lrat_ReportConfigCsfbGeran_thresholdGeran {
    type int32 {
      range -110..-47;
    }
  }
  typedef ddt-Lrat_ExternalGNodeBFunction_userLabel {
    type string {
      length 1..128;
    }
  }
  typedef ddt-Lrat_EUtranCellTDD_rxSinrTargetClpc {
    type int32 {
      range -50..50;
    }
  }
  typedef ddt-Lrat_EUtranCellFDD_dynCellSubscrCap {
    type int32 {
      range 0..1000000;
    }
  }
  typedef ddt-Lrat_RATFreqPrio_userLabel {
    type string {
      length 1..128;
    }
  }
  typedef ddt-Lrat_ENodeBFunction_licUlBbPercentileConf {
    type int32 {
      range 1..100;
    }
  }
  typedef ddt-Lrat_EUtranFreqRelation_tReselectionEutraSfHigh {
    type int32 {
      range 25..100;
    }
  }
  typedef ddt-Lrat_EUtranCellTDD_estCellCapUsableFraction {
    type int32 {
      range 0..100;
    }
  }
  typedef ddt-Lrat_EUtranCellFDD_harqOffsetUl {
    type int32 {
      range -20..20;
    }
  }
  typedef ddt-Lrat_EUtranCellTDD_puschMaxNrOfPrbsPerUe {
    type int32 {
      range 1..100;
    }
  }
  typedef ddt-Lrat_EUtranCellTDD_noOfPucchFormat1PrbPairsPerFrame {
    type int32 {
      range 0..1000;
    }
  }
  typedef ddt-Lrat_ExternalGeranCell_userLabel {
    type string {
      length 1..128;
    }
  }
  typedef ddt-Lrat_InterNodalProtocolVerRO_eRanUlCompProtVerExact {
    type int32 {
      range -1..2147483647;
    }
  }
  typedef ddt-Lrat_MeasReportConfigParams_a1ThresholdRsrpSecOffset {
    type int32 {
      range -100..100;
    }
  }
  typedef ddt-Lrat_EUtranCellRelation_timeOfCreation {
    type string {
      length 0..19;
    }
  }
  typedef ddt-Lrat_Cdma20001xRttCellRelation_userLabel {
    type string {
      length 1..128;
    }
  }
  typedef ddt-Lrat_BlackListEntry_physicalLayerCellIdGroup {
    type int32 {
      range -1..167;
    }
  }
  typedef ddt-Lrat_ReportConfigEUtraIFBestCell_a3RsrqOffset {
    type int32 {
      range -150..150;
    }
  }
  typedef ddt-Lrat_BandCombCompression_requestMaxCCsDL {
    type int32 {
      range 0..32;
    }
  }
  typedef ddt-Lrat_NbIotCell_allocatedUlPrb {
    type int32 {
      range "-10..110 | 255..255";
    }
  }
  typedef ddt-Lrat_QciProfileOperatorDefined_drxPriority {
    type int32 {
      range 0..100;
    }
  }
  typedef ddt-Lrat_AcBarringConfig1xRtt_acBarringEmgR9 {
    type int32 {
      range 0..7;
    }
  }
  typedef ddt-Lrat_ReportConfigB2Cdma2000_hysteresisB2 {
    type int32 {
      range 0..150;
    }
  }
  typedef ddt-Lrat_ENodeBFunction_timePhaseMaxDeviationIeNbCa {
    type int32 {
      range 9..100;
    }
  }
  typedef ddt-Lrat_AdmissionControl_nrOfPrevPreempPaRbReservation {
    type int32 {
      range 0..3;
    }
  }
  typedef ddt-Lrat_EUtranCellTDD_pdcchLaGinrMargin {
    type int32 {
      range -50..150;
    }
  }
  typedef ddt-Lrat_MACConfiguration_ulTtiBundlingMaxHARQTx {
    type int32 {
      range "1..1 | 2..2 | 3..3 | 4..4 | 5..5 | 6..6 | 7..7";
    }
  }
  typedef ddt-Lrat_EUtranCellFDD_freqBand {
    type int32 {
      range 1..256;
    }
  }
  typedef ddt-Lrat_TraceStreamStructRO_ipAddress {
    type string {
      length 2..46;
    }
  }
  typedef ddt-Lrat_EUtranCellTDD_gpsTimeSFN0DecimalSecond {
    type int64 {
      range 0..4294967295;
    }
  }
  typedef ddt-Lrat_ENodeBFunction_dlBbCapacityNet {
    type int32 {
      range "-1..-1 | 0..65535";
    }
  }
  typedef ddt-Lrat_MeasReportConfigParams_b2Threshold2Cdma2000Offset {
    type int32 {
      range -50..50;
    }
  }
  typedef ddt-Lrat_ENodeBFunction_tRelocOverallValue {
    type int32 {
      range 1..32000;
    }
  }
  typedef ddt-Lrat_ENodeBFunction_userLabel {
    type string {
      length 1..128;
    }
  }
  typedef ddt-Lrat_PmFlexCounterFilter_subscriberGroupFilterMin {
    type int32 {
      range 0..4;
    }
  }
  typedef ddt-Lrat_ENodeBFunction_timePhaseMaxDeviationCdma2000 {
    type int32 {
      range 9..100;
    }
  }
  typedef ddt-Lrat_MbmsService_userLabel {
    type string {
      length 1..128;
    }
  }
  typedef ddt-Lrat_ExternalUtranCellTDD_timeOfCreation {
    type string {
      length 0..19;
    }
  }
  typedef ddt-Lrat_AdmissionControl_zzzTemp16 {
    type int32 {
      range 0..1000;
    }
  }
  typedef ddt-Lrat_AdmissionControl_zzzTemp17 {
    type int32 {
      range 0..1000;
    }
  }
  typedef ddt-Lrat_AdmissionControl_zzzTemp14 {
    type int32 {
      range 0..1000;
    }
  }
  typedef ddt-Lrat_NbIotCell_preambleIniRecTargetPower {
    type int32 {
      range -120..-90;
    }
  }
  typedef ddt-Lrat_FrameStartOffsetTDD_subFrameOffset {
    type int32 {
      range 0..4;
    }
  }
  typedef ddt-Lrat_AdmissionControl_zzzTemp15 {
    type int32 {
      range 0..1000;
    }
  }
  typedef ddt-Lrat_AdmissionControl_zzzTemp12 {
    type int32 {
      range 0..1000;
    }
  }
  typedef ddt-Lrat_AdmissionControl_zzzTemp13 {
    type int32 {
      range 0..1000;
    }
  }
  typedef ddt-Lrat_EUtranCellTDD_noOfChannelSelectionSets {
    type int32 {
      range "0..0 | 4..12";
    }
  }
  typedef ddt-Lrat_AdmissionControl_zzzTemp10 {
    type int32 {
      range 0..1000;
    }
  }
  typedef ddt-Lrat_EUtranCellTDD_lbabThreshTimeLow {
    type int32 {
      range 0..4095;
    }
  }
  typedef ddt-Lrat_AdmissionControl_zzzTemp11 {
    type int32 {
      range 0..1000;
    }
  }
  typedef ddt-Lrat_AdmissionControl_lbAtoThresholdLevel2 {
    type int32 {
      range 0..100;
    }
  }
  typedef ddt-Lrat_EUtranCellTDD_uncertSemiMinor {
    type int32 {
      range 0..127;
    }
  }
  typedef ddt-Lrat_AdmissionControl_lbAtoThresholdLevel1 {
    type int32 {
      range 0..100;
    }
  }
  typedef ddt-Lrat_ReportConfigSearch_a2UlCriticalThreshold {
    type int32 {
      range -150..450;
    }
  }
  typedef ddt-Lrat_LoadBasedCaMsrThr_ulSeUtilThreshHigh {
    type int32 {
      range 0..100;
    }
  }
  typedef ddt-Lrat_PeriodicitySI_siPeriodicitySI3 {
    type int32 {
      range "8..8 | 16..16 | 32..32 | 64..64 | 128..128 | 256..256 | 512..512";
    }
  }
  typedef ddt-Lrat_PeriodicitySI_siPeriodicitySI4 {
    type int32 {
      range "8..8 | 16..16 | 32..32 | 64..64 | 128..128 | 256..256 | 512..512";
    }
  }
  typedef ddt-Lrat_PeriodicitySI_siPeriodicitySI5 {
    type int32 {
      range "8..8 | 16..16 | 32..32 | 64..64 | 128..128 | 256..256 | 512..512";
    }
  }
  typedef ddt-Lrat_SciProfile_ulMaxWaitingTime {
    type int32 {
      range 0..500;
    }
  }
  typedef ddt-Lrat_PeriodicitySI_siPeriodicitySI6 {
    type int32 {
      range "8..8 | 16..16 | 32..32 | 64..64 | 128..128 | 256..256 | 512..512";
    }
  }
  typedef ddt-Lrat_PeriodicitySI_siPeriodicitySI1 {
    type int32 {
      range "8..8 | 16..16 | 32..32 | 64..64 | 128..128 | 256..256 | 512..512";
    }
  }
  typedef ddt-Lrat_PeriodicitySI_siPeriodicitySI2 {
    type int32 {
      range "8..8 | 16..16 | 32..32 | 64..64 | 128..128 | 256..256 | 512..512";
    }
  }
  typedef ddt-Lrat_ENodeBFunction_iuaBbmResourceLimit {
    type int32 {
      range 1..80;
    }
  }
  typedef ddt-Lrat_EUtranCellFDD_ulTxPsdDistrThr {
    type int32 {
      range 0..100;
    }
  }
  typedef ddt-Lrat_AdmissionControl_dlAdmDifferentiationThr {
    type int32 {
      range 0..1000;
    }
  }
  typedef ddt-Lrat_ResourcePartition_partitionId {
    type int32 {
      range "0..0 | 1..24";
    }
  }
  typedef ddt-Lrat_EUtranCellTDD_dlPowerRampUpInitialRatio {
    type int32 {
      range 10..100;
    }
  }
  typedef ddt-Lrat_EutranCellCorner_cornerLatitude {
    type int32 {
      range -90000000..90000000;
    }
  }
  typedef ddt-Lrat_AdmissionControl_zzzTemp18 {
    type int32 {
      range 0..1000;
    }
  }
  typedef ddt-Lrat_EUtranCellFDD_cellCapMaxCellSubCap {
    type int32 {
      range 0..1000000;
    }
  }
  typedef ddt-Lrat_AdmissionControl_zzzTemp19 {
    type int32 {
      range 0..1000;
    }
  }
  typedef ddt-Lrat_OcngPrbSerie_prbFirst {
    type int32 {
      range 0..99;
    }
  }
  typedef ddt-Lrat_ReportConfigSCellA1A2_hysteresisA1A2RsrpBidirectional {
    type int32 {
      range 0..150;
    }
  }
  typedef ddt-Lrat_ReportConfigParamsUlQciOffset_a1a2UlThrQciOffset {
    type int32 {
      range -100..100;
    }
  }
  typedef ddt-Lrat_ENodeBFunction_maxNrOfInterEnbUlCompLbm {
    type int32 {
      range 0..10;
    }
  }
  typedef ddt-EUtranCellFDD_changeFrequency_earfcn {
    type int32 {
      range "0..17999 | 46590..262143";
    }
  }
  typedef ddt-Lrat_NbIotCell_cellId {
    type int32 {
      range 0..255;
    }
  }
  typedef ddt-Lrat_CellSleepFunction_sleepEndTime {
    type string {
      length 5..5;
    }
  }
  typedef ddt-Lrat_FrameStartOffset_subFrameOffset {
    type int32 {
      range 0..5;
    }
  }
  typedef ddt-Lrat_CellSleepFunction_capCellRrcConnSleepThreshold {
    type int32 {
      range 0..3000;
    }
  }
  typedef ddt-Lrat_GeranFreqGroupRelation_userLabel {
    type string {
      length 1..128;
    }
  }
  typedef ddt-Lrat_NbIdleModeLoadDistr_nbCarrierFreqList {
    type int32 {
      range 0..262143;
    }
  }
  typedef ddt-Lrat_EUtranFreqRelation_csgPhysCellIdRange {
    type int32 {
      range "1..1 | 4..4 | 8..8 | 12..12 | 16..16 | 24..24 | 32..32 | 48..48 | 64..64 | 84..84 | 96..96 | 128..128 | 168..168 | 252..252 | 504..504";
    }
  }
  typedef ddt-Lrat_CellSleepFunction_covCellRrcConnWakeUpThreshold {
    type int32 {
      range 0..3000;
    }
  }
  typedef ddt-Lrat_NbIotCell_earfcndl {
    type int32 {
      range "-1..-1 | 0..17999 | 46590..262143";
    }
  }
  typedef ddt-Lrat_ReportConfigA1Prim_hysteresisA1Prim {
    type int32 {
      range 0..150;
    }
  }
  typedef ddt-Lrat_EUtranCellTDD_additionalFreqBandList {
    type int32 {
      range 1..256;
    }
  }
  typedef ddt-Lrat_ENodeBFunction_dlBbCapacityMaxLimit {
    type int32 {
      range "-1..-1 | 0..65535";
    }
  }
  typedef ddt-Lrat_EUtranCellTDD_dlPowerChangeRate {
    type int32 {
      range 1..10;
    }
  }
  typedef ddt-Lrat_IdleModePrioAtRelease_mediumHighLoadThreshold {
    type int32 {
      range 0..16000;
    }
  }
  typedef ddt-Lrat_GeranFreqGroupRelation_csFallbackPrio {
    type int32 {
      range -1..7;
    }
  }
  typedef ddt-Lrat_SciProfile_ulMinBitRate {
    type int32 {
      range 0..75000;
    }
  }
  typedef ddt-Lrat_EUtranCellFDD_iuaMaxResourcePerCell {
    type int32 {
      range 0..100;
    }
  }
  typedef ddt-Lrat_ENodeBFunction_licDlBbPercentileConf {
    type int32 {
      range 1..100;
    }
  }
  typedef ddt-Lrat_GeranFreqGroupRelation_pMaxGeran {
    type int32 {
      range "0..39 | 1000..1000";
    }
  }
  typedef ddt-Lrat_QciProfilePredefined_lessMaxDelayThreshold {
    type int32 {
      range 0..20;
    }
  }
  typedef ddt-Lrat_GUGroupIdRO_mncLength {
    type int32 {
      range 2..3;
    }
  }
  typedef ddt-Lrat_BandClassPrioCdma1xRtt_voicePrio {
    type int32 {
      range -1..7;
    }
  }
  typedef ddt-Lrat_EUtranCellFDD_serviceAreaId {
    type int32 {
      range 0..65535;
    }
  }
  typedef ddt-Lrat_NbIotFrequencyInfo_tReselectionNb {
    type int32 {
      range "0..0 | 3..3 | 6..6 | 9..9 | 12..12 | 15..15 | 18..18 | 21..21";
    }
  }
  typedef ddt-Lrat_ReportConfigEUtraIFA3UlTrig_hysteresisA3 {
    type int32 {
      range 0..150;
    }
  }
  typedef ddt-Lrat_EUtranCellRelationUnlicensed_sCellPriority {
    type int32 {
      range -1..7;
    }
  }
  typedef ddt-Lrat_UeMeasControl_a3MobilityTimerBr {
    type int32 {
      range 0..120000;
    }
  }
  typedef ddt-Lrat_Cdma2000Network_userLabel {
    type string {
      length 1..128;
    }
  }
  typedef ddt-Lrat_AdmissionControl_zzzTemp21 {
    type int32 {
      range 0..1000;
    }
  }
  typedef ddt-Lrat_PreschedulingProfile_preschedulingDuration {
    type int32 {
      range 5..30000;
    }
  }
  typedef ddt-Lrat_EUtranCellFDD_iuaMaxPrbsPerUe {
    type int32 {
      range 0..100;
    }
  }
  typedef ddt-Lrat_AdmissionControl_zzzTemp20 {
    type int32 {
      range 0..1000;
    }
  }
  typedef ddt-Lrat_ReportConfigInterRatPm_b2Threshold2EcNoUtraPm {
    type int32 {
      range -245..0;
    }
  }
  typedef ddt-Lrat_SectorCarrier_noOfRxAntennas {
    type int32 {
      range "0..0 | 1..1 | 2..2 | 4..4 | 8..8";
    }
  }
  typedef ddt-Lrat_SIB8_searchWindowSizeCdma {
    type int32 {
      range 0..15;
    }
  }
  typedef ddt-Lrat_NotificationConfig_notificationSFIndex {
    type int32 {
      range 1..6;
    }
  }
  typedef ddt-Lrat_EUtranCellTDD_noOfEnhAdptReTxCand {
    type int32 {
      range -1..5;
    }
  }
  typedef ddt-Lrat_EUtranFreqRelation_timeOfCreation {
    type string {
      length 0..19;
    }
  }
  typedef ddt-Lrat_ReportConfigCsfbUtra_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_AcBarringConfig1xRtt_acBarring11R9 {
    type int32 {
      range 0..7;
    }
  }
  typedef ddt-Lrat_ReportConfigB2Utra_timeToTriggerB2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_SubFrameConfigRO_sfAllocationOneFrame {
    type int32 {
      range 0..63;
    }
  }
  typedef ddt-Lrat_EUtranCellTDD_dlPowerRampUpInitRatio {
    type int32 {
      range 40..100;
    }
  }
  typedef ddt-Lrat_UtranFreqToQciProfileRelation_lbUtranB1ThresholdEcNoOffset {
    type int32 {
      range 0..50;
    }
  }
  typedef ddt-Lrat_PrefTrafficMgmt_spidBlacklistHo {
    type int32 {
      range "-1..-1 | 1..256";
    }
  }
  typedef ddt-Lrat_EUtranCellTDD_interEnbUlCompUserSelSinrThr {
    type int32 {
      range -150..250;
    }
  }
  typedef ddt-Lrat_AnrFunction_maxNoPciReportsEvent {
    type int32 {
      range 0..100;
    }
  }
  typedef ddt-Lrat_AdmissionControl_admResourceMinQciPrio {
    type int32 {
      range 0..14;
    }
  }
  typedef ddt-Lrat_EUtranCellFDD_filterUeDlThpVolThr {
    type int32 {
      range 0..4000;
    }
  }
  typedef ddt-Lrat_BandClassPrioCdma1xRtt_csFallbackPrioEC {
    type int32 {
      range "-1000..-1000 | 0..7";
    }
  }
  typedef ddt-Lrat_EUtranCellFDD_hoOptStatNumQci1 {
    type int32 {
      range 1..32767;
    }
  }
  typedef ddt-Lrat_LoadBalancingFunction_lbRateOffsetLoadThreshold {
    type int32 {
      range 0..16000;
    }
  }
  typedef ddt-Lrat_QciProfilePredefined_dscp {
    type int32 {
      range 0..63;
    }
  }
  typedef ddt-Lrat_ReportConfigParamsQciOffset_a1a2ThrRsrpQciOffset {
    type int32 {
      range -100..100;
    }
  }
  typedef ddt-Lrat_GeranFreqGroupRelation_altCsfbTargetPrioEc {
    type int32 {
      range -1..7;
    }
  }
  typedef ddt-Lrat_EUtranCellFDD_pdcchTargetBler {
    type int32 {
      range 1..200;
    }
  }
  typedef ddt-Lrat_EUtranCellFDD_pdschMaxNrOfPrbsPerUe {
    type int32 {
      range 1..100;
    }
  }
  typedef ddt-Lrat_GeranFreqGroupRelation_nccPermitted {
    type string {
      length 8..8;
    }
  }
  typedef ddt-Lrat_UtranTDDFreqRelation_cellReselectionPriority {
    type int32 {
      range 0..7;
    }
  }
  typedef ddt-Lrat_LoadBasedCaMsrThr_ulPrbUtilThreshHigh {
    type int32 {
      range 0..100;
    }
  }
  typedef ddt-Lrat_MimoSleepFunction_sleepStartTime {
    type string {
      length 5..5;
    }
  }
  typedef ddt-Lrat_ReportConfigEUtraIntraFreqPm_a4ThresholdRsrpPm {
    type int32 {
      range -140..-44;
    }
  }
  typedef ddt-Lrat_EUtranCellTDD_iuaMaxResourcePerCell {
    type int32 {
      range 0..100;
    }
  }
  typedef ddt-Lrat_AirIfLoadProfile_userLabel {
    type string {
      length 1..128;
    }
  }
  typedef ddt-Lrat_EUtranCellTDD_cioLowerLimitAdjBySon {
    type int32 {
      range -24..0;
    }
  }
  typedef ddt-Lrat_EUtranCellTDD_outOfCoverageThreshold {
    type int32 {
      range 1..63;
    }
  }
  typedef ddt-Lrat_TermPointToENB_timeOfCreation {
    type string {
      length 0..19;
    }
  }
  typedef ddt-Lrat_MbsfnAreaCellRelation_userLabel {
    type string {
      length 1..128;
    }
  }
  typedef ddt-Lrat_ExternalUtranCellFDD_userLabel {
    type string {
      length 1..128;
    }
  }
  typedef ddt-Lrat_MbsfnArea_notificationIndicator {
    type int32 {
      range 0..7;
    }
  }
  typedef ddt-Lrat_SubFrameConfigRO_sfAllocationFourFrame {
    type int32 {
      range 0..16777215;
    }
  }
  typedef ddt-Lrat_CarrierAggregationFunction_effectiveBwImpactDl4Layer {
    type int32 {
      range 0..200;
    }
  }
  typedef ddt-Lrat_ReportConfigA1Prim_a1ThresholdRsrpPrim {
    type int32 {
      range -140..-44;
    }
  }
  typedef ddt-Lrat_ReportConfigEUtraBadCovSec_a2ThresholdRsrqSec {
    type int32 {
      range -195..-30;
    }
  }
  typedef ddt-Lrat_SignalingRadioBearer_tPollRetransmitDl {
    type int32 {
      range "5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500";
    }
  }
  typedef ddt-Lrat_PlmnIdentity_mnc {
    type int32 {
      range 0..999;
    }
  }
  typedef ddt-Lrat_SciProfile_lessMaxDelayThreshold {
    type int32 {
      range 0..20;
    }
  }
  typedef ddt-Lrat_NbIotCell_primaryFreqBand {
    type int32 {
      range "-1..-1 | 1..256";
    }
  }
  typedef ddt-Lrat_ReportConfigB2CdmaRttUlTrig_timeToTriggerB2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_RlfProfile_n310 {
    type int32 {
      range "1..1 | 2..2 | 3..3 | 4..4 | 6..6 | 8..8 | 10..10 | 20..20";
    }
  }
  typedef ddt-Lrat_RlfProfile_n311 {
    type int32 {
      range "1..1 | 2..2 | 3..3 | 4..4 | 5..5 | 6..6 | 8..8 | 10..10";
    }
  }
  typedef ddt-Lrat_UtranCellRelation_timeOfCreation {
    type string {
      length 0..19;
    }
  }
  typedef ddt-Lrat_ReportConfigA5UlTrig_timeToTriggerA5 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_ReportConfigSearch_hysteresisA1A2SearchRsrp {
    type int32 {
      range 0..150;
    }
  }
  typedef ddt-Lrat_ReportConfigSearch_hysteresisA1A2SearchRsrq {
    type int32 {
      range 0..150;
    }
  }
  typedef ddt-Lrat_ReportConfigSearch_timeToTriggerA2UlCritical {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_QciProfilePredefined_tReorderingDl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-Lrat_QciProfileOperatorDefined_dlMinBitRate {
    type int32 {
      range 0..150000;
    }
  }
  typedef ddt-Lrat_PtmResOpUseConfig_resSRatioThreshold {
    type int32 {
      range 0..1600;
    }
  }
  typedef ddt-Lrat_ReportConfigEUtraIntraFreqPm_hysteresisPm {
    type int32 {
      range 0..150;
    }
  }
  typedef ddt-Lrat_EUtranFreqRelation_pMax {
    type int32 {
      range "-30..33 | 1000..1000";
    }
  }
  typedef ddt-Lrat_CellPortion_altitude {
    type int32 {
      range -32768..32767;
    }
  }
  typedef ddt-Lrat_EUtranCellFDD_preambleInitialReceivedTargetPower {
    type int32 {
      range -120..-90;
    }
  }
  typedef ddt-Lrat_MSCid_marketId {
    type int32 {
      range 0..65535;
    }
  }
  typedef ddt-Lrat_ExternalEUtranCellTDD_subframeAssignment {
    type int32 {
      range "-1..-1 | 0..6";
    }
  }
  typedef ddt-Lrat_TrafficModelPrb_ulDlRatioPerQci {
    type int32 {
      range 0..100;
    }
  }
  typedef ddt-Lrat_ReportConfigInterEnbUlComp_timeToTriggerA3 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_AirIfLoadProfile_ailgChangePeriod {
    type int32 {
      range "1..1 | 5..5 | 10..10";
    }
  }
  typedef ddt-Lrat_A5PCOffsetMCPC_a5Thr1RsrpPCOffset {
    type int32 {
      range -100..100;
    }
  }
  typedef ddt-Lrat_UtranTDDFreqRelation_csFallbackPrioEC {
    type int32 {
      range -1..7;
    }
  }
  typedef ddt-Lrat_PrioOffsetPerQci_offsetPerQciPrio {
    type int32 {
      range -1..7;
    }
  }
  typedef ddt-Lrat_ReportConfigCsg_a5Thr1RsrpAltCsgOffset {
    type int32 {
      range -100..100;
    }
  }
  typedef ddt-Lrat_EUtranCellTDD_allocThrPucchFormat1 {
    type int32 {
      range 0..2000;
    }
  }
  typedef ddt-Lrat_TermPointToMme_relativeMmeCapacity {
    type int32 {
      range 0..255;
    }
  }
  typedef ddt-Lrat_TrafficModelPrb_qciDistSinrLow {
    type int32 {
      range 0..100;
    }
  }
  typedef ddt-Lrat_UeMeasControl_csfbHoTargetSearchTimer {
    type int32 {
      range 1..12000;
    }
  }
  typedef ddt-Lrat_EUtranFreqRelation_qRxLevMin {
    type int32 {
      range -140..-44;
    }
  }
  typedef ddt-Lrat_EUtranCellTDD_dlConfigurableFrequencyStart {
    type int32 {
      range 0..100;
    }
  }
  typedef ddt-Lrat_EUtranCellTDD_lbabThreshRejectRateHigh {
    type int32 {
      range 0..1000;
    }
  }
  typedef ddt-Lrat_ExternalEUtranCellFDD_freqBand {
    type int32 {
      range 1..256;
    }
  }
  typedef ddt-Lrat_ReportConfigB2GeranUlTrig_hysteresisB2 {
    type int32 {
      range 0..150;
    }
  }
  typedef ddt-Lrat_QciProfileOperatorDefined_ulMinBitRate {
    type int32 {
      range 0..75000;
    }
  }
  typedef ddt-Lrat_ReportConfigEUtraIntraFreqPm_a2ThresholdRsrpPm {
    type int32 {
      range -140..-44;
    }
  }
  typedef ddt-Lrat_ReportConfigSCellA6_timeToTriggerA6 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_dlInternalChannelBandwidth {
    type int32 {
      range "0..0 | 4200..4200 | 4400..4400 | 4600..4600 | 4800..4800 | 9000..9000";
    }
  }
  typedef ddt-Lrat_EUtranCellFDD_userLabel {
    type string {
      length 1..128;
    }
  }
  typedef ddt-Lrat_EUtranCellFDD_hpueCaSwitchHyst {
    type int32 {
      range 0..150;
    }
  }
  typedef ddt-Lrat_AnrFunctionEUtran_anrUesEUtraIntraFMin {
    type int32 {
      range 0..100;
    }
  }
  typedef ddt-Lrat_EUtranCellFDD_gpsTimeSFN0DecimalSecond {
    type int64 {
      range 0..4294967295;
    }
  }
  typedef ddt-Lrat_MeasReportConfigParams_a3IntraOffsetAdjustmentRsrq {
    type int32 {
      range -150..150;
    }
  }
  typedef ddt-Lrat_PmFlexCounterFilter_qciFilterMin {
    type int32 {
      range 0..255;
    }
  }
  typedef ddt-Lrat_MeasReportConfigParams_a3IntraOffsetAdjustmentRsrp {
    type int32 {
      range -150..150;
    }
  }
  typedef ddt-Lrat_EUtranFreqRelation_a3RsrqFreqOffsetAdjustment {
    type int32 {
      range -150..150;
    }
  }
  typedef ddt-Lrat_EUtranCellTDD_dlDynUeAdmCtrlRetDiffThr {
    type int32 {
      range 0..1000;
    }
  }
  typedef ddt-Lrat_EUtranFrequency_userLabel {
    type string {
      length 1..128;
    }
  }
  typedef ddt-Lrat_CarrierAggregationFunction_waitForCaOpportunity {
    type int32 {
      range -1..60000;
    }
  }
  typedef ddt-Lrat_ENodeBFunction_x2retryTimerStart {
    type int32 {
      range 0..1000;
    }
  }
  typedef ddt-Lrat_EUtranCellTDD_srDetectHighThres {
    type int32 {
      range 0..300;
    }
  }
  typedef ddt-Lrat_NbIotCell_prbIndex {
    type int32 {
      range "-10..110 | 255..255";
    }
  }
  typedef ddt-Lrat_EUtranCellTDD_interferenceThresholdSinrClpc {
    type int32 {
      range -125..-60;
    }
  }
  typedef ddt-Lrat_GeranFreqGroupRelation_b2Thr1RsrqGeranFreqOffset {
    type int32 {
      range -240..240;
    }
  }
  typedef ddt-Lrat_ExternalEUtranCellFDD_lbEUtranCellOffloadCapacity {
    type int32 {
      range 0..1000000;
    }
  }
  typedef ddt-Lrat_FreqGroupPrioGERAN_frequencyGroupId {
    type int32 {
      range "-1000..-1000 | 0..1024";
    }
  }
  typedef ddt-Lrat_AdmissionControl_admNrRrcDifferentiationThr {
    type int32 {
      range 0..1000;
    }
  }
  typedef ddt-Lrat_ENodeBFunction_biasThpWifiMobility {
    type int32 {
      range 1..100;
    }
  }
  typedef ddt-Lrat_CellSleepFunction_capCellSleepProhibitInterval {
    type int32 {
      range 0..10000;
    }
  }
  typedef ddt-Lrat_UtranFreqToQciProfileRelation_b2Thr1RsrpUtraFreqQciOffset {
    type int32 {
      range -100..100;
    }
  }
  typedef ddt-Lrat_ReportConfigSearch_timeToTriggerA1UlSearch {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_ENodeBFunction_iuaMaxResourcePerBbm {
    type int32 {
      range 0..100;
    }
  }
  typedef ddt-Lrat_ReportConfigSearch_a1a2UlSearchThreshold {
    type int32 {
      range -150..450;
    }
  }
  typedef ddt-Lrat_LoadBalancingFunction_lbHitRateEUtranRemoveThreshold {
    type int32 {
      range 0..99;
    }
  }
  typedef ddt-Lrat_NbIotCell_pMax {
    type int32 {
      range "-30..33 | 1000..1000";
    }
  }
  typedef ddt-Lrat_SIB3_sIntraSearchQ {
    type int32 {
      range 0..31;
    }
  }
  typedef ddt-Lrat_ReportConfigB1Geran_b1ThresholdGeran {
    type int32 {
      range -110..-47;
    }
  }
  typedef ddt-Lrat_UeMeasControl_servOrPrioIFHoTimer {
    type int32 {
      range 0..60000;
    }
  }
  typedef ddt-Lrat_PtmResOpUseConfig_unresSRatioThreshold {
    type int32 {
      range 0..1600;
    }
  }
  typedef ddt-Lrat_AdmissionControl_zzzTemp9 {
    type int32 {
      range 0..1000;
    }
  }
  typedef ddt-Lrat_SIB3_sIntraSearchP {
    type int32 {
      range 0..62;
    }
  }
  typedef ddt-Lrat_MobilityParams1xRtt_imsiBit11and12 {
    type int32 {
      range 0..127;
    }
  }
  typedef ddt-Lrat_EUtranFrequency_freqBand {
    type int32 {
      range 1..256;
    }
  }
  typedef ddt-Lrat_PtmAtoConfig_minSuccRateThreshold {
    type int32 {
      range 0..100;
    }
  }
  typedef ddt-Lrat_UnlicensedAccessFunction_laaSCellActDeactDataThresHyst {
    type int32 {
      range -1..5000;
    }
  }
  typedef ddt-Lrat_AnrFunction_removeNenbTime {
    type int32 {
      range 0..1000;
    }
  }
  typedef ddt-Lrat_EUtranCellFDD_cellRange {
    type int32 {
      range 1..100;
    }
  }
  typedef ddt-Lrat_EUtranCellTDD_cioUpperLimitAdjBySon {
    type int32 {
      range 0..24;
    }
  }
  typedef ddt-Lrat_TermPointToMme_mmeGIListLTERelated {
    type int32 {
      range -1..65535;
    }
  }
  typedef ddt-Lrat_MeasReportConfigParams_b2Threshold2GeranOffset {
    type int32 {
      range -24..24;
    }
  }
  typedef ddt-Lrat_EUtranCellFDD_lbEUtranCellOffloadCapacity {
    type int32 {
      range 0..1000000;
    }
  }
  typedef ddt-Lrat_EUtranCellFDD_interEnbUlCompUserSelSinrThr {
    type int32 {
      range -150..250;
    }
  }
  typedef ddt-Lrat_AdmissionControl_zzzTemp6 {
    type int32 {
      range 0..1000;
    }
  }
  typedef ddt-Lrat_AdmissionControl_zzzTemp5 {
    type int32 {
      range -1..20000;
    }
  }
  typedef ddt-Lrat_QciProfileOperatorDefined_harqPriority {
    type int32 {
      range 0..99;
    }
  }
  typedef ddt-Lrat_AdmissionControl_zzzTemp8 {
    type int32 {
      range 0..1000;
    }
  }
  typedef ddt-Lrat_AcBarringConfig1xRtt_acBarring15R9 {
    type int32 {
      range 0..7;
    }
  }
  typedef ddt-Lrat_AdmissionControl_zzzTemp7 {
    type int32 {
      range 0..1000;
    }
  }
  typedef ddt-Lrat_MbsfnArea_mbsfnAreaIdentity {
    type int32 {
      range 0..255;
    }
  }
  typedef ddt-Lrat_AdmissionControl_zzzTemp2 {
    type int32 {
      range -1..10000;
    }
  }
  typedef ddt-Lrat_FreqPrioEUTRA_arfcnValueEUtranDl {
    type int32 {
      range "-1000..-1000 | 0..17999 | 36000..262143";
    }
  }
  typedef ddt-Lrat_AdmissionControl_zzzTemp1 {
    type int32 {
      range -1..10000;
    }
  }
  typedef ddt-Lrat_SciProfile_priority {
    type int32 {
      range 1..14;
    }
  }
  typedef ddt-Lrat_AdmissionControl_zzzTemp4 {
    type int32 {
      range -1..20000;
    }
  }
  typedef ddt-Lrat_PmEventService_totalCellTraceStorageSize {
    type int32 {
      range 100..250000;
    }
  }
  typedef ddt-Lrat_AdmissionControl_zzzTemp3 {
    type int32 {
      range -1..20000;
    }
  }
  typedef ddt-Lrat_AnrFunctionUtran_cellAddRscpThresholdUtranDelta {
    type int32 {
      range -10..10;
    }
  }
  typedef ddt-Lrat_EUtranFreqToQciProfileRelation_a5Thr2RsrpFreqQciOffset {
    type int32 {
      range -100..100;
    }
  }
  typedef ddt-Lrat_NbIotCell_alpha {
    type int32 {
      range "0..0 | 4..10";
    }
  }
  typedef ddt-Lrat_NbIotIntraFrequencyInfo_tReselection {
    type int32 {
      range "0..0 | 3..3 | 6..6 | 9..9 | 12..12 | 15..15 | 18..18 | 21..21";
    }
  }
  typedef ddt-Lrat_LoadBasedCaMsrThr_dlSeUtilThreshLow {
    type int32 {
      range 0..100;
    }
  }
  typedef ddt-Lrat_EUtranCellTDD_prsConfigIndexMapped {
    type int32 {
      range 0..4095;
    }
  }
  typedef ddt-Lrat_ExternalEUtranCellTDD_timeOfCreation {
    type string {
      length 0..19;
    }
  }
  typedef ddt-Lrat_SIB3_qHystSfMedium {
    type int32 {
      range -6..0;
    }
  }
  typedef ddt-Lrat_QciProfilePredefined_pdb {
    type int32 {
      range 0..500;
    }
  }
  typedef ddt-Lrat_EUtranCellFDD_dlConfigurableFrequencyStart {
    type int32 {
      range 0..100;
    }
  }
  typedef ddt-Lrat_UeMeasControl_searchEffortTime {
    type int32 {
      range 0..1200;
    }
  }
  typedef ddt-Lrat_EUtranCellTDD_cceDynUeAdmCtrlRetDiffThr {
    type int32 {
      range 0..1000;
    }
  }
  typedef ddt-Lrat_LoadBalancingFunction_lbHitRateUtranAddThreshold {
    type int32 {
      range 1..100;
    }
  }
  typedef ddt-Lrat_QciProfileOperatorDefined_dscp {
    type int32 {
      range 0..63;
    }
  }
  typedef ddt-Lrat_EUtranFreqRelation_qQualMinRsrqCe {
    type int32 {
      range "-34..-3 | 0..0";
    }
  }
  typedef ddt-Lrat_EUtranCellTDD_cellSubscriptionCapacity {
    type int32 {
      range 0..1000000;
    }
  }
  typedef ddt-Lrat_Cdma2000FreqBandRelation_userLabel {
    type string {
      length 1..128;
    }
  }
  typedef ddt-Lrat_NbIotCell_dlAllocatedPrb {
    type int32 {
      range "-10..110 | 255..255";
    }
  }
  typedef ddt-Lrat_ReportConfigInterRatLb_utranB1ThresholdEcNo {
    type int32 {
      range -245..0;
    }
  }
  typedef ddt-Lrat_ReportConfigB2CdmaRttUlTrig_hysteresisB2 {
    type int32 {
      range 0..150;
    }
  }
  typedef ddt-Lrat_ReportConfigA5_a5Threshold2Rsrp {
    type int32 {
      range -140..-44;
    }
  }
  typedef ddt-Lrat_ReportConfigA5_a5Threshold2Rsrq {
    type int32 {
      range -195..-30;
    }
  }
  typedef ddt-Lrat_EUtranCellFDD_estCellCapUsableFraction {
    type int32 {
      range 0..100;
    }
  }
  typedef ddt-Lrat_PmEventService_cellTraceFileSize {
    type int32 {
      range 100..20000;
    }
  }
  typedef ddt-Lrat_ReportConfigA5Anr_a5Threshold2RsrpAnrDelta {
    type int32 {
      range -10..10;
    }
  }
  typedef ddt-Lrat_NbIotCell_additionalFreqBandList {
    type int32 {
      range 1..256;
    }
  }
  typedef ddt-Lrat_B2GeranPCOffsetMCPC_b2Thr1RsrqGeranPCOffset {
    type int32 {
      range -240..240;
    }
  }
  typedef ddt-Lrat_AnrFunction_removeNrelTime {
    type int32 {
      range 0..1000;
    }
  }
  typedef ddt-Lrat_TermPointToMme_mmeName {
    type string {
      length 0..150;
    }
  }
  typedef ddt-Lrat_TermPointToENB_eRanUlCompProtVerActive {
    type int32 {
      range -1..2147483647;
    }
  }
  typedef ddt-Lrat_UtranFreqRelation_connectedModeMobilityPrio {
    type int32 {
      range -1..7;
    }
  }
  typedef ddt-Lrat_QciProfilePredefined_qciACTuning {
    type int32 {
      range 1..1999;
    }
  }
  typedef ddt-Lrat_UtranFreqRelation_b2Thr2EcNoUtraFreqOffset {
    type int32 {
      range -50..50;
    }
  }
  typedef ddt-Lrat_EUtranCellFDD_beamWeightSet16TrTm9 {
    type int32 {
      range 0..128;
    }
  }
  typedef ddt-Lrat_UtranFreqToQciProfileRelation_lbUtranB1ThresholdRscpOffset {
    type int32 {
      range 0..24;
    }
  }
  typedef ddt-Lrat_ReportConfigA5UlTrig_a5Threshold2Rsrq {
    type int32 {
      range -195..-31;
    }
  }
  typedef ddt-Lrat_ReportConfigA5UlTrig_a5Threshold2Rsrp {
    type int32 {
      range -140..-44;
    }
  }
  typedef ddt-Lrat_EUtranCellFDD_orientMajorAxis {
    type int32 {
      range 0..179;
    }
  }
  typedef ddt-Lrat_EUtranCellTDD_pdschMaxNrOfPrbsPerUe {
    type int32 {
      range 1..100;
    }
  }
  typedef ddt-Lrat_ReportConfigB2Cdma2000_timeToTriggerB2Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_QciProfileOperatorDefined_tReorderingDl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 100..100 | 110..110 | 120..120 | 130..130 | 140..140 | 150..150 | 160..160 | 170..170 | 180..180 | 190..190 | 200..200";
    }
  }
  typedef ddt-Lrat_GeranFreqGroupRelation_b2Thr1RsrpGeranFreqOffset {
    type int32 {
      range -100..100;
    }
  }
  typedef ddt-Lrat_EUtranCellFDD_latencyLongThreshold {
    type int32 {
      range 125..1200;
    }
  }
  typedef ddt-Lrat_CellIdentityUtra_cId {
    type int32 {
      range 0..65535;
    }
  }
  typedef ddt-Lrat_Cdma1xRttCellId_cellId {
    type int32 {
      range 0..4095;
    }
  }
  typedef ddt-Lrat_EUtranCellFDD_cioLowerLimitAdjBySon {
    type int32 {
      range -24..0;
    }
  }
  typedef ddt-Lrat_ReportConfigA1Sec_a1ThresholdRsrqSec {
    type int32 {
      range -195..-30;
    }
  }
  typedef ddt-Lrat_SIB3_sIntraSearch {
    type int32 {
      range "0..62 | 1000..1000";
    }
  }
  typedef ddt-Lrat_UtranFrequency_userLabel {
    type string {
      length 1..128;
    }
  }
  typedef ddt-Lrat_InterNodalProtocolVerRO_interEnbUlCompProtVerExact {
    type int32 {
      range -1..2147483647;
    }
  }
  typedef ddt-Lrat_TermPointToENB_interEnbUlCompProtVerActive {
    type int32 {
      range -1..2147483647;
    }
  }
  typedef ddt-Lrat_CarrierAggregationFunction_selectionPolicyUlTargetRatio {
    type int32 {
      range 0..100;
    }
  }
  typedef ddt-Lrat_A2CriticalPCOffsetMCPC_a2CriticalThrRsrpPCOffset {
    type int32 {
      range -100..100;
    }
  }
  typedef ddt-Lrat_GeranCellRelation_timeOfCreation {
    type string {
      length 0..19;
    }
  }
  typedef ddt-Lrat_EUtranCellFDD_ttiBundlingSwitchThres {
    type int32 {
      range -150..250;
    }
  }
  typedef ddt-Lrat_TermPointToENB_ipAddress {
    type string {
      length 7..15;
    }
  }
  typedef ddt-Lrat_SubscriberGroupProfile_pZeroNominalPuschOffset {
    type int32 {
      range -10..20;
    }
  }
  typedef ddt-Lrat_EUtranFrequency_excludeAdditionalFreqBandList {
    type int32 {
      range 1..256;
    }
  }
  typedef ddt-Lrat_ReportConfigSearch_timeToTriggerA2Critical {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_CarrierAggregationFunction_sCellActDeactDataThresHyst {
    type int32 {
      range 0..5000;
    }
  }
  typedef ddt-Lrat_EUtranCellFDD_modificationPeriodCoeff {
    type int32 {
      range "2..2 | 4..4 | 8..8 | 16..16";
    }
  }
  typedef ddt-Lrat_NbIotCell_dlAnchPrbIndex {
    type int32 {
      range "-10..110 | 255..255";
    }
  }
  typedef ddt-Lrat_EUtranCellFDD_dlFrequencyAllocationProportion {
    type int32 {
      range 0..100;
    }
  }
  typedef ddt-Lrat_TacSvAndSnRange_maxSv {
    type int32 {
      range 0..98;
    }
  }
  typedef ddt-Lrat_TermPointToGNB_ipAddress {
    type string {
      length 7..15;
    }
  }
  typedef ddt-Lrat_EUtranCellTDD_prsConfigIndex {
    type int32 {
      range -1..4095;
    }
  }
  typedef ddt-Lrat_EUtranCellTDD_dynLoadCtrlMinNewConn {
    type int32 {
      range 1..110;
    }
  }
  typedef ddt-Lrat_TermPointToMme_domainName {
    type string {
      length 0..255;
    }
  }
  typedef ddt-Lrat_EUtranCellTDD_minBestCellHoAttempts {
    type int32 {
      range 1..10;
    }
  }
  typedef ddt-Lrat_ENodeBFunction_timePhaseMaxDevIeNBUlComp {
    type int32 {
      range 9..100;
    }
  }
  typedef ddt-Lrat_GeranFreqGroup_frequencyGroupId {
    type int32 {
      range 0..1024;
    }
  }
  typedef ddt-Lrat_ReportConfigB2Cdma2000_hysteresisB2RsrqOffset {
    type int32 {
      range -150..150;
    }
  }
  typedef ddt-Lrat_ENodeBFunction_tddVoipDrxProfileId {
    type int32 {
      range -1..17;
    }
  }
  typedef ddt-Lrat_EUtranCellTDD_dlPowerRatio {
    type int32 {
      range 10..100;
    }
  }
  typedef ddt-Lrat_TacSvAndSnRange_maxSn {
    type int32 {
      range 0..99;
    }
  }
  typedef ddt-Lrat_ReportConfigSearch_a2OuterSearchThrRsrpOffset {
    type int32 {
      range -100..0;
    }
  }
  typedef ddt-Lrat_EUtranCellTDD_nonCaF3ResCollisionThresh {
    type int32 {
      range 1..100;
    }
  }
  typedef ddt-Lrat_PmFlexCounterFilter_uePowerClassFilterMax {
    type int32 {
      range 1..5;
    }
  }
  typedef ddt-Lrat_AdmissionControl_ulAdmOverloadThr {
    type int32 {
      range 0..1000;
    }
  }
  typedef ddt-Lrat_ReportConfigEUtraInterFreqPm_a5Threshold1RsrpPm {
    type int32 {
      range -140..-44;
    }
  }
  typedef ddt-Lrat_Rcs_tInactivityTimerBr {
    type int32 {
      range 0..86400;
    }
  }
  typedef ddt-Lrat_PlmnIdentityRO_mnc {
    type int32 {
      range 0..999;
    }
  }
  typedef ddt-Lrat_EUtranCellRelation_timeOfLastModification {
    type string {
      length 0..19;
    }
  }
  typedef ddt-Lrat_QciProfilePredefined_inactivityTimerOffset {
    type int32 {
      range 0..65535;
    }
  }
  typedef ddt-Lrat_AnrFunctionUtran_anrUtranMeasReportMin {
    type int32 {
      range 0..1000;
    }
  }
  typedef ddt-Lrat_ReportConfigA1Prim_timeToTriggerA1Prim {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_PmFlexCounterFilter_plmnFilterMax {
    type int32 {
      range 0..5;
    }
  }
  typedef ddt-Lrat_ReportConfigEUtraBadCovSec_timeToTriggerA2Sec {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_A5PCOffsetMCPC_a5Thr1RsrqPCOffset {
    type int32 {
      range -240..240;
    }
  }
  typedef ddt-Lrat_ReportConfigSearch_a2CriticalThrQci1RsrqOffset {
    type int32 {
      range -240..240;
    }
  }
  typedef ddt-Lrat_ReportConfigEUtraIntraFreqPm_a5ThresholdRsrqPm1 {
    type int32 {
      range -195..-30;
    }
  }
  typedef ddt-Lrat_ReportConfigEUtraIntraFreqPm_a5ThresholdRsrqPm2 {
    type int32 {
      range -195..-30;
    }
  }
  typedef ddt-Lrat_MeasReportConfigParams_b2Threshold1RsrpUtraOffset {
    type int32 {
      range -100..100;
    }
  }
  typedef ddt-Lrat_SubFrameConfig_sfAllocationFourFrame {
    type int32 {
      range 0..16777215;
    }
  }
  typedef ddt-Lrat_BlackListEntry_physicalLayerSubCellId {
    type int32 {
      range -1..2;
    }
  }
  typedef ddt-Lrat_MobilityParams1xRtt_maxNumAltServiceOption {
    type int32 {
      range 0..7;
    }
  }
  typedef ddt-Lrat_ExternalEUtranCellFDD_physicalLayerCellIdGroup {
    type int32 {
      range 0..167;
    }
  }
  typedef ddt-Lrat_GeranFreqGroupRelation_altCsfbTargetPrio {
    type int32 {
      range -1..7;
    }
  }
  typedef ddt-Lrat_EUtranFreqRelation_nonPlannedPciCIO {
    type int32 {
      range "-24..-24 | -22..-22 | -20..-20 | -18..-18 | -16..-16 | -14..-14 | -12..-12 | -10..-10 | -8..-8 | -6..-6 | -5..-5 | -4..-4 | -3..-3 | -2..-2 | -1..-1 | 0..0 | 1..1 | 2..2 | 3..3 | 4..4 | 5..5 | 6..6 | 8..8 | 10..10 | 12..12 | 14..14 | 16..16 | 18..18 | 20..20 | 22..22 | 24..24";
    }
  }
  typedef ddt-Lrat_UtranFreqRelation_threshXLowQ {
    type int32 {
      range 0..31;
    }
  }
  typedef ddt-Lrat_EUtranCellTDD_eranUlCompUserSelSinrHys {
    type int32 {
      range 10..50;
    }
  }
  typedef ddt-Lrat_RATFreqPrio_spidList {
    type int32 {
      range "-1000..-1000 | 1..256";
    }
  }
  typedef ddt-Lrat_LoadBalancingFunction_lbHitRateEUtranMeasUeThreshold {
    type int32 {
      range 1..1000;
    }
  }
  typedef ddt-Lrat_EUtranCellFDD_pdcchOuterLoopUpStep {
    type int32 {
      range 0..100;
    }
  }
  typedef ddt-Lrat_EUtranCellTDD_ulHarqVolteBlerTarget {
    type int32 {
      range 0..10;
    }
  }
  typedef ddt-Lrat_QciProfilePredefined_qci {
    type int32 {
      range "0..9 | 65..65 | 66..66 | 69..69 | 70..70";
    }
  }
  typedef ddt-Lrat_AnrFunction_maxTimeEventBasedPciConf {
    type int32 {
      range 0..1440;
    }
  }
  typedef ddt-Lrat_ReportConfigEUtraIFBestCell_hysteresisA3 {
    type int32 {
      range 0..150;
    }
  }
  typedef ddt-Lrat_QciProfileOperatorDefined_relativePriority {
    type int32 {
      range 1..65535;
    }
  }
  typedef ddt-Lrat_QciProfilePredefined_ulMinBitRate {
    type int32 {
      range 0..75000;
    }
  }
  typedef ddt-Lrat_ReportConfigB2Utra_b2Threshold2RscpUtra {
    type int32 {
      range -120..-24;
    }
  }
  typedef ddt-Lrat_NotificationConfig_notificationConfigurationPriority {
    type int32 {
      range 0..7;
    }
  }
  typedef ddt-Lrat_ReportConfigB2Geran_timeToTriggerB2Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_QciProfileOperatorDefined_pdb {
    type int32 {
      range 0..500;
    }
  }
  typedef ddt-Lrat_ExternalENodeBFunction_masterEnbFunctionId {
    type string {
      length 0..128;
    }
  }
  typedef ddt-Lrat_LoadBasedCaMsrThr_cceUtilThreshLow {
    type int32 {
      range 0..100;
    }
  }
  typedef ddt-Lrat_EUtranCellTDD_qRxLevMinOffset {
    type int32 {
      range "2..16 | 1000..1000";
    }
  }
  typedef ddt-Lrat_ReportConfigB2UtraUlTrig_timeToTriggerB2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_LoadBalancingFunction_lbMeasScalingLimit {
    type int32 {
      range 1..100;
    }
  }
  typedef ddt-Lrat_QciProfilePredefined_qciSubscriptionQuanta {
    type int32 {
      range 0..50000;
    }
  }
  typedef ddt-Lrat_Cdma2000Freq_freqCdma {
    type int32 {
      range 0..2047;
    }
  }
  typedef ddt-Lrat_ExternalGUtranCell_physicalLayerCellIdGroup {
    type int32 {
      range 0..335;
    }
  }
  typedef ddt-Lrat_UtranFreqToQciProfileRelation_b2Thr2EcNoUtraFreqQciOffset {
    type int32 {
      range -50..50;
    }
  }
  typedef ddt-Lrat_TimerProfile_tRrcConnReest {
    type int32 {
      range 1..20;
    }
  }
  typedef ddt-Lrat_IdleModePrioAtRelease_lowLoadThreshold {
    type int32 {
      range 0..16000;
    }
  }
  typedef ddt-Lrat_ENodeBFunction_gtpuErrorIndicationDscp {
    type int32 {
      range 0..63;
    }
  }
  typedef ddt-Lrat_SectorCarrier_ulForcedTimingAdvanceCommand {
    type int32 {
      range 0..10;
    }
  }
  typedef ddt-Lrat_MeasReportConfigParams_a5Threshold1RsrqOffset {
    type int32 {
      range -240..240;
    }
  }
  typedef ddt-Lrat_NbIotCell_freqBand {
    type int32 {
      range 1..256;
    }
  }
  typedef ddt-Lrat_Cdma20001xRttFreqRelation_csFallbackPrioEC {
    type int32 {
      range 0..7;
    }
  }
  typedef ddt-Lrat_ReportConfigB1Utra_hysteresisB1 {
    type int32 {
      range 0..150;
    }
  }
  typedef ddt-Lrat_ResourcePartitionGroupMember_resourcePartitionShare {
    type int32 {
      range 0..100;
    }
  }
  typedef ddt-Lrat_QciProfilePredefined_dlMaxWaitingTime {
    type int32 {
      range 0..500;
    }
  }
  typedef ddt-Lrat_EUtranCellTDD_hoOptStatNum {
    type int32 {
      range 1..32767;
    }
  }
  typedef ddt-Lrat_UnlicensedAccessFunction_laaLbtCheckTimer {
    type int32 {
      range 1..1800;
    }
  }
  typedef ddt-Lrat_Band46UnlicensedProfile_b46B48690MaxPower {
    type int32 {
      range 0..30;
    }
  }
  typedef ddt-Lrat_TermPointToSGW_usedIpAddress {
    type string {
      length 2..39;
    }
  }
  typedef ddt-EUtranCellTDD_setCbrsTxExpireTime_transmitExpireTime {
    type int32;
  }
  typedef ddt-Lrat_CsfbRegParams1xRtt_registrationZone {
    type int32 {
      range 0..4095;
    }
  }
  typedef ddt-Lrat_GeranFreqGroupRelation_qRxLevMin {
    type int32 {
      range -115..-25;
    }
  }
  typedef ddt-Lrat_EUtranCellTDD_cellRange {
    type int32 {
      range 1..100;
    }
  }
  typedef ddt-Lrat_ReportConfigSCellA4_a4ThresholdRsrp {
    type int32 {
      range -140..-44;
    }
  }
  typedef ddt-Lrat_QciProfileOperatorDefined_ulMaxWaitingTime {
    type int32 {
      range 0..500;
    }
  }
  typedef ddt-Lrat_ReportConfigSCellA4_a4ThresholdRsrq {
    type int32 {
      range -195..-30;
    }
  }
  typedef ddt-Lrat_EUtranCellTDD_rtpTimeout {
    type int32 {
      range 1..15;
    }
  }
  typedef ddt-Lrat_EUtranCellFDD_noOfEnhAdptReTxCand {
    type int32 {
      range -1..5;
    }
  }
  typedef ddt-Lrat_ReportConfigEUtraInterFreqLb_hysteresisA5 {
    type int32 {
      range 0..150;
    }
  }
  typedef ddt-Lrat_RlfProfile_t301 {
    type int32 {
      range "100..100 | 200..200 | 300..300 | 400..400 | 600..600 | 1000..1000 | 1500..1500 | 2000..2000";
    }
  }
  typedef ddt-Lrat_ReportConfigSearch_timeToTriggerA2OutSearchRsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_ReportConfigEUtraIntraFreqPm_a1ThresholdRsrpPm {
    type int32 {
      range -140..-44;
    }
  }
  typedef ddt-Lrat_ReportConfigSearch_timeToTriggerA2CriticalRsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_SubscriberGroupProfile_caRateAdjustCoeff {
    type int32 {
      range -1..10;
    }
  }
  typedef ddt-Lrat_BbLink_remotePort {
    type string {
      length 0..128;
    }
  }
  typedef ddt-Lrat_EUtranCellFDD_deallocTimerPucchFormat1 {
    type int32 {
      range 0..36000;
    }
  }
  typedef ddt-Lrat_ReportConfigA5Anr_a5Threshold1RsrpAnrDelta {
    type int32 {
      range -10..10;
    }
  }
  typedef ddt-Lrat_NbIotCell_ceLevelNumber {
    type int32 {
      range 1..3;
    }
  }
  typedef ddt-Lrat_NbIotFrequencyInfo_qQualMin {
    type int32 {
      range "-34..-3 | 0..0";
    }
  }
  typedef ddt-Lrat_EUtranFreqRelation_a3RsrpFreqOffsetAdjustment {
    type int32 {
      range -150..150;
    }
  }
  typedef ddt-Lrat_Cdma2000FreqRelation_b2Thr2Cdma2000FreqOffset {
    type int32 {
      range -250..250;
    }
  }
  typedef ddt-Lrat_EUtranFrequency_additionalFreqBandList {
    type int32 {
      range 1..256;
    }
  }
  typedef ddt-Lrat_ENodeBFunction_s1GtpuEchoInterval {
    type int32 {
      range "100..100 | 1000..1000";
    }
  }
  typedef ddt-Lrat_EUtranCellTDD_tUeBlockingTimer {
    type int32 {
      range 50..200;
    }
  }
  typedef ddt-Lrat_EUtranCellTDD_allocTimerPucchFormat1 {
    type int32 {
      range 0..36000;
    }
  }
  typedef ddt-Lrat_RlfProfile_t311 {
    type int32 {
      range "1000..1000 | 3000..3000 | 5000..5000 | 10000..10000 | 15000..15000 | 20000..20000 | 30000..30000";
    }
  }
  typedef ddt-Lrat_RlfProfile_t310 {
    type int32 {
      range "0..0 | 50..50 | 100..100 | 200..200 | 500..500 | 1000..1000 | 2000..2000";
    }
  }
  typedef ddt-Lrat_EutranCellCorner_cornerLongitude {
    type int32 {
      range -180000000..180000000;
    }
  }
  typedef ddt-Lrat_ReportConfigEUtraInterFreqPm_maxReportCellsPm {
    type int32 {
      range 1..8;
    }
  }
  typedef ddt-Lrat_CellSleepNodeFunction_csmEutranInterFMeasReportDecr {
    type int32 {
      range 0..1000;
    }
  }
  typedef ddt-Lrat_EUtranCellFDD_noOfPucchFormat1PrbPairsPerFrame {
    type int32 {
      range 0..1000;
    }
  }
  typedef ddt-Lrat_PmchMch_userLabel {
    type string {
      length 1..128;
    }
  }
  typedef ddt-Lrat_EUtranCellTDD_physicalLayerSubCellId {
    type int32 {
      range 0..2;
    }
  }
  typedef ddt-Lrat_EUtranCellTDD_maxSoftLockBackoffTime {
    type int32 {
      range 10..90;
    }
  }
  typedef ddt-Lrat_UeMeasControl_maxNoMeasReportsInact {
    type int32 {
      range 0..100;
    }
  }
  typedef ddt-Lrat_PmchMch_sfAllocEnd {
    type int32 {
      range -1..1535;
    }
  }
  typedef ddt-Lrat_ENodeBFunction_dscpLabel {
    type int32 {
      range 0..63;
    }
  }
  typedef ddt-Lrat_ImeisvProfile_elcPreHeatingLength {
    type int32 {
      range 1..7;
    }
  }
  typedef ddt-Lrat_MeasReportConfigParams_a3InterOffsetAdjustmentRsrq {
    type int32 {
      range -150..150;
    }
  }
  typedef ddt-Lrat_MeasReportConfigParams_a3InterOffsetAdjustmentRsrp {
    type int32 {
      range -150..150;
    }
  }
  typedef ddt-Lrat_EUtranCellFDD_pdschTypeBGain {
    type int32 {
      range "0..0 | 1..1 | 2..2 | 3..3";
    }
  }
  typedef ddt-Lrat_PreschedulingProfile_preschedulingPeriod {
    type int32 {
      range 1..20;
    }
  }
  typedef ddt-Lrat_ReportConfigA5_hysteresisA5RsrqOffset {
    type int32 {
      range -150..150;
    }
  }
  typedef ddt-Lrat_CellSleepFunction_covCellRrcConnEstAttMin {
    type int32 {
      range 0..100000;
    }
  }
  typedef ddt-Lrat_MobilityParams1xRtt_protocolRev {
    type int32 {
      range 0..255;
    }
  }
  typedef ddt-Lrat_GUtranSyncSignalFrequency_userLabel {
    type string {
      length 1..128;
    }
  }
  typedef ddt-Lrat_ExternalUtranCellFDD_rac {
    type int32 {
      range -1..255;
    }
  }
  typedef ddt-Lrat_EUtranCellTDD_lbabThreshTimeHigh {
    type int32 {
      range 0..4095;
    }
  }
  typedef ddt-Lrat_SubscriberGroupProfile_qciOffsetForQCI9 {
    type int32 {
      range 0..247;
    }
  }
  typedef ddt-Lrat_EUtranCellFDD_pdcchOuterLoopUpStepPCell {
    type int32 {
      range 0..100;
    }
  }
  typedef ddt-Lrat_EUtranCellTDD_validDlBrSubframes {
    type int32 {
      range 0..1023;
    }
  }
  typedef ddt-Lrat_EUtranCellFDD_eranUlCompUserSelSinrThr {
    type int32 {
      range -150..400;
    }
  }
  typedef ddt-Lrat_EUtranFreqRelation_arpPrio {
    type int32 {
      range -1..7;
    }
  }
  typedef ddt-Lrat_EUtranCellTDD_serviceAreaId {
    type int32 {
      range 0..65535;
    }
  }
  typedef ddt-Lrat_LogicalChannelGroup_userLabel {
    type string {
      length 1..128;
    }
  }
  typedef ddt-Lrat_SubscriberGroupProfile_qciOffsetForQCI6 {
    type int32 {
      range "0..0 | 4..250";
    }
  }
  typedef ddt-Lrat_B2UtranPCOffsetMCPC_b2Thr1RsrpUtranPCOffset {
    type int32 {
      range -100..100;
    }
  }
  typedef ddt-Lrat_SubscriberGroupProfile_qciOffsetForQCI7 {
    type int32 {
      range "0..0 | 3..249";
    }
  }
  typedef ddt-Lrat_ReportConfigSearch_a1a2SearchThresholdRsrq {
    type int32 {
      range -195..-30;
    }
  }
  typedef ddt-Lrat_SubscriberGroupProfile_qciOffsetForQCI8 {
    type int32 {
      range "0..0 | 2..248";
    }
  }
  typedef ddt-Lrat_ReportConfigSearch_a1a2SearchThresholdRsrp {
    type int32 {
      range -140..-44;
    }
  }
  typedef ddt-Lrat_EUtranCellFDD_lbabMinBarringFactor {
    type int32 {
      range 0..100;
    }
  }
  typedef ddt-Lrat_AnrFunctionUtran_anrUtranMeasReportDecr {
    type int32 {
      range 0..1000;
    }
  }
  typedef ddt-Lrat_CarrierAggregationFunction_sCellDeactProhibitTimer {
    type int32 {
      range 0..5000;
    }
  }
  typedef ddt-Lrat_CellSleepFunction_sleepProhibitStartTime {
    type string {
      length 0..19;
    }
  }
  typedef ddt-Lrat_PmFlexCounterFilter_plmnFilterMin {
    type int32 {
      range 0..5;
    }
  }
  typedef ddt-Lrat_GeranFreqRelQciB2ThrOffsets_b2Thr2GeranFreqQciOffset {
    type int32 {
      range -24..24;
    }
  }
  typedef ddt-Lrat_ReportConfigCsfbGeran_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_CellSleepFunction_covCellWakeUpMonitorDurTimer {
    type int32 {
      range 5..120;
    }
  }
  typedef ddt-Lrat_AnrFunctionGeran_anrGeranMeasReportMin {
    type int32 {
      range 0..1000;
    }
  }
  typedef ddt-Lrat_ResourcePartition_spidList {
    type int32 {
      range 0..256;
    }
  }
  typedef ddt-Lrat_NbIotCell_pZeroNominalNPusch {
    type int32 {
      range -126..24;
    }
  }
  typedef ddt-Lrat_EUtranFreqRelation_nonPlannedPhysCellId {
    type int32 {
      range "0..503 | 1000..1000";
    }
  }
  typedef ddt-Lrat_ReportConfigEUtraInterFreqPm_a4ThresholdRsrqPm {
    type int32 {
      range -195..-30;
    }
  }
  typedef ddt-Lrat_PlmnIdentityRO_mcc {
    type int32 {
      range 0..999;
    }
  }
  typedef ddt-Lrat_AnrFunctionUtran_anrUtranMeasReportMax {
    type int32 {
      range 0..1000;
    }
  }
  typedef ddt-Lrat_EUtranFreqToQciProfileRelation_lbA5Threshold2RsrqOffset {
    type int32 {
      range 0..240;
    }
  }
  typedef ddt-Lrat_InstantUplinkAccess_iuaInactivityTimer {
    type int32 {
      range 0..500;
    }
  }
  typedef ddt-Lrat_CarrierAggregationFunction_sCellActProhibitTimer {
    type int32 {
      range 0..5000;
    }
  }
  typedef ddt-Lrat_EndcProfilePredefined_userLabelPredefined {
    type string {
      length 1..128;
    }
  }
  typedef ddt-Lrat_UtranTDDFreqRelation_connectedModeMobilityPrio {
    type int32 {
      range -1..7;
    }
  }
  typedef ddt-Lrat_ReportConfigSearch_timeToTriggerA2Search {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_SIB6_tReselectionUtraSfMedium {
    type int32 {
      range 25..100;
    }
  }
  typedef ddt-Lrat_EUtranCellTDD_tTimeAlignmentTimer {
    type int32 {
      range "0..0 | 500..500 | 750..750 | 1280..1280 | 1920..1920 | 2560..2560 | 5120..5120 | 10240..10240";
    }
  }
  typedef ddt-Lrat_UtranTDDFreqRelation_b2Thr1RsrpUtraFreqOffset {
    type int32 {
      range -100..100;
    }
  }
  typedef ddt-Lrat_QciProfilePredefined_pdcpSNLength {
    type int32 {
      range "7..7 | 12..12 | 15..15";
    }
  }
  typedef ddt-Lrat_AnrFunctionEUtran_anrUesEUtraIntraFDecr {
    type int32 {
      range 0..1000;
    }
  }
  typedef ddt-Lrat_EUtranCellFDD_alpha {
    type int32 {
      range "0..0 | 4..4 | 5..5 | 6..6 | 7..7 | 8..8 | 9..9 | 10..10";
    }
  }
  typedef ddt-Lrat_QciProfileOperatorDefined_rlfPriority {
    type int32 {
      range 0..100;
    }
  }
  typedef ddt-Lrat_CarrierAggregationFunction_dcSCellActDeactDataThresHyst {
    type int32 {
      range 0..5000;
    }
  }
  typedef ddt-Lrat_EUtranCellTDD_interEnbUlCompUserSelSinrHys {
    type int32 {
      range 10..50;
    }
  }
  typedef ddt-Lrat_EUtranCellTDD_earfcn {
    type int32 {
      range 36000..262143;
    }
  }
  typedef ddt-Lrat_EUtranCellRelation_cellIndividualOffsetEUtran {
    type int32 {
      range "-24..-24 | -22..-22 | -20..-20 | -18..-18 | -16..-16 | -14..-14 | -12..-12 | -10..-10 | -8..-8 | -6..-6 | -5..-5 | -4..-4 | -3..-3 | -2..-2 | -1..-1 | 0..0 | 1..1 | 2..2 | 3..3 | 4..4 | 5..5 | 6..6 | 8..8 | 10..10 | 12..12 | 14..14 | 16..16 | 18..18 | 20..20 | 22..22 | 24..24";
    }
  }
  typedef ddt-Lrat_AtoConfig_minSuccRateThreshold {
    type int32 {
      range 0..100;
    }
  }
  typedef ddt-Lrat_CarrierAggregationFunction_laaSCellActDeactDataThres {
    type int32 {
      range 0..5000;
    }
  }
  typedef ddt-Lrat_ReportConfigInterRatPm_hysteresisPm {
    type int32 {
      range 0..150;
    }
  }
  typedef ddt-Lrat_Band46UnlicensedProfile_b46D53740MaxPower {
    type int32 {
      range 0..30;
    }
  }
  typedef ddt-Lrat_EUtranCellTDD_catmMbmsDlSubframes {
    type int32 {
      range 0..2;
    }
  }
  typedef ddt-Lrat_EUtranCellTDD_advCellSupSensitivity {
    type int32 {
      range 0..100;
    }
  }
  typedef ddt-Lrat_ExternalENodeBFunction_eNBId {
    type int32 {
      range 0..1048575;
    }
  }
  typedef ddt-Lrat_AnrFunctionUtran_cellAddEcNoThresholdUtranDelta {
    type int32 {
      range -100..100;
    }
  }
  typedef ddt-Lrat_Band46UnlicensedProfile_b46C52490MaxPower {
    type int32 {
      range 0..30;
    }
  }
  typedef ddt-Lrat_PreschedProfile_preschedulingPeriod {
    type int32 {
      range 1..20;
    }
  }
  typedef ddt-Lrat_EUtranCellTDD_siWindowLength {
    type int32 {
      range "1..1 | 2..2 | 5..5 | 10..10 | 15..15 | 20..20 | 40..40";
    }
  }
  typedef ddt-EUtranCellTDD_changeFrequency_earfcn {
    type int32 {
      range 36000..262143;
    }
  }
  typedef ddt-Lrat_CarrierAggregationFunction_laaSCellDeactProhibitTimer {
    type int32 {
      range 0..5000;
    }
  }
  typedef ddt-Lrat_EUtranCellFDD_ulSCellPriority {
    type int32 {
      range 0..5;
    }
  }
  typedef ddt-Lrat_ReportConfigB2Utra_hysteresisB2RsrqOffset {
    type int32 {
      range -150..150;
    }
  }
  typedef ddt-Lrat_CellPortion_lppaCellPortionId {
    type int32 {
      range 0..255;
    }
  }
  typedef ddt-Lrat_GlobalEnbId_enbId {
    type int32 {
      range 0..1048575;
    }
  }
  typedef ddt-Lrat_FreqPrioUTRAN_altCsfbTargetPrio {
    type int32 {
      range "-1000..-1000 | -1..7";
    }
  }
  typedef ddt-Lrat_ParameterChangeRequestRO_timeOfChange {
    type string {
      length 0..19;
    }
  }
  typedef ddt-Lrat_HoWhiteList_spidList {
    type int32 {
      range "-1000..-1000 | 1..256";
    }
  }
  typedef ddt-Lrat_UnlicensedAccessFunction_laaDrsOffset {
    type int32 {
      range 0..159;
    }
  }
  typedef ddt-Lrat_ReportConfigB2Cdma2000_timeToTriggerB2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_ExternalGeranCell_timeOfCreation {
    type string {
      length 0..19;
    }
  }
  typedef ddt-Lrat_SIB6_tReselectionUtraSfHigh {
    type int32 {
      range 25..100;
    }
  }
  typedef ddt-Lrat_MeasReportConfigParams_a5Threshold2RsrqOffset {
    type int32 {
      range -240..240;
    }
  }
  typedef ddt-Lrat_EUtranCellFDD_maxNoClusteredPuschAlloc {
    type int32 {
      range 0..5;
    }
  }
  typedef ddt-Lrat_PmFlexCounterFilter_uePowerClassFilterMin {
    type int32 {
      range 1..5;
    }
  }
  typedef ddt-Lrat_SectorCarrier_virtualComChBeamfrmWtsAmplitude {
    type int32 {
      range 0..100;
    }
  }
  typedef ddt-Lrat_AnrFunctionEUtran_anrUesThreshInterFMax {
    type int32 {
      range 0..100;
    }
  }
  typedef ddt-Lrat_Cgi_mnc {
    type int32 {
      range 0..999;
    }
  }
  typedef ddt-Lrat_ExternalGeranCell_masterGeranCellId {
    type string {
      length 0..128;
    }
  }
  typedef ddt-Lrat_EUtranFreqRelation_hybridCsgPhysCellIdRange {
    type int32 {
      range 1..504;
    }
  }
  typedef ddt-Lrat_EUtranCellTDD_lbabThreshRejectRateLow {
    type int32 {
      range 0..1000;
    }
  }
  typedef ddt-Lrat_SIB8_tReselectionCdma1xRttSfMedium {
    type int32 {
      range 25..100;
    }
  }
  typedef ddt-Lrat_B2Cdma2000PCOffsetMCPC_b2Thr1RsrpCdma2000PCOffset {
    type int32 {
      range -100..100;
    }
  }
  typedef ddt-Lrat_EUtranCellFDD_dlPowerChangeRate {
    type int32 {
      range 1..10;
    }
  }
  typedef ddt-Lrat_ReportConfigEUtraBadCovPrim_a2ThresholdRsrqPrim {
    type int32 {
      range -195..-30;
    }
  }
  typedef ddt-Lrat_PrefTrafficMgmt_plmnUnresOpUseSRatioThreshold {
    type int32 {
      range 0..1600;
    }
  }
  typedef ddt-Lrat_QciProfilePredefined_relativePriority {
    type int32 {
      range 1..65535;
    }
  }
  typedef ddt-Lrat_GeranFreqGroupRelation_cellReselectionPriority {
    type int32 {
      range 0..7;
    }
  }
  typedef ddt-Lrat_Tmgi_mncLength {
    type int32 {
      range 2..3;
    }
  }
  typedef ddt-Lrat_MbsfnSubframeConfigRO_subframeAllocationOneFrame {
    type string {
      length 6..6;
    }
  }
  typedef ddt-Lrat_FreqPrioUTRAN_csFallbackPrio {
    type int32 {
      range "-1000..-1000 | -1..7";
    }
  }
  typedef ddt-Lrat_ReportConfigSCellA4_timeToTriggerA4 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_Tmgi_mnc {
    type int32 {
      range 0..999;
    }
  }
  typedef ddt-Lrat_MeasReportConfigParams_a1ThresholdRsrpPrimOffset {
    type int32 {
      range -100..100;
    }
  }
  typedef ddt-Lrat_ExternalUtranCellFDD_timeOfLastModification {
    type string {
      length 0..19;
    }
  }
  typedef ddt-Lrat_BlackListEntry_range {
    type int32 {
      range "1..1 | 4..4 | 8..8 | 12..12 | 16..16 | 24..24 | 32..32 | 48..48 | 64..64 | 84..84 | 96..96 | 128..128 | 168..168 | 252..252 | 504..504";
    }
  }
  typedef ddt-Lrat_UeMeasControl_a5B2MobilityTimer {
    type int32 {
      range 0..120000;
    }
  }
  typedef ddt-Lrat_MeasReportConfigParams_b2Threshold1RsrqCdma2000Offset {
    type int32 {
      range -240..240;
    }
  }
  typedef ddt-Lrat_UtranTDDFreqRelation_pMaxUtra {
    type int32 {
      range -50..33;
    }
  }
  typedef ddt-Lrat_QciProfileOperatorDefined_qciACTuning {
    type int32 {
      range 1..1999;
    }
  }
  typedef ddt-Lrat_Cdma20001xRttFreqRelation_b2Thr1RsrqCdma20001xFreqOffset {
    type int32 {
      range -240..240;
    }
  }
  typedef ddt-Lrat_Band46UnlicensedProfile_b46C50690MaxPower {
    type int32 {
      range 0..30;
    }
  }
  typedef ddt-Lrat_SIB3_nCellChangeMedium {
    type int32 {
      range 1..16;
    }
  }
  typedef ddt-Lrat_EUtranCellFDD_physicalLayerSubCellId {
    type int32 {
      range 0..2;
    }
  }
  typedef ddt-Lrat_EUtranCellTDD_ulDynUeAdmCtrlOverloadThr {
    type int32 {
      range 0..1000;
    }
  }
  typedef ddt-Lrat_EUtranCellFDD_noOfPucchFormat2PrbPairsPerFrame {
    type int32 {
      range 0..1000;
    }
  }
  typedef ddt-Lrat_EUtranCellFDD_hoOptAdjThresholdPercQci1 {
    type int32 {
      range 0..1000;
    }
  }
  typedef ddt-Lrat_QciProfileOperatorDefined_ulMaxHARQTxQci {
    type int32 {
      range "1..1 | 2..2 | 3..3 | 4..4 | 5..5 | 6..6 | 7..7";
    }
  }
  typedef ddt-Lrat_SubscriberGroupProfile_userLabel {
    type string {
      length 1..128;
    }
  }
  typedef ddt-Lrat_TermPointToGNB_ipv6Address {
    type string {
      length 2..39;
    }
  }
  typedef ddt-Lrat_AnrFunction_probCellDetectMedHoSuccThres {
    type int32 {
      range 2..100;
    }
  }
  typedef ddt-Lrat_UnlicensedAccessFunction_laaDrsPeriodicity {
    type int32 {
      range "40..40 | 80..80 | 160..160";
    }
  }
  typedef ddt-Lrat_AcBarringConfig1xRtt_acBarring0to9R9 {
    type int32 {
      range 0..63;
    }
  }
  typedef ddt-Lrat_InstantUplinkAccess_iuaCellResourceLimit {
    type int32 {
      range 1..80;
    }
  }
  typedef ddt-Lrat_EUtranCellFDD_siWindowLength {
    type int32 {
      range "1..1 | 2..2 | 5..5 | 10..10 | 15..15 | 20..20 | 40..40";
    }
  }
  typedef ddt-Lrat_CarrierAggregationFunction_selectionPolicyUlWeighting {
    type int32 {
      range -1..100;
    }
  }
  typedef ddt-Lrat_ReportConfigCsfbUtra_thresholdEcNo {
    type int32 {
      range -245..0;
    }
  }
  typedef ddt-Lrat_EUtranCellFDD_tTimeAlignmentTimer {
    type int32 {
      range "0..0 | 500..500 | 750..750 | 1280..1280 | 1920..1920 | 2560..2560 | 5120..5120 | 10240..10240";
    }
  }
  typedef ddt-Lrat_EUtranCellTDD_lbabDecr {
    type int32 {
      range 5..100;
    }
  }
  typedef ddt-Lrat_EUtranCellTDD_filterUeDlThpTimeThr {
    type int32 {
      range 0..200;
    }
  }
  typedef ddt-Lrat_AcBarringConfig1xRtt_acBarring12R9 {
    type int32 {
      range 0..7;
    }
  }
  typedef ddt-Lrat_Cdma2000FreqBandRelation_cellReselectionPriority {
    type int32 {
      range 0..7;
    }
  }
  typedef ddt-Lrat_UtranFreqRelation_altCsfbTargetPrio {
    type int32 {
      range -1..7;
    }
  }
  typedef ddt-Lrat_ExternalEUtranCellFDD_localCellId {
    type int32 {
      range 0..255;
    }
  }
  typedef ddt-Lrat_EUtranCellTDD_prachFrequencyAllocation {
    type int32 {
      range 0..1;
    }
  }
  typedef ddt-Lrat_SciProfile_dlMinBitRate {
    type int32 {
      range 0..15000;
    }
  }
  typedef ddt-Lrat_ReportConfigB2CdmaUlTrig_b2Threshold2Cdma2000 {
    type int32 {
      range -315..0;
    }
  }
  typedef ddt-Lrat_ReportConfigB2Geran_b2Threshold2Geran {
    type int32 {
      range -110..-47;
    }
  }
  typedef ddt-Lrat_SciProfile_dlRelativePriority {
    type int32 {
      range 1..65535;
    }
  }
  typedef ddt-Lrat_ExternalEUtranCellFDD_csgPhysCellIdRange {
    type int32 {
      range "1..1 | 4..4 | 8..8 | 12..12 | 16..16 | 24..24 | 32..32 | 48..48 | 64..64 | 84..84 | 96..96 | 128..128 | 168..168 | 252..252 | 504..504";
    }
  }
  typedef ddt-Lrat_TrafficModelPrb_bitRatePerQci {
    type int32 {
      range 0..65535;
    }
  }
  typedef ddt-Lrat_EUtranCellFDD_pdcchAdmThreshold {
    type int32 {
      range 0..1000;
    }
  }
  typedef ddt-Lrat_InstantUplinkAccess_iuaSinrThreshold {
    type int32 {
      range -10..20;
    }
  }
  typedef ddt-Lrat_UtranFreqRelation_pMaxUtra {
    type int32 {
      range -50..33;
    }
  }
  typedef ddt-Lrat_AnrFunctionGeran_anrGeranMeasReportMax {
    type int32 {
      range 0..1000;
    }
  }
  typedef ddt-Lrat_ReportConfigEUtraBadCovSec_a2ThresholdRsrpSec {
    type int32 {
      range -140..-44;
    }
  }
  typedef ddt-Lrat_ReportConfigEUtraIntraFreqPm_maxReportCellsPm {
    type int32 {
      range 1..8;
    }
  }
  typedef ddt-Lrat_UtranTDDFreqRelation_b2Thr1RsrqUtraFreqOffset {
    type int32 {
      range -240..240;
    }
  }
  typedef ddt-Lrat_EUtranCellFDD_ulDynUeAdmCtrlRetDiffThr {
    type int32 {
      range 0..1000;
    }
  }
  typedef ddt-Lrat_EUtranCellTDD_gpsTimeSFN0Seconds {
    type int64 {
      range 0..4294967295;
    }
  }
  typedef ddt-Lrat_CarrierAggregationFunction_waitForBetterSCellRep {
    type int32 {
      range -1..32000;
    }
  }
  typedef ddt-Lrat_ReportConfigInterRatPm_maxReportCellsPm {
    type int32 {
      range 1..8;
    }
  }
  typedef ddt-Lrat_EUtranCellTDD_prsMutingPatternLen {
    type int32 {
      range "1..1 | 2..2 | 4..4 | 8..8 | 16..16";
    }
  }
  typedef ddt-Lrat_EUtranFreqRelationUnlicensed_allowedMeasBandwidth {
    type int32 {
      range "6..6 | 15..15 | 25..25 | 50..50 | 75..75 | 100..100";
    }
  }
  typedef ddt-Lrat_EUtranCellFDD_pdcchOuterLoopInitialAdj {
    type int32 {
      range -200..200;
    }
  }
  typedef ddt-Lrat_CandNeighborRelInfoRO_mcc {
    type int32 {
      range 0..999;
    }
  }
  typedef ddt-Lrat_ReportConfigEUtraBestCell_a3offset {
    type int32 {
      range -150..150;
    }
  }
  typedef ddt-Lrat_ResOpUseConfig_unresSRatioThreshold {
    type int32 {
      range 0..1600;
    }
  }
  typedef ddt-Lrat_EUtranCellFDD_allocTimerPucchFormat1 {
    type int32 {
      range 0..36000;
    }
  }
  typedef ddt-Lrat_UeMeasControl_a5MobilityTimerBr {
    type int32 {
      range 0..120000;
    }
  }
  typedef ddt-Lrat_Band46UnlicensedProfile_b46A47490MaxPower {
    type int32 {
      range 0..30;
    }
  }
  typedef ddt-Lrat_SectorCarrier_virtualComChBeamfrmWtsPhase {
    type int32 {
      range 0..359;
    }
  }
  typedef ddt-Lrat_GeranFreqGroupRelation_b2Thr2GeranFreqOffset {
    type int32 {
      range -24..24;
    }
  }
  typedef ddt-Lrat_LoadBalancingFunction_lbCaCapHysteresis {
    type int32 {
      range 0..100;
    }
  }
  typedef ddt-Lrat_IflbConfig_stopIncomingIflbThreshold {
    type int32 {
      range 0..1600;
    }
  }
  typedef ddt-Lrat_DataRadioBearer_tPollRetransmitUl {
    type int32 {
      range "5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500";
    }
  }
  typedef ddt-Lrat_Cdma2000CellRelation_userLabel {
    type string {
      length 1..128;
    }
  }
  typedef ddt-Lrat_EUtranCellFDD_dlDynUeAdmCtrlRetDiffThr {
    type int32 {
      range 0..1000;
    }
  }
  typedef ddt-Lrat_EUtranCellFDD_pdcchOuterLoopInitialAdjPCell {
    type int32 {
      range -200..200;
    }
  }
  typedef ddt-Lrat_PlmnIdentity_mncLength {
    type int32 {
      range 2..3;
    }
  }
  typedef ddt-Lrat_ReportConfigSearch_timeToTriggerA2UlSearch {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_BbLink_localPort {
    type string {
      length 0..128;
    }
  }
  typedef ddt-Lrat_Paging_pagingDiscardTimer {
    type int32 {
      range 1..30;
    }
  }
  typedef ddt-Lrat_ENodeBFunction_maxNoCellsNaccCsfb {
    type int32 {
      range 0..16;
    }
  }
  typedef ddt-Lrat_Rrc_t301NbIot {
    type int32 {
      range "2500..2500 | 4000..4000 | 6000..6000 | 10000..10000 | 15000..15000 | 25000..25000 | 40000..40000 | 60000..60000";
    }
  }
  typedef ddt-Lrat_CarrierAggregationFunction_waitForAdditionalSCellOpportunity {
    type int32 {
      range -1..60000;
    }
  }
  typedef ddt-Lrat_EUtranCellFDD_iuaInterval {
    type int32 {
      range 0..5;
    }
  }
  typedef ddt-Lrat_AnrFunctionGeran_anrGeranMeasReportDecr {
    type int32 {
      range 0..1000;
    }
  }
  typedef ddt-Lrat_ExternalUtranCellFDD_lbUtranCellOffloadCapacity {
    type int32 {
      range 0..1000000;
    }
  }
  typedef ddt-Lrat_FreqPrioUTRAN_connectedModeMobilityPrio {
    type int32 {
      range "-1000..-1000 | -1..7";
    }
  }
  typedef ddt-Lrat_TacSvAndSnRange_minSv {
    type int32 {
      range 0..98;
    }
  }
  typedef ddt-Lrat_AnrFunctionEUtran_anrUesThreshInterFIncrHo {
    type int32 {
      range 0..1000;
    }
  }
  typedef ddt-Lrat_ReportConfigEUtraBadCovPrim_timeToTriggerA2Prim {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_ReportConfigEUtraInterFreqMbms_hysteresisA5 {
    type int32 {
      range 0..150;
    }
  }
  typedef ddt-Lrat_TermPointToMme_mmeCodeListOtherRATs {
    type int32 {
      range -1..255;
    }
  }
  typedef ddt-Lrat_EUtranFreqRelation_caFreqPriority {
    type int32 {
      range -1..7;
    }
  }
  typedef ddt-Lrat_QciProfileOperatorDefined_rlcSNLength {
    type int32 {
      range "5..5 | 10..10 | 16..16";
    }
  }
  typedef ddt-Lrat_TacSvAndSnRange_minSn {
    type int32 {
      range 0..99;
    }
  }
  typedef ddt-Lrat_ReportConfigCsfbCdma2000_hysteresis {
    type int32 {
      range 0..150;
    }
  }
  typedef ddt-Lrat_EUtranCellFDD_latitude {
    type int32 {
      range -90000000..90000000;
    }
  }
  typedef ddt-Lrat_ENodeBFunction_dlMaxWaitingTimeGlobal {
    type int32 {
      range 0..500;
    }
  }
  typedef ddt-Lrat_MeasReportConfigParams_b2Threshold2EcNoUtraOffset {
    type int32 {
      range -50..50;
    }
  }
  typedef ddt-Lrat_EUtranCellRelationUnlicensed_earfcn {
    type int32 {
      range "0..17999 | 46590..262143";
    }
  }
  typedef ddt-Lrat_SectorCarrier_noOfMutedTxAntennas {
    type int32 {
      range 0..7;
    }
  }
  typedef ddt-Lrat_Band46UnlicensedProfile_b46D52740MaxPower {
    type int32 {
      range 0..30;
    }
  }
  typedef ddt-Lrat_ExternalEUtranCellTDD_physicalLayerSubCellId {
    type int32 {
      range 0..2;
    }
  }
  typedef ddt-Lrat_Band46UnlicensedProfile_b46B47890MaxPower {
    type int32 {
      range 0..30;
    }
  }
  typedef ddt-Lrat_EUtranCellTDD_outOfCoverageSrTimerPeriodicity {
    type int32 {
      range "40..40 | 80..80 | 160..160 | 320..320 | 640..640 | 960..960 | 1280..1280";
    }
  }
  typedef ddt-Lrat_Band46UnlicensedProfile_b46C50090MaxPower {
    type int32 {
      range 0..30;
    }
  }
  typedef ddt-Lrat_HoWhiteList_userLabel {
    type string {
      length 1..128;
    }
  }
  typedef ddt-Lrat_ReportConfigSCellA1A2_a1a2ThresholdRsrp {
    type int32 {
      range -140..-44;
    }
  }
  typedef ddt-Lrat_EUtranCellFDD_ns05FullBandUsersInCellThres {
    type int32 {
      range 1..100;
    }
  }
  typedef ddt-Lrat_ReportConfigSCellA1A2_a1a2ThresholdRsrq {
    type int32 {
      range -195..-30;
    }
  }
  typedef ddt-Lrat_FreqGroupPrioGERAN_csFallbackPrioEC {
    type int32 {
      range "-1000..-1000 | -1..7";
    }
  }
  typedef ddt-Lrat_ResOpUseConfig_unresMsrUsageThreshold {
    type int32 {
      range 0..100;
    }
  }
  typedef ddt-Lrat_SIRepetitionNB_siRepetitionSI1 {
    type int32 {
      range "2..2 | 4..4 | 8..8 | 16..16";
    }
  }
  typedef ddt-Lrat_SIRepetitionNB_siRepetitionSI2 {
    type int32 {
      range "2..2 | 4..4 | 8..8 | 16..16";
    }
  }
  typedef ddt-Lrat_EUtranCellFDD_srvccDelayTimer {
    type int32 {
      range 0..30000;
    }
  }
  typedef ddt-Lrat_EUtranFreqToQciProfileRelation_a5Thr1RsrqFreqQciOffset {
    type int32 {
      range -240..240;
    }
  }
  typedef ddt-Lrat_SIRepetitionNB_siRepetitionSI3 {
    type int32 {
      range "2..2 | 4..4 | 8..8 | 16..16";
    }
  }
  typedef ddt-Lrat_SIRepetitionNB_siRepetitionSI4 {
    type int32 {
      range "2..2 | 4..4 | 8..8 | 16..16";
    }
  }
  typedef ddt-Lrat_GeranFreqGroupRelation_qOffsetFreq {
    type int32 {
      range -15..15;
    }
  }
  typedef ddt-Lrat_SIRepetitionNB_siRepetitionSI5 {
    type int32 {
      range "2..2 | 4..4 | 8..8 | 16..16";
    }
  }
  typedef ddt-Lrat_ReportConfigB2Utra_b2Threshold2EcNoUtra {
    type int32 {
      range -245..0;
    }
  }
  typedef ddt-Lrat_AnrFunctionEUtran_anrUesThreshInterFMin {
    type int32 {
      range 0..100;
    }
  }
  typedef ddt-Lrat_EUtranCellFDD_measuredMaxNoOfUsersInCell {
    type int32 {
      range 0..32768;
    }
  }
  typedef ddt-Lrat_ResOpUseConfig_resMsrUsageThreshold {
    type int32 {
      range 0..100;
    }
  }
  typedef ddt-Lrat_EUtranCellFDD_cellSubscriptionCapacity {
    type int32 {
      range 0..1000000;
    }
  }
  typedef ddt-Lrat_NbIotCell_ulAllocatedPrb {
    type int32 {
      range "-10..110 | 255..255";
    }
  }
  typedef ddt-Lrat_SubFrameConfig_subframeAllocation {
    type int32 {
      range "1..1 | 4..4";
    }
  }
  typedef ddt-Lrat_EUtranFreqRelation_csmUeCapMonitorTime {
    type int32 {
      range 0..1440;
    }
  }
  typedef ddt-Lrat_Paging_defaultPagingCycle {
    type int32 {
      range "32..32 | 64..64 | 128..128 | 256..256";
    }
  }
  typedef ddt-Lrat_EUtranCellFDD_qRxLevMinCe {
    type int32 {
      range -140..-44;
    }
  }
  typedef ddt-Lrat_EUtranFreqRelation_csgPhysCellId {
    type int32 {
      range "0..503 | 1000..1000";
    }
  }
  typedef ddt-Lrat_EUtranCellTDD_crsGain {
    type int32 {
      range "-300..-300 | -200..-200 | -100..-100 | 0..0 | 177..177 | 300..300 | 477..477 | 600..600";
    }
  }
  typedef ddt-Lrat_EUtranCellTDD_nonCaHarqAnModeMuxThresh {
    type int32 {
      range 1..100;
    }
  }
  typedef ddt-Lrat_ParameterChangeRequestRO_requestedValue {
    type string {
      length 0..32;
    }
  }
  typedef ddt-Lrat_UeMeasControl_maxUtranCellsToMeasure {
    type int32 {
      range 0..64;
    }
  }
  typedef ddt-Lrat_MbsfnArea_commonSFAllocPeriod {
    type int32 {
      range "4..4 | 8..8 | 16..16 | 32..32 | 64..64 | 128..128 | 256..256";
    }
  }
  typedef ddt-Lrat_EUtranFreqRelation_userLabel {
    type string {
      length 1..128;
    }
  }
  typedef ddt-Lrat_ExternalGeranCell_lac {
    type int32 {
      range "1..65533 | 65535..65535";
    }
  }
  typedef ddt-Lrat_SIB7_tReselectionGeranSfMedium {
    type int32 {
      range 25..100;
    }
  }
  typedef ddt-Lrat_B2Cdma2000PCOffsetMCPC_b2Thr1RsrqCdma2000PCOffset {
    type int32 {
      range -240..240;
    }
  }
  typedef ddt-Lrat_ReportConfigA5Anr_a5Threshold2RsrqAnrDelta {
    type int32 {
      range -10..10;
    }
  }
  typedef ddt-Lrat_ExternalUtranCellFDD_physicalCellIdentity {
    type int32 {
      range 0..511;
    }
  }
  typedef ddt-Lrat_PmEventService_streamPortPmUeTrace {
    type int32 {
      range 0..65535;
    }
  }
  typedef ddt-Lrat_EUtranCellFDD_maxSoftLockBackoffTime {
    type int32 {
      range 10..90;
    }
  }
  typedef ddt-Lrat_PrefTrafficMgmt_lbStopIncomingIflbThreshold {
    type int32 {
      range 0..1600;
    }
  }
  typedef ddt-Lrat_ReportConfigA1A2Br_a1a2UlIntraSearchIntraFThr {
    type int32 {
      range -150..450;
    }
  }
  typedef ddt-Lrat_Cdma20001xRttFreqRelation_userLabel {
    type string {
      length 1..128;
    }
  }
  typedef ddt-Lrat_ReportConfigEUtraInterFreqLb_a5Threshold1Rsrp {
    type int32 {
      range -140..-44;
    }
  }
  typedef ddt-Lrat_EUtranCellFDD_prsMutingPatternLen {
    type int32 {
      range "1..1 | 2..2 | 4..4 | 8..8 | 16..16";
    }
  }
  typedef ddt-Lrat_MeasReportConfigParams_a2ThresholdRsrpPrimOffset {
    type int32 {
      range -100..100;
    }
  }
  typedef ddt-Lrat_EUtranCellFDD_uncertSemiMajor {
    type int32 {
      range 0..127;
    }
  }
  typedef ddt-Lrat_CarrierAggregationFunction_dcSCellActDeactDataThres {
    type int32 {
      range -1..5000;
    }
  }
  typedef ddt-Lrat_EUtranCellTDD_activeServiceAreaId {
    type int32 {
      range 0..65535;
    }
  }
  typedef ddt-Lrat_PmEventService_totalUeTraceStorageSize {
    type int32 {
      range 100..20000;
    }
  }
  typedef ddt-Lrat_Cgi_mcc {
    type int32 {
      range 0..999;
    }
  }
  typedef ddt-Lrat_NbIotCell_ulNonAnchPrbNum {
    type int32 {
      range 0..7;
    }
  }
  typedef ddt-Lrat_ReportConfigB2Geran_b2Threshold1Rsrp {
    type int32 {
      range -140..-44;
    }
  }
  typedef ddt-Lrat_MdtConfiguration_a2ThresholdRsrqMdt {
    type int32 {
      range -195..-30;
    }
  }
  typedef ddt-Lrat_FreqGroupPrioGERAN_altCsfbTargetPrio {
    type int32 {
      range "-1000..-1000 | -1..7";
    }
  }
  typedef ddt-Lrat_EUtranCellFDD_hoOptStatTime {
    type int32 {
      range 1..32767;
    }
  }
  typedef ddt-Lrat_UtranFreqRelation_qQualMin {
    type int32 {
      range -24..0;
    }
  }
  typedef ddt-Lrat_EUtranCellFDD_cellCapMinCellSubCap {
    type int32 {
      range 0..1000000;
    }
  }
  typedef ddt-Lrat_Band46UnlicensedProfile_b46A47290MaxPower {
    type int32 {
      range 0..30;
    }
  }
  typedef ddt-Lrat_AnrFunctionEUtran_anrEutranInterFMeasReportIncr {
    type int32 {
      range 0..1000;
    }
  }
  typedef ddt-Lrat_ReportConfigA1Sec_a1ThresholdRsrpSec {
    type int32 {
      range -140..-44;
    }
  }
  typedef ddt-Lrat_Tmgi_mcc {
    type int32 {
      range 0..999;
    }
  }
  typedef ddt-Lrat_FreqGroupPrioGERAN_connectedModeMobilityPrio {
    type int32 {
      range "-1000..-1000 | -1..7";
    }
  }
  typedef ddt-Lrat_EUtranCellTDD_qQualMin {
    type int32 {
      range "-34..-3 | 0..0";
    }
  }
  typedef ddt-Lrat_ExternalUtranCellTDD_timeOfLastModification {
    type string {
      length 0..19;
    }
  }
  typedef ddt-Lrat_EUtranCellFDD_pMaxServingCell {
    type int32 {
      range "-30..33 | 1000..1000";
    }
  }
  typedef ddt-Lrat_ENodeBFunction_maxNrOfEnbPartnersEranUlComp {
    type int32 {
      range 0..20;
    }
  }
  typedef ddt-Lrat_ReportConfigSearch_hysteresisA1A2UlSearch {
    type int32 {
      range 0..150;
    }
  }
  typedef ddt-Lrat_MeasReportConfigParams_a2ThresholdRsrqPrimOffset {
    type int32 {
      range -240..240;
    }
  }
  typedef ddt-Lrat_ReportConfigB2Geran_b2Threshold1Rsrq {
    type int32 {
      range -195..-30;
    }
  }
  typedef ddt-Lrat_CellSleepFunction_covCellDlPrbWakeUpThreshold {
    type int32 {
      range 0..100;
    }
  }
  typedef ddt-Lrat_MultipleNSPmaxListRO_multiplePmax {
    type int32 {
      range "-30..33 | 1000..1000";
    }
  }
  typedef ddt-Lrat_Band46UnlicensedProfile_b46D52940MaxPower {
    type int32 {
      range 0..30;
    }
  }
  typedef ddt-Lrat_NbIotCell_cmcIndex {
    type int32 {
      range 0..2;
    }
  }
  typedef ddt-Lrat_EUtranCellFDD_lbEUtranAcceptOffloadThreshold {
    type int32 {
      range 0..1600;
    }
  }
  typedef ddt-Lrat_ReportConfigB1GUtra_b1Threshold {
    type int32 {
      range 0..127;
    }
  }
  typedef ddt-Lrat_EUtranFreqRelation_threshXLow {
    type int32 {
      range 0..62;
    }
  }
  typedef ddt-Lrat_EricssonLeanCarrierFunction_elcDrxOnDurationPostHeating {
    type int32 {
      range 0..38;
    }
  }
  typedef ddt-Lrat_SIB3_nCellChangeHigh {
    type int32 {
      range 1..16;
    }
  }
  typedef ddt-Lrat_EUtranFreqRelation_threshXHigh {
    type int32 {
      range 0..62;
    }
  }
  typedef ddt-Lrat_EUtranFreqRelation_hybridCsgPhysCellId {
    type int32 {
      range "0..503 | 1000..1000";
    }
  }
  typedef ddt-Lrat_IdleModePrioAtRelease_lowMediumLoadThreshold {
    type int32 {
      range 0..16000;
    }
  }
  typedef ddt-Lrat_RATFreqPrio_t320 {
    type int32 {
      range "5..5 | 10..10 | 20..20 | 30..30 | 60..60 | 120..120 | 180..180";
    }
  }
  typedef ddt-Lrat_PtmSubscriberGroup_spidList {
    type int32 {
      range "-1..-1 | 0..256";
    }
  }
  typedef ddt-Lrat_EUtranCellFDD_msg3FrequencyAllocationBr {
    type int32 {
      range 0..1;
    }
  }
  typedef ddt-Lrat_CarrierAggregationFunction_sCellActDeactDataThres {
    type int32 {
      range -1..5000;
    }
  }
  typedef ddt-Lrat_EUtranCellTDD_threshServingLow {
    type int32 {
      range 0..62;
    }
  }
  typedef ddt-Lrat_InstantUplinkAccess_iuaSinrDeactHyst {
    type int32 {
      range 0..50;
    }
  }
  typedef ddt-Lrat_UnlicensedAccessFunction_laaMaxOccupancy {
    type int32 {
      range 4..20;
    }
  }
  typedef ddt-Lrat_EUtranCellFDD_ulDynUeAdmCtrlOverloadThr {
    type int32 {
      range 0..1000;
    }
  }
  typedef ddt-Lrat_SciProfile_pdb {
    type int32 {
      range 0..500;
    }
  }
  typedef ddt-Lrat_ReportConfigEUtraInterFreqMbms_a5ThresholdRsrp {
    type int32 {
      range -140..-44;
    }
  }
  typedef ddt-Lrat_ReportConfigSCellA1A2_hysteresisA1A2Rsrq {
    type int32 {
      range 0..150;
    }
  }
  typedef ddt-Lrat_ReportConfigSCellA1A2_hysteresisA1A2Rsrp {
    type int32 {
      range 0..150;
    }
  }
  typedef ddt-Lrat_CellSleepFunction_capCellDlPrbSleepThreshold {
    type int32 {
      range 0..100;
    }
  }
  typedef ddt-Lrat_ReportConfigA1A2Br_timeToTriggerA2UlIntraFSearch {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_SIB8_tReselectionCdma1xRttSfHigh {
    type int32 {
      range 25..100;
    }
  }
  typedef ddt-Lrat_UtranTDDFreqRelation_csFallbackPrio {
    type int32 {
      range -1..7;
    }
  }
  typedef ddt-Lrat_Band46UnlicensedProfile_b46D53140MaxPower {
    type int32 {
      range 0..30;
    }
  }
  typedef ddt-Lrat_MobilityParams1xRtt_pilotIncrement {
    type int32 {
      range 1..15;
    }
  }
  typedef ddt-Lrat_QciProfileOperatorDefined_pdcpSNLength {
    type int32 {
      range "7..7 | 12..12 | 15..15";
    }
  }
  typedef ddt-Lrat_EUtranCellTDD_ns05FullBandUsersInCellThres {
    type int32 {
      range 1..100;
    }
  }
  typedef ddt-Lrat_EUtranCellTDD_dlPowerRampUpRate {
    type int32 {
      range 1..10;
    }
  }
  typedef ddt-Lrat_SectorCarrier_noOfTxAntennas {
    type int32 {
      range "0..0 | 1..1 | 2..2 | 4..4 | 8..8 | 16..16";
    }
  }
  typedef ddt-Lrat_QciProfilePredefined_ulMaxWaitingTime {
    type int32 {
      range 0..500;
    }
  }
  typedef ddt-Lrat_SIB8_tReselectionCdma1xRtt {
    type int32 {
      range 0..7;
    }
  }
  typedef ddt-Lrat_QciProfilePredefined_priorityFraction {
    type int32 {
      range 0..9;
    }
  }
  typedef ddt-Lrat_EUtranCellFDD_lbabDecr {
    type int32 {
      range 5..100;
    }
  }
  typedef ddt-Lrat_ReportConfigEUtraInterFreqPm_a6OffsetPm {
    type int32 {
      range -150..150;
    }
  }
  typedef ddt-Lrat_NbIotFrequencyInfo_tReselection {
    type int32 {
      range 0..7;
    }
  }
  typedef ddt-Lrat_ReportConfigEUtraIntraFreqPm_a2ThresholdRsrqPm {
    type int32 {
      range -195..-30;
    }
  }
  typedef ddt-Lrat_MbsfnArea_serviceAreaId {
    type int32 {
      range 0..65535;
    }
  }
  typedef ddt-Lrat_ReportConfigEUtraInterFreqPm_a2ThresholdRsrpPm {
    type int32 {
      range -140..-44;
    }
  }
  typedef ddt-Lrat_LoadBalancingFunction_lbHitRateUtranMeasUeIntensity {
    type int32 {
      range 1..100;
    }
  }
  typedef ddt-Lrat_ReportConfigB2Utra_hysteresisB2 {
    type int32 {
      range 0..150;
    }
  }
  typedef ddt-Lrat_ReportConfigA4_hysteresisA4 {
    type int32 {
      range 0..150;
    }
  }
  typedef ddt-Lrat_Cgi_cellId {
    type int32 {
      range 0..255;
    }
  }
  typedef ddt-Lrat_ReportConfigInterRatPm_b2Threshold1RsrqPm {
    type int32 {
      range -195..-30;
    }
  }
  typedef ddt-Lrat_ExternalEUtranCellFDD_physicalLayerCellId {
    type int32 {
      range 0..503;
    }
  }
  typedef ddt-Lrat_TraceStreamStructRO_portNumber {
    type int32 {
      range 0..65535;
    }
  }
  typedef ddt-Lrat_Cdma1xRttCellId_sectorNumber {
    type int32 {
      range 0..15;
    }
  }
  typedef ddt-Lrat_ReportConfigEUtraBestCellAnr_a3offsetAnrDelta {
    type int32 {
      range -10..10;
    }
  }
  typedef ddt-Lrat_AnrFunction_maxNoPciReportsInact {
    type int32 {
      range 0..100;
    }
  }
  typedef ddt-Lrat_ExternalEUtranCellTDD_timeOfLastModification {
    type string {
      length 0..19;
    }
  }
  typedef ddt-Lrat_EUtranCellFDD_interEnbUlCompUserSelSinrHys {
    type int32 {
      range 10..50;
    }
  }
  typedef ddt-Lrat_EUtranCellFDD_ns05PathlossOffsetThres {
    type int32 {
      range 0..1000;
    }
  }
  typedef ddt-Lrat_EUtranCellTDD_maxQciLatencyMeas {
    type int32 {
      range 0..255;
    }
  }
  typedef ddt-Lrat_QciProfileOperatorDefined_qciSubscriptionQuanta {
    type int32 {
      range 0..50000;
    }
  }
  typedef ddt-Lrat_EUtranCellTDD_clusteredPuschMprFactor {
    type int32 {
      range 0..200;
    }
  }
  typedef ddt-Lrat_Band46UnlicensedProfile_b46C51490MaxPower {
    type int32 {
      range 0..30;
    }
  }
  typedef ddt-Lrat_EUtranFreqRelation_threshXHighQ {
    type int32 {
      range 0..31;
    }
  }
  typedef ddt-Lrat_DataRadioBearer_dlMaxRetxThreshold {
    type int32 {
      range "1..1 | 2..2 | 3..3 | 4..4 | 6..6 | 8..8 | 16..16 | 32..32";
    }
  }
  typedef ddt-Lrat_NbIotCell_ulAnchPrbIndex {
    type int32 {
      range "-10..110 | 255..255";
    }
  }
  typedef ddt-Lrat_ReportConfigElcA1A2_timeToTriggerA2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_clusteredPuschMprFactor {
    type int32 {
      range 0..200;
    }
  }
  typedef ddt-Lrat_ReportConfigElcA1A2_timeToTriggerA1 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_QciProfileOperatorDefined_qci {
    type int32 {
      range 10..255;
    }
  }
  typedef ddt-Lrat_EUtranCellFDD_bsrThreshold {
    type int32 {
      range 0..32767;
    }
  }
  typedef ddt-Lrat_EUtranCellFDD_eranUlCompUserSelSinrHys {
    type int32 {
      range 10..50;
    }
  }
  typedef ddt-Lrat_EUtranCellFDD_earfcnul {
    type int32 {
      range "0..0 | 18000..35999 | 46590..262143";
    }
  }
  typedef ddt-Lrat_MeasCellGroup_groupId {
    type int32 {
      range 0..24;
    }
  }
  typedef ddt-Lrat_PmFlexCounterFilter_arpFilterMin {
    type int32 {
      range 0..15;
    }
  }
  typedef ddt-Lrat_TrafficModelPrb_noOfArtificialUsers {
    type int32 {
      range 0..400;
    }
  }
  typedef ddt-Lrat_NbIotCell_prbNumber {
    type int32 {
      range -10..110;
    }
  }
  typedef ddt-Lrat_AnrFunctionEUtran_anrUesThreshInterFIncrAnr {
    type int32 {
      range 0..1000;
    }
  }
  typedef ddt-Lrat_AnrFunctionEUtran_cellAddRsrqThresholdEutran {
    type int32 {
      range -1920..0;
    }
  }
  typedef ddt-Lrat_ReportConfigElcA1A2_hysteresisA1A2Rsrp {
    type int32 {
      range 0..150;
    }
  }
  typedef ddt-Lrat_ImeisvProfile_elcPostHeatingLength {
    type int32 {
      range 0..8;
    }
  }
  typedef ddt-Lrat_ParameterChangeRequestRO_timeOfCreation {
    type string {
      length 0..19;
    }
  }
  typedef ddt-Lrat_LoadBasedCaMsrThr_ulSeUtilThreshLow {
    type int32 {
      range 0..100;
    }
  }
  typedef ddt-Lrat_ReportConfigA5_timeToTriggerA5Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_ReportConfigEUtraBestCellAnr_timeToTriggerA3 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_DistributionInfo_freqDistributionList {
    type int32 {
      range 0..100;
    }
  }
  typedef ddt-Lrat_ENodeBFunction_eranUlCompReSelectLinkTime {
    type int32 {
      range 0..1000;
    }
  }
  typedef ddt-Lrat_DrxProfile_shortDrxCycleTimer {
    type int32 {
      range 0..16;
    }
  }
  typedef ddt-Lrat_BandClassPrioCdma1xRtt_cellReselectionPriority {
    type int32 {
      range "-1000..-1000 | 0..7";
    }
  }
  typedef ddt-Lrat_PreschedProfile_preschedulingDuration {
    type int32 {
      range 5..30000;
    }
  }
  typedef ddt-Lrat_ExternalEUtranCellTDD_csgPhysCellIdRange {
    type int32 {
      range "1..1 | 4..4 | 8..8 | 12..12 | 16..16 | 24..24 | 32..32 | 48..48 | 64..64 | 84..84 | 96..96 | 128..128 | 168..168 | 252..252 | 504..504";
    }
  }
  typedef ddt-Lrat_TimerProfile_tRrcConnectionReconfiguration {
    type int32 {
      range 1..20;
    }
  }
  typedef ddt-Lrat_ReportConfigSearch_hysteresisA2OuterSearchRsrp {
    type int32 {
      range 0..150;
    }
  }
  typedef ddt-Lrat_EUtranCellFDD_rxSinrTargetClpc {
    type int32 {
      range -50..50;
    }
  }
  typedef ddt-Lrat_Band46UnlicensedProfile_b46D53940MaxPower {
    type int32 {
      range 0..30;
    }
  }
  typedef ddt-Lrat_MeasReportConfigParams_a1ThresholdRsrqPrimOffset {
    type int32 {
      range -240..240;
    }
  }
  typedef ddt-Lrat_ENodeBFunction_releaseInactiveUesInactTime {
    type int32 {
      range 0..32767;
    }
  }
  typedef ddt-Lrat_EUtranCellTDD_qRxLevMinCe {
    type int32 {
      range -140..-44;
    }
  }
  typedef ddt-Lrat_NbIotCell_allocatedPrbIndex {
    type int32 {
      range "-10..110 | 255..255";
    }
  }
  typedef ddt-Lrat_EUtranCellFDD_qQualMin {
    type int32 {
      range "-34..-3 | 0..0";
    }
  }
  typedef ddt-Lrat_AirIfLoadProfile_minLoadLevelPdcch {
    type int32 {
      range 0..100;
    }
  }
  typedef ddt-Lrat_EUtranCellFDD_expectedMaxNoOfUsersInCell {
    type int32 {
      range -1..32768;
    }
  }
  typedef ddt-Lrat_EUtranCellFDD_cceDynUeAdmCtrlOverloadThr {
    type int32 {
      range 0..1000;
    }
  }
  typedef ddt-Lrat_MeasReportConfigParams_timeToTriggerInterA3 {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_QciProfilePredefined_ulMaxHARQTxQci {
    type int32 {
      range "1..1 | 2..2 | 3..3 | 4..4 | 5..5 | 6..6 | 7..7";
    }
  }
  typedef ddt-Lrat_ReportConfigSearch_hysteresisA2OuterSearchRsrq {
    type int32 {
      range 0..150;
    }
  }
  typedef ddt-Lrat_ReportConfigEUtraInterFreqPm_a5Threshold1RsrqPm {
    type int32 {
      range -195..-30;
    }
  }
  typedef ddt-Lrat_QciProfileOperatorDefined_priorityFraction {
    type int32 {
      range 0..9;
    }
  }
  typedef ddt-Lrat_CellSleepFunction_covCellLatestStatsAdaRatio {
    type int32 {
      range 0..100;
    }
  }
  typedef ddt-Lrat_UtranFreqToQciProfileRelation_b2Thr2RscpUtraFreqQciOffset {
    type int32 {
      range -24..24;
    }
  }
  typedef ddt-Lrat_FreqPrioEUTRA_voicePrio {
    type int32 {
      range "-1000..-1000 | -1..7";
    }
  }
  typedef ddt-Lrat_ExternalEUtranCellFDD_masterEUtranCellFDDId {
    type string {
      length 0..128;
    }
  }
  typedef ddt-Lrat_CellSleepNodeFunction_csmEutranInterFMeasReportMax {
    type int32 {
      range 0..1000;
    }
  }
  typedef ddt-Lrat_Cdma20001xRttBandRelation_threshXLow1xRtt {
    type int32 {
      range 0..63;
    }
  }
  typedef ddt-Lrat_GeranFreqRelQciB2ThrOffsets_b2Thr1RsrpGeranFreqQciOffset {
    type int32 {
      range -100..100;
    }
  }
  typedef ddt-Lrat_EUtranCellFDD_outOfCoverageSrTimerPeriodicity {
    type int32 {
      range "40..40 | 80..80 | 160..160 | 320..320 | 640..640 | 960..960 | 1280..1280";
    }
  }
  typedef ddt-Lrat_ReportConfigInterRatPm_reportAmountPm {
    type int32 {
      range "0..0 | 1..1 | 2..2 | 4..4 | 8..8 | 16..16 | 32..32 | 64..64";
    }
  }
  typedef ddt-Lrat_InstantUplinkAccess_iuaUePrbLimit {
    type int32 {
      range 1..100;
    }
  }
  typedef ddt-Lrat_EUtranFreqRelation_voicePrioBr {
    type int32 {
      range -1..7;
    }
  }
  typedef ddt-Lrat_Band46UnlicensedProfile_b46B48090MaxPower {
    type int32 {
      range 0..30;
    }
  }
  typedef ddt-Lrat_ReportConfigEUtraIntraFreqPm_a1ThresholdRsrqPm {
    type int32 {
      range -195..-30;
    }
  }
  typedef ddt-Lrat_UtranFreqRelation_cellReselectionPriority {
    type int32 {
      range 0..7;
    }
  }
  typedef ddt-Lrat_ReportConfigSearch_timeToTriggerA1SearchRsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranFreqRelationUnlicensed_userLabel {
    type string {
      length 1..128;
    }
  }
  typedef ddt-Lrat_ReportConfigB2Cdma20001xRtt_hysteresisB2RsrqOffset {
    type int32 {
      range -150..150;
    }
  }
  typedef ddt-Lrat_ENodeBFunction_eNBId {
    type int32 {
      range -1..1048575;
    }
  }
  typedef ddt-Lrat_AcBarringConfig1xRtt_acBarringMsgR9 {
    type int32 {
      range 0..7;
    }
  }
  typedef ddt-Lrat_MbsfnSubframeConfigRO_radioframeAllocationPeriod {
    type int32 {
      range "1..1 | 2..2 | 4..4 | 8..8 | 16..16 | 32..32";
    }
  }
  typedef ddt-Lrat_GUtranSyncSignalFrequency_band {
    type int32 {
      range 1..512;
    }
  }
  typedef ddt-Lrat_CarrierAggregationFunction_dcSCellDeactDelayTimer {
    type int32 {
      range 0..5000;
    }
  }
  typedef ddt-Lrat_Band46UnlicensedProfile_b46C51890MaxPower {
    type int32 {
      range 0..30;
    }
  }
  typedef ddt-Lrat_MdtConfiguration_reportAmountMdt {
    type int32 {
      range "0..0 | 1..1 | 2..2 | 4..4 | 8..8 | 16..16 | 32..32 | 64..64";
    }
  }
  typedef ddt-Lrat_NbIotCell_userLabel {
    type string {
      length 1..128;
    }
  }
  typedef ddt-Lrat_UtranFreqRelation_maxNrUtranCellRelations {
    type int32 {
      range 0..64;
    }
  }
  typedef ddt-Lrat_SectorCarrier_antCalModeTddAasDl {
    type int32 {
      range 0..1;
    }
  }
  typedef ddt-Lrat_TermPointToENB_domainName {
    type string {
      length 0..255;
    }
  }
  typedef ddt-Lrat_ExternalCdma20001xRttCell_nid {
    type int32 {
      range 0..65535;
    }
  }
  typedef ddt-Lrat_AdmissionControl_dlTransNwBandwidth {
    type int32 {
      range 0..1000;
    }
  }
  typedef ddt-Lrat_AnrFunctionEUtran_anrEutranInterFMeasReportDecr {
    type int32 {
      range 0..1000;
    }
  }
  typedef ddt-Lrat_ReportConfigParamsQciOffset_a1a2ThrRsrqQciOffset {
    type int32 {
      range -240..240;
    }
  }
  typedef ddt-Lrat_SIB8_tReselectionCdmaHrpdSfHigh {
    type int32 {
      range 25..100;
    }
  }
  typedef ddt-Lrat_EUtranCellTDD_lbTpNonQualFraction {
    type int32 {
      range "0..0 | 20..80";
    }
  }
  typedef ddt-Lrat_ResOpUseConfig_resSRatioThreshold {
    type int32 {
      range 0..1600;
    }
  }
  typedef ddt-Lrat_EUtranCellFDD_deallocThrPucchFormat1 {
    type int32 {
      range 0..2000;
    }
  }
  typedef ddt-Lrat_EUtranCellFDD_maxValidSubframeDlBr {
    type int32 {
      range 50..100;
    }
  }
  typedef ddt-Lrat_EUtranCellFDD_uncertSemiMinor {
    type int32 {
      range 0..127;
    }
  }
  typedef ddt-Lrat_Band46UnlicensedProfile_b46D53540MaxPower {
    type int32 {
      range 0..30;
    }
  }
  typedef ddt-Lrat_ReportConfigInterRatPm_b1ThresholdEcNoUtraPm {
    type int32 {
      range -245..0;
    }
  }
  typedef ddt-Lrat_PeriodicitySI_siPeriodicitySI10 {
    type int32 {
      range "8..8 | 16..16 | 32..32 | 64..64 | 128..128 | 256..256 | 512..512";
    }
  }
  typedef ddt-Lrat_AcBarringConfig_acBarringTime {
    type int32 {
      range "4..4 | 8..8 | 16..16 | 32..32 | 64..64 | 128..128 | 256..256 | 512..512";
    }
  }
  typedef ddt-Lrat_UeMeasControl_maxMeasCdma2000eHrpd {
    type int32 {
      range 1..5;
    }
  }
  typedef ddt-Lrat_EUtranCellFDD_hoOptStatNum {
    type int32 {
      range 1..32767;
    }
  }
  typedef ddt-Lrat_Cdma20001xRttFreqRelation_csFallbackPrio {
    type int32 {
      range 0..7;
    }
  }
  typedef ddt-Lrat_Cdma2000FreqRelation_b2Thr1RsrpCdma2000FreqOffset {
    type int32 {
      range -100..100;
    }
  }
  typedef ddt-Lrat_EUtranCellTDD_maxNoClusteredPuschAlloc {
    type int32 {
      range 0..5;
    }
  }
  typedef ddt-Lrat_ParameterChangeRequestRO_originalValue {
    type string {
      length 0..32;
    }
  }
  typedef ddt-Lrat_ReportConfigB1Geran_hysteresisB1 {
    type int32 {
      range 0..150;
    }
  }
  typedef ddt-Lrat_EUtranCellFDD_outOfCoverageThreshold {
    type int32 {
      range 1..63;
    }
  }
  typedef ddt-Lrat_TrafficModelPrb_qciDistSinrHigh {
    type int32 {
      range 0..100;
    }
  }
  typedef ddt-Lrat_MobilityParams1xRtt_fchFchInitSetupRc12 {
    type int32 {
      range 8..255;
    }
  }
  typedef ddt-Lrat_ReportConfigB2Utra_b2Threshold1Rsrp {
    type int32 {
      range -140..-44;
    }
  }
  typedef ddt-Lrat_ReportConfigB2Utra_b2Threshold1Rsrq {
    type int32 {
      range -195..-30;
    }
  }
  typedef ddt-Lrat_MobilityParams1xRtt_fchFchInitSetupRc11 {
    type int32 {
      range 8..255;
    }
  }
  typedef ddt-Lrat_EUtranCellFDD_additionalFreqBandList {
    type int32 {
      range 1..256;
    }
  }
  typedef ddt-Lrat_PmchMch_dataMcs {
    type int32 {
      range 0..28;
    }
  }
  typedef ddt-Lrat_QciProfilePredefined_drxPriority {
    type int32 {
      range 0..100;
    }
  }
  typedef ddt-Lrat_EUtranCellFDD_ulChannelBandwidth {
    type int32 {
      range "1400..1400 | 3000..3000 | 5000..5000 | 10000..10000 | 15000..15000 | 20000..20000";
    }
  }
  typedef ddt-Lrat_CarrierAggregationFunction_sCellScheduleUlPathlossThresh {
    type int32 {
      range 0..2000;
    }
  }
  typedef ddt-Lrat_ExternalEUtranCellTDD_userLabel {
    type string {
      length 1..128;
    }
  }
  typedef ddt-Lrat_SectorCarrier_pimMitigDlMutingPeriod {
    type int32 {
      range 4..15;
    }
  }
  typedef ddt-Lrat_EUtranCellFDD_pZeroNominalPusch {
    type int32 {
      range -126..24;
    }
  }
  typedef ddt-Lrat_UeMeasControl_sMeasure {
    type int32 {
      range "-140..-44 | 0..0";
    }
  }
  typedef ddt-Lrat_EranInterMeLink_linkLatency15minHWM {
    type int32 {
      range -1..1000000;
    }
  }
  typedef ddt-Lrat_SIPeriodicityNB_siPeriodicitySI14 {
    type int32 {
      range "64..64 | 128..128 | 256..256 | 512..512 | 1024..1024 | 2048..2048 | 4096..4096";
    }
  }
  typedef ddt-Lrat_EUtranCellTDD_dynUeAdmCtrlFilterConst {
    type int32 {
      range 0..10000;
    }
  }
  typedef ddt-Lrat_Band46UnlicensedProfile_b46D54140MaxPower {
    type int32 {
      range 0..30;
    }
  }
  typedef ddt-Lrat_A5PCOffsetMCPC_a5Thr2RsrpPCOffset {
    type int32 {
      range -100..100;
    }
  }
  typedef ddt-Lrat_TimerProfile_tRelocOverall {
    type int32 {
      range 1..20;
    }
  }
  typedef ddt-Lrat_SectorCarrier_pimMitigDlMutingPerc {
    type int32 {
      range 0..100;
    }
  }
  typedef ddt-Lrat_SciProfile_dlMaxWaitingTime {
    type int32 {
      range 0..500;
    }
  }
  typedef ddt-Lrat_EUtranFreqToQciProfileRelation_timeToTriggerA3Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_ENodeBFunction_softLockRwRWaitTimerInternal {
    type int32 {
      range 20..80;
    }
  }
  typedef ddt-Lrat_ExternalUtranCellTDD_masterUtranCellId {
    type string {
      length 0..128;
    }
  }
  typedef ddt-Lrat_ENodeBFunction_interEnbUlCompTunnelDscp {
    type int32 {
      range 0..63;
    }
  }
  typedef ddt-Lrat_AnrFunction_probCellDetectLowHoSuccTime {
    type int32 {
      range 1..30;
    }
  }
  typedef ddt-Lrat_SIB3_sNonIntraSearch {
    type int32 {
      range "0..62 | 1000..1000";
    }
  }
  typedef ddt-Lrat_ReportConfigA5_timeToTriggerA5 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_Cdma2000FreqBand_userLabel {
    type string {
      length 1..128;
    }
  }
  typedef ddt-Lrat_CandNeighborRelInfoRO_mnc {
    type int32 {
      range 0..999;
    }
  }
  typedef ddt-Lrat_NbIotIntraFrequencyInfo_pMax {
    type int32 {
      range "-30..33 | 1000..1000";
    }
  }
  typedef ddt-Lrat_PmFlexCounterFilter_arpFilterMax {
    type int32 {
      range 0..15;
    }
  }
  typedef ddt-Lrat_InterNodalProtocolVerRO_eRanCaProtVerExact {
    type int32 {
      range -1..2147483647;
    }
  }
  typedef ddt-Lrat_FreqPrioUTRAN_cellReselectionPriority {
    type int32 {
      range "-1000..-1000 | 0..7";
    }
  }
  typedef ddt-Lrat_UtranTDDFreqRelation_b2Thr2RscpUtraFreqOffset {
    type int32 {
      range -24..24;
    }
  }
  typedef ddt-Lrat_CarrierAggregationFunction_laaSCellScheduleSinrThres {
    type int32 {
      range -200..300;
    }
  }
  typedef ddt-Lrat_CarrierAggregationFunction_laaSCellActProhibitTimer {
    type int32 {
      range 0..5000;
    }
  }
  typedef ddt-Lrat_TermPointToMme_ipv6Address1 {
    type string {
      length 2..39;
    }
  }
  typedef ddt-Lrat_MbsfnArea_nonMbsfnRegionLength {
    type int32 {
      range "1..1 | 2..2";
    }
  }
  typedef ddt-Lrat_AnrFunction_cellRelHoAttRateThreshold {
    type int32 {
      range 0..200;
    }
  }
  typedef ddt-Lrat_ENodeBFunction_interEnbCaTunnelDscp {
    type int32 {
      range 0..63;
    }
  }
  typedef ddt-Lrat_TermPointToMme_ipv6Address2 {
    type string {
      length 2..39;
    }
  }
  typedef ddt-Lrat_MeasReportConfigParams_timeToTriggerInterA3Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_ExternalGNodeBFunction_gNBId {
    type int32 {
      range -1..1048575;
    }
  }
  typedef ddt-Lrat_EUtranCellFDD_puschPwrOffset64qam {
    type int32 {
      range 0..8;
    }
  }
  typedef ddt-Lrat_SectorCarrier_partOfSectorPower {
    type int32 {
      range 0..100;
    }
  }
  typedef ddt-Lrat_EUtranCellTDD_userLabel {
    type string {
      length 1..128;
    }
  }
  typedef ddt-Lrat_ExternalCdma20001xRttCell_pnOffset {
    type int32 {
      range 0..511;
    }
  }
  typedef ddt-Lrat_EUtranCellFDD_lbabPeriod {
    type int32 {
      range 0..4095;
    }
  }
  typedef ddt-Lrat_EndcProfile_meNbS1TermReqArpLev {
    type int32 {
      range 0..15;
    }
  }
  typedef ddt-Lrat_Cdma20001xRttBandRelation_userLabel {
    type string {
      length 1..128;
    }
  }
  typedef ddt-Lrat_MbmsService_syncSequenceLength {
    type int32 {
      range "8..8 | 16..16 | 32..32 | 64..64 | 128..128 | 256..256 | 512..512 | 1024..1024";
    }
  }
  typedef ddt-Lrat_Cdma2000FreqRelation_userLabel {
    type string {
      length 1..128;
    }
  }
  typedef ddt-Lrat_ReportConfigSCellA1A2_hysteresisA1A2RsrpBidir {
    type int32 {
      range 0..150;
    }
  }
  typedef ddt-Lrat_EUtranCellFDD_minBestCellHoAttempts {
    type int32 {
      range 1..10;
    }
  }
  typedef ddt-Lrat_NbIotFrequencyInfo_qOffsetFreq {
    type int32 {
      range "-24..-24 | -22..-22 | -20..-20 | -18..-18 | -16..-16 | -14..-14 | -12..-12 | -10..-10 | -8..-8 | -6..-6 | -5..-5 | -4..-4 | -3..-3 | -2..-2 | -1..-1 | 0..0 | 1..1 | 2..2 | 3..3 | 4..4 | 5..5 | 6..6 | 8..8 | 10..10 | 12..12 | 14..14 | 16..16 | 18..18 | 20..20 | 22..22 | 24..24";
    }
  }
  typedef ddt-Lrat_ExternalGUtranCell_physicalLayerSubCellId {
    type int32 {
      range 0..2;
    }
  }
  typedef ddt-Lrat_UtranFreqRelation_qOffsetFreq {
    type int32 {
      range -15..15;
    }
  }
  typedef ddt-Lrat_NbIotFrequencyInfo_freqBandList {
    type int32 {
      range 1..256;
    }
  }
  typedef ddt-Lrat_FreqPrioEUTRA_connectedModeMobilityPrio {
    type int32 {
      range "-1000..-1000 | -1..7";
    }
  }
  typedef ddt-Lrat_EUtranCellTDD_pdcchOuterLoopInitialAdjVolte {
    type int32 {
      range -200..200;
    }
  }
  typedef ddt-Lrat_EUtranCellFDD_dynLoadCtrlMinNewConn {
    type int32 {
      range 1..110;
    }
  }
  typedef ddt-Lrat_Cdma20001xRttBandRelation_threshXHigh1xRtt {
    type int32 {
      range 0..63;
    }
  }
  typedef ddt-Lrat_TermPointToENB_ipv6Address {
    type string {
      length 2..39;
    }
  }
  typedef ddt-Lrat_MimoSleepFunction_switchUpMonitorDurTimer {
    type int32 {
      range 5..120;
    }
  }
  typedef ddt-Lrat_ExternalUtranCellTDD_lac {
    type int32 {
      range "0..65533 | 65535..65535";
    }
  }
  typedef ddt-Lrat_GeranFrequency_arfcnValueGeranDl {
    type int32 {
      range 0..1023;
    }
  }
  typedef ddt-Lrat_ReportConfigB1Utra_b1ThresholdRscpUtra {
    type int32 {
      range -120..-24;
    }
  }
  typedef ddt-Lrat_EUtranCellTDD_noOfPucchCqiUsers {
    type int32 {
      range 0..4000;
    }
  }
  typedef ddt-Lrat_UeMeasControl_maxMeasCdma20001xRtt {
    type int32 {
      range 1..5;
    }
  }
  typedef ddt-Lrat_AnrFunctionEUtran_anrUesEUtraIntraFIncrAnr {
    type int32 {
      range 0..1000;
    }
  }
  typedef ddt-Lrat_ReportConfigInterEnbUlComp_hysteresisA3 {
    type int32 {
      range 0..150;
    }
  }
  typedef ddt-Lrat_EUtranCellFDD_pdcchTargetBlerVolte {
    type int32 {
      range 1..200;
    }
  }
  typedef ddt-Lrat_SubscriberGroupProfile_profilePriority {
    type int32 {
      range 1..65535;
    }
  }
  typedef ddt-Lrat_EUtranCellTDD_minQciLatencyMeas {
    type int32 {
      range 0..255;
    }
  }
  typedef ddt-Lrat_EUtranCellTDD_pdcchTargetBlerPCell {
    type int32 {
      range 1..200;
    }
  }
  typedef ddt-Lrat_ReportConfigEUtraInterFreqPm_a3OffsetPm {
    type int32 {
      range -150..150;
    }
  }
  typedef ddt-Lrat_Cgi_mncLength {
    type int32 {
      range 2..3;
    }
  }
  typedef ddt-Lrat_ReportConfigInterEnbUlComp_a3Offset {
    type int32 {
      range -150..150;
    }
  }
  typedef ddt-Lrat_SIB7_tReselectionGeranSfHigh {
    type int32 {
      range 25..100;
    }
  }
  typedef ddt-Lrat_EUtranCellTDD_cceDynUeAdmCtrlOverloadThr {
    type int32 {
      range 0..1000;
    }
  }
  typedef ddt-Lrat_SIPeriodicityNB_siPeriodicitySI116 {
    type int32 {
      range "64..64 | 128..128 | 256..256 | 512..512 | 1024..1024 | 2048..2048 | 4096..4096";
    }
  }
  typedef ddt-Lrat_EUtranCellFDD_gpsTimeSFN0Seconds {
    type int64 {
      range 0..4294967295;
    }
  }
  typedef ddt-Lrat_UtraNetwork_userLabel {
    type string {
      length 1..128;
    }
  }
  typedef ddt-Lrat_EUtranCellFDD_noOfPucchFormat3PrbPairs {
    type int32 {
      range 0..3;
    }
  }
  typedef ddt-Lrat_EUtranCellFDD_noOfPucchFormat3PrbPairsPerFrame {
    type int32 {
      range 0..1000;
    }
  }
  typedef ddt-Lrat_MbsfnArea_signallingMCS {
    type int32 {
      range "2..2 | 7..7 | 13..13 | 19..19";
    }
  }
  typedef ddt-Lrat_UtranFrequency_arfcnValueUtranDl {
    type int32 {
      range 0..16383;
    }
  }
  typedef ddt-Lrat_QciProfileOperatorDefined_timerPriority {
    type int32 {
      range 0..100;
    }
  }
  typedef ddt-Lrat_WhiteListPlmnIdentity_mnc {
    type int32 {
      range -1..999;
    }
  }
  typedef ddt-Lrat_UtranFreqRelation_threshXHighQ {
    type int32 {
      range 0..31;
    }
  }
  typedef ddt-Lrat_EUtranFreqRelation_lbA5Thr1RsrpFreqOffset {
    type int32 {
      range 0..100;
    }
  }
  typedef ddt-Lrat_ENodeBFunction_extendedWaitTimeNb {
    type int32 {
      range 0..1800;
    }
  }
  typedef ddt-Lrat_TermPointToENB_usedIpAddress {
    type string {
      length 2..39;
    }
  }
  typedef ddt-Lrat_NbIotCell_tTatDedicatedNbCe0 {
    type int32 {
      range "0..0 | 500..500 | 750..750 | 1280..1280 | 1920..1920 | 2560..2560 | 5120..5120 | 10240..10240";
    }
  }
  typedef ddt-Lrat_LoadBasedCaMsrThr_cceUtilThreshHigh {
    type int32 {
      range 0..100;
    }
  }
  typedef ddt-Lrat_EUtranCellFDD_prsConfigIndex {
    type int32 {
      range -1..4095;
    }
  }
  typedef ddt-Lrat_CellSleepFunction_capCellSleepMonitorDurTimer {
    type int32 {
      range 5..120;
    }
  }
  typedef ddt-Lrat_NbIotCell_tTatDedicatedNbCe1 {
    type int32 {
      range "0..0 | 500..500 | 750..750 | 1280..1280 | 1920..1920 | 2560..2560 | 5120..5120 | 10240..10240";
    }
  }
  typedef ddt-Lrat_NbIotCell_tTatDedicatedNbCe2 {
    type int32 {
      range "0..0 | 500..500 | 750..750 | 1280..1280 | 1920..1920 | 2560..2560 | 5120..5120 | 10240..10240";
    }
  }
  typedef ddt-Lrat_Band46UnlicensedProfile_b46C50890MaxPower {
    type int32 {
      range 0..30;
    }
  }
  typedef ddt-Lrat_Rrc_t300Br {
    type int32 {
      range "0..0 | 2500..2500 | 3000..3000 | 3500..3500 | 4000..4000 | 5000..5000 | 6000..6000 | 8000..8000 | 10000..10000";
    }
  }
  typedef ddt-Lrat_MimoSleepFunction_switchDownPrbThreshold {
    type int32 {
      range 0..90;
    }
  }
  typedef ddt-Lrat_LoadBalancingFunction_txPwrForOverlaidCellDetect {
    type int32 {
      range 0..540;
    }
  }
  typedef ddt-Lrat_EUtranCellRelation_covCellDlPrbWakeUpThreshold {
    type int32 {
      range 0..100;
    }
  }
  typedef ddt-Lrat_MeasReportConfigParams_b2Threshold1RsrqUtraOffset {
    type int32 {
      range -240..240;
    }
  }
  typedef ddt-Lrat_EUtranCellTDD_timeOfLastModification {
    type string {
      length 0..19;
    }
  }
  typedef ddt-Lrat_FreqPrioUTRAN_altCsfbTargetPrioEc {
    type int32 {
      range "-1000..-1000 | -1..7";
    }
  }
  typedef ddt-Lrat_Paging_numRepetitionsPagingNbIot {
    type int32 {
      range "1..1 | 2..2 | 4..4 | 8..8 | 16..16 | 32..32 | 64..64 | 128..128 | 256..256 | 512..512 | 1024..1024 | 2048..2048";
    }
  }
  typedef ddt-Lrat_MeasReportConfigParams_b2Threshold1RsrqGeranOffset {
    type int32 {
      range -240..240;
    }
  }
  typedef ddt-Lrat_FrameStartOffsetTDD_timeOffset {
    type int32 {
      range 0..1000000;
    }
  }
  typedef ddt-Lrat_FreqPrioUTRAN_csFallbackPrioEC {
    type int32 {
      range "-1000..-1000 | -1..7";
    }
  }
  typedef ddt-Lrat_ExternalGUtranCell_localCellId {
    type int32 {
      range 0..16383;
    }
  }
  typedef ddt-Lrat_EUtranFreqRelation_threshXLowQ {
    type int32 {
      range 0..31;
    }
  }
  typedef ddt-Lrat_MbsfnSubframeConfigRO_radioframeAllocationOffset {
    type int32 {
      range 0..7;
    }
  }
  typedef ddt-Lrat_ENodeBFunction_minRandc {
    type int32 {
      range 1..254;
    }
  }
  typedef ddt-Lrat_QciProfileOperatorDefined_lessMaxDelayThreshold {
    type int32 {
      range 0..20;
    }
  }
  typedef ddt-Lrat_PlmnIdentityRO_mncLength {
    type int32 {
      range 2..3;
    }
  }
  typedef ddt-Lrat_MeasReportConfigParams_offsetPerQciPrio {
    type int32 {
      range -1..7;
    }
  }
  typedef ddt-Lrat_EUtranCellFDD_hoOptAdjThresholdAbs {
    type int32 {
      range 0..32767;
    }
  }
  typedef ddt-Lrat_Band46UnlicensedProfile_b46C51090MaxPower {
    type int32 {
      range 0..30;
    }
  }
  typedef ddt-Lrat_EUtranCellTDD_lbUtranOffloadThreshold {
    type int32 {
      range 0..1600;
    }
  }
  typedef ddt-Lrat_FreqGroupPrioGERAN_csFallbackPrio {
    type int32 {
      range "-1000..-1000 | -1..7";
    }
  }
  typedef ddt-Lrat_IdleModePrioAtRelease_mediumLoadThreshold {
    type int32 {
      range 0..16000;
    }
  }
  typedef ddt-Lrat_EUtranCellTDD_cellCapMaxCellSubCap {
    type int32 {
      range 0..1000000;
    }
  }
  typedef ddt-Lrat_MeasReportConfigParams_a5Threshold1RsrpOffset {
    type int32 {
      range -100..100;
    }
  }
  typedef ddt-Lrat_Rrc_tWaitForRrcConnReest {
    type int32 {
      range 1..20;
    }
  }
  typedef ddt-Lrat_EUtranCellFDD_prachFrequencyAllocation {
    type int32 {
      range 0..1;
    }
  }
  typedef ddt-Lrat_ReportConfigEUtraInterFreqPm_a5Threshold2RsrqPm {
    type int32 {
      range -195..-30;
    }
  }
  typedef ddt-Lrat_TermPointToMme_ipAddress1 {
    type string {
      length 7..15;
    }
  }
  typedef ddt-Lrat_PrefTrafficMgmt_inhibitIMPrioritizationInterval {
    type int32 {
      range 0..60;
    }
  }
  typedef ddt-Lrat_ReportConfigEUtraBestCell_timeToTriggerA3Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-ExternalEUtranCellFDD_changeFrequency_earfcn {
    type int32 {
      range "0..17999 | 46590..262143";
    }
  }
  typedef ddt-Lrat_EUtranFreqToQciProfileRelation_a5Thr1RsrpFreqQciOffset {
    type int32 {
      range -100..100;
    }
  }
  typedef ddt-Lrat_EUtranCellFDD_earfcndl {
    type int32 {
      range "0..17999 | 46590..262143";
    }
  }
  typedef ddt-Lrat_ReportConfigB1Geran_timeToTriggerB1 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_TermPointToMme_ipAddress2 {
    type string {
      length 7..15;
    }
  }
  typedef ddt-Lrat_ReportConfigA1Prim_a1ThresholdRsrqPrim {
    type int32 {
      range -195..-30;
    }
  }
  typedef ddt-Lrat_AnrFunctionEUtran_anrUesEUtraIntraFIncrHo {
    type int32 {
      range 0..1000;
    }
  }
  typedef ddt-Lrat_ReportConfigB2Geran_timeToTriggerB2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_Cdma20001xRttBandRelation_cellReselectionPriority {
    type int32 {
      range 0..7;
    }
  }
  typedef ddt-Lrat_Band46UnlicensedProfile_b46C52290MaxPower {
    type int32 {
      range 0..30;
    }
  }
  typedef ddt-Lrat_Cgi_enbId {
    type int32 {
      range 0..1048575;
    }
  }
  typedef ddt-Lrat_CsfbRegParams1xRtt_zoneTimer {
    type int32 {
      range "1..1 | 2..2 | 5..5 | 10..10 | 20..20 | 30..30 | 45..45 | 60..60";
    }
  }
  typedef ddt-Lrat_ReportConfigB2Geran_hysteresisB2RsrqOffset {
    type int32 {
      range -150..150;
    }
  }
  typedef ddt-Lrat_ReportConfigA5_a5Threshold1Rsrp {
    type int32 {
      range -140..-44;
    }
  }
  typedef ddt-Lrat_UtranFreqRelation_b2Thr1RsrqUtraFreqOffset {
    type int32 {
      range -240..240;
    }
  }
  typedef ddt-Lrat_ReportConfigA5_a5Threshold1Rsrq {
    type int32 {
      range -195..-30;
    }
  }
  typedef ddt-Lrat_EUtranCellTDD_ulDynUeAdmCtrlRetDiffThr {
    type int32 {
      range 0..1000;
    }
  }
  typedef ddt-Lrat_ReportConfigB2Cdma2000_b2Threshold2Cdma2000 {
    type int32 {
      range -315..0;
    }
  }
  typedef ddt-Lrat_ReportConfigEUtraInterFreqPm_a2ThresholdRsrqPm {
    type int32 {
      range -195..-30;
    }
  }
  typedef ddt-Lrat_EutranCellArea_posCellRadius {
    type int32 {
      range 0..100000;
    }
  }
  typedef ddt-Lrat_EUtranCellFDD_pdcchPowerBoostMax {
    type int32 {
      range 0..6;
    }
  }
  typedef ddt-Lrat_QciProfileOperatorDefined_pdbOffset {
    type int32 {
      range -500..1000;
    }
  }
  typedef ddt-Lrat_ExternalEUtranCellFDD_timeOfLastModification {
    type string {
      length 0..19;
    }
  }
  typedef ddt-Lrat_MbsfnArea_mcchModificationPeriod {
    type int32 {
      range "512..512 | 1024..1024";
    }
  }
  typedef ddt-Lrat_AdmissionControl_ulAdmDifferentiationThr {
    type int32 {
      range 0..1000;
    }
  }
  typedef ddt-Lrat_LoadBalancingFunction_lbDiffCaOffset {
    type int32 {
      range 0..1000;
    }
  }
  typedef ddt-Lrat_ReportConfigB2CdmaUlTrig_timeToTriggerB2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_caPrioThreshold {
    type int32 {
      range 0..65535;
    }
  }
  typedef ddt-Lrat_UtranFreqRelation_threshXHigh {
    type int32 {
      range 0..62;
    }
  }
  typedef ddt-Lrat_ReportConfigA5Anr_timeToTriggerA5 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_tac {
    type int32 {
      range 0..65535;
    }
  }
  typedef ddt-Lrat_ExternalEUtranCellFDD_noOfTxAntennas {
    type int32 {
      range "1..1 | 2..2 | 4..4";
    }
  }
  typedef ddt-Lrat_QciProfilePredefined_pdbOffset {
    type int32 {
      range -500..1000;
    }
  }
  typedef ddt-Lrat_ReportConfigEUtraInterFreqPm_a1ThresholdRsrqPm {
    type int32 {
      range -195..-30;
    }
  }
  typedef ddt-Lrat_EUtranCellFDD_threshServingLow {
    type int32 {
      range 0..62;
    }
  }
  typedef ddt-Lrat_UtranTDDFreqRelation_qRxLevMin {
    type int32 {
      range -119..-25;
    }
  }
  typedef ddt-Lrat_DataRadioBearer_ulMaxRetxThreshold {
    type int32 {
      range "1..1 | 2..2 | 3..3 | 4..4 | 6..6 | 8..8 | 16..16 | 32..32";
    }
  }
  typedef ddt-Lrat_ExternalEUtranCellFDD_csgPhysCellId {
    type int32 {
      range "0..503 | 1000..1000";
    }
  }
  typedef ddt-Lrat_QciProfileOperatorDefined_dlMaxHARQTxQci {
    type int32 {
      range "1..1 | 2..2 | 3..3 | 4..4 | 5..5 | 6..6 | 7..7 | 8..8 | 10..10 | 12..12 | 16..16 | 20..20 | 24..24 | 28..28";
    }
  }
  typedef ddt-Lrat_EUtraNetwork_userLabel {
    type string {
      length 1..128;
    }
  }
  typedef ddt-Lrat_EUtranCellFDD_physicalLayerCellIdGroup {
    type int32 {
      range 0..167;
    }
  }
  typedef ddt-Lrat_EUtranCellTDD_noOfPucchSrUsers {
    type int32 {
      range 0..4000;
    }
  }
  typedef ddt-Lrat_UtranFreqToQciProfileRelation_b2Thr1RsrqUtraFreqQciOffset {
    type int32 {
      range -240..240;
    }
  }
  typedef ddt-Lrat_UnlicensedFrequencyProperties_maxUnlicensedTxPower {
    type int32 {
      range 0..40000;
    }
  }
  typedef ddt-Lrat_AnrFunction_prioHoSuccRate {
    type int32 {
      range 0..100;
    }
  }
  typedef ddt-Lrat_UtranFreqRelation_voicePrio {
    type int32 {
      range -1..7;
    }
  }
  typedef ddt-Lrat_ReportConfigSCellA1A2_timeToTriggerA1 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_QciProfilePredefined_rlcSNLength {
    type int32 {
      range "5..5 | 10..10 | 16..16";
    }
  }
  typedef ddt-Lrat_ReportConfigSCellA1A2_timeToTriggerA2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_CarrierAggregationFunction_sCellPdcchOuterLoopMargin {
    type int32 {
      range -200..200;
    }
  }
  typedef ddt-Lrat_GUGroupIdRO_mmeGI {
    type int32 {
      range 0..65535;
    }
  }
  typedef ddt-Lrat_EranInterMeLink_localPort {
    type string {
      length 0..128;
    }
  }
  typedef ddt-Lrat_Paging_defaultPagingCycleNbIot {
    type int32 {
      range "128..128 | 256..256 | 512..512 | 1024..1024";
    }
  }
  typedef ddt-Lrat_MeasCellGroup_spidList {
    type int32 {
      range 0..256;
    }
  }
  typedef ddt-Lrat_CellResource_resourceId {
    type int32 {
      range 0..24;
    }
  }
  typedef ddt-Lrat_ReportConfigEUtraIFBestCell_timeToTriggerA3Rsrq {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-Lrat_ReportConfigEUtraInterFreqPm_reportAmountPm {
    type int32 {
      range "0..0 | 1..1 | 2..2 | 4..4 | 8..8 | 16..16 | 32..32 | 64..64";
    }
  }
  typedef ddt-Lrat_ExternalEUtranCellTDD_tac {
    type int32 {
      range 0..65535;
    }
  }
  typedef ddt-Lrat_ReportConfigSCellA1A2_a1a2ThresholdRsrpBidir {
    type int32 {
      range -140..-44;
    }
  }
  typedef ddt-Lrat_SectorCarrier_pimMitigLevelThresh {
    type int32 {
      range "-180..-125 | 0..0";
    }
  }
  typedef ddt-Lrat_EUtranFreqToQciProfileRelation_a3RsrqFreqQciOffsetAdjustment {
    type int32 {
      range -150..150;
    }
  }
  typedef ddt-Lrat_EUtranCellFDD_interferenceThresholdSinrClpc {
    type int32 {
      range -125..-60;
    }
  }
  typedef ddt-Lrat_AcBarringConfig_acBarringFactor {
    type int32 {
      range "0..0 | 5..5 | 10..10 | 15..15 | 20..20 | 25..25 | 30..30 | 40..40 | 50..50 | 60..60 | 70..70 | 75..75 | 80..80 | 85..85 | 90..90 | 95..95";
    }
  }
  typedef ddt-Lrat_UeMeasControl_filterCoefficientEcnoUtra {
    type int32 {
      range "0..0 | 1..1 | 2..2 | 3..3 | 4..4 | 5..5 | 6..6 | 7..7 | 8..8 | 9..9 | 11..11 | 13..13 | 15..15 | 17..17 | 19..19";
    }
  }
  typedef ddt-Lrat_CarrierAggregationFunction_sCellDeactDelayTimer {
    type int32 {
      range 0..5000;
    }
  }
  typedef ddt-Lrat_EUtranCellFDD_lbabMinBarringFactorPrio1 {
    type int32 {
      range 0..100;
    }
  }
  typedef ddt-Lrat_NbIotCell_tac {
    type int32 {
      range 0..65535;
    }
  }
  typedef ddt-Lrat_EUtranCellFDD_lbabMinBarringFactorPrio2 {
    type int32 {
      range 0..100;
    }
  }
  typedef ddt-Lrat_ENodeBFunction_inactivitySupervisionTimerNb {
    type int32 {
      range 0..2000;
    }
  }
  typedef ddt-Lrat_EUtranCellFDD_lbabMinBarringFactorPrio3 {
    type int32 {
      range 0..100;
    }
  }
  typedef ddt-Lrat_EUtranCellFDD_lbabMinBarringFactorPrio4 {
    type int32 {
      range 0..100;
    }
  }
  typedef ddt-Lrat_ReportConfigInterRatPm_b1ThresholdRscpUtraPm {
    type int32 {
      range -120..-24;
    }
  }
  typedef ddt-Lrat_ENodeBFunction_randUpdateInterval {
    type int32 {
      range 15..1440;
    }
  }
  typedef ddt-Lrat_EUtranCellTDD_lbabPeriod {
    type int32 {
      range 0..4095;
    }
  }
  typedef ddt-Lrat_MeasReportConfigParams_b2Threshold1RsrpCdma2000Offset {
    type int32 {
      range -100..100;
    }
  }
  typedef ddt-Lrat_BandClassPrioCdma1xRtt_csFallbackPrio {
    type int32 {
      range "-1000..-1000 | 0..7";
    }
  }
  typedef ddt-Lrat_QciProfileOperatorDefined_dlMaxWaitingTime {
    type int32 {
      range 0..500;
    }
  }
  typedef ddt-Lrat_ENodeBFunction_tOutgoingHoExecCdma1xRtt {
    type int32 {
      range 1..32000;
    }
  }
  typedef ddt-Lrat_EUtranCellTDD_ulPsdLoadThresholdSinrClpc {
    type int32 {
      range -126..24;
    }
  }
  typedef ddt-Lrat_EricssonLeanCarrierFunction_elcDrxOnDurationPreHeating {
    type int32 {
      range 0..38;
    }
  }
  typedef ddt-Lrat_EUtranCellFDD_hpueCaSwitchThres {
    type int32 {
      range -150..450;
    }
  }
  typedef ddt-Lrat_EUtranFreqToQciProfileRelation_lbA5Threshold2RsrpOffset {
    type int32 {
      range 0..24;
    }
  }
  typedef ddt-Lrat_QciProfilePredefined_timerPriority {
    type int32 {
      range 0..100;
    }
  }
  typedef ddt-Lrat_ReportConfigSearch_timeToTriggerA2OutSearch {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EranInterMeLink_remotePort {
    type string {
      length 0..128;
    }
  }
  typedef ddt-Lrat_UserProfile_arpList {
    type int32 {
      range 1..15;
    }
  }
  typedef ddt-Lrat_Paging_pagingDiscardTimerDrxNb {
    type int32 {
      range 1..30;
    }
  }
  typedef ddt-Lrat_UtranTDDFreqRelation_qOffsetFreq {
    type int32 {
      range -15..15;
    }
  }
  typedef ddt-Lrat_LoadBalancingFunction_lbHitRateUtranRemoveThreshold {
    type int32 {
      range 0..99;
    }
  }
  typedef ddt-Lrat_ENodeBFunction_timePhaseMaxDeviationSib16 {
    type int32 {
      range 9..100;
    }
  }
  typedef ddt-Lrat_EranInterMeLink_linkLatency1minAvg {
    type int32 {
      range -1..1000000;
    }
  }
  typedef ddt-Lrat_EUtranCellTDD_tac {
    type int32 {
      range 0..65535;
    }
  }
  typedef ddt-Lrat_EUtranCellFDD_minQciLatencyMeas {
    type int32 {
      range 0..255;
    }
  }
  typedef ddt-Lrat_EUtranCellFDD_tUeBlockingTimer {
    type int32 {
      range 50..200;
    }
  }
  typedef ddt-Lrat_AdmissionControl_ulTransNwBandwidth {
    type int32 {
      range 0..1000;
    }
  }
  typedef ddt-Lrat_CsfbRegParams1xRtt_totalZone {
    type int32 {
      range 0..7;
    }
  }
  typedef ddt-Lrat_Rrc_t304Br {
    type int32 {
      range "50..50 | 100..100 | 150..150 | 200..200 | 500..500 | 1000..1000 | 2000..2000 | 10000..10000";
    }
  }
  typedef ddt-UtranFreqRelation_setMaxNrUtranCellRelations_maxNrUtranCellRelations {
    type int32 {
      range 0..64;
    }
  }
  typedef ddt-Lrat_MdtConfiguration_a2ThresholdRsrpMdt {
    type int32 {
      range -140..-44;
    }
  }
  typedef ddt-Lrat_TermPointToGNB_usedIpAddress {
    type string {
      length 2..39;
    }
  }
  typedef ddt-Lrat_EUtranFreqRelation_qOffsetFreq {
    type int32 {
      range "-24..-24 | -22..-22 | -20..-20 | -18..-18 | -16..-16 | -14..-14 | -12..-12 | -10..-10 | -8..-8 | -6..-6 | -5..-5 | -4..-4 | -3..-3 | -2..-2 | -1..-1 | 0..0 | 1..1 | 2..2 | 3..3 | 4..4 | 5..5 | 6..6 | 8..8 | 10..10 | 12..12 | 14..14 | 16..16 | 18..18 | 20..20 | 22..22 | 24..24";
    }
  }
  typedef ddt-Lrat_ReportConfigA1Sec_timeToTriggerA1Sec {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_Band46UnlicensedProfile_b46C52090MaxPower {
    type int32 {
      range 0..30;
    }
  }
  typedef ddt-Lrat_BearerTriggerElement_arp {
    type int32 {
      range 0..15;
    }
  }
  typedef ddt-Lrat_EUtranFreqRelation_a5Thr1RsrpFreqOffset {
    type int32 {
      range -100..100;
    }
  }
  typedef ddt-Lrat_ENodeBFunction_tS1HoCancelTimer {
    type int32 {
      range 1..30;
    }
  }
  typedef ddt-Lrat_ExternalUtranCellTDD_userLabel {
    type string {
      length 1..128;
    }
  }
  typedef ddt-Lrat_Cdma2000FreqRelation_qOffsetFreq {
    type int32 {
      range -15..15;
    }
  }
  typedef ddt-Lrat_NbIotCell_cellRange {
    type int32 {
      range 1..100;
    }
  }
  typedef ddt-Lrat_MobilityParams1xRtt_gcsnaSequenceContextTimer {
    type int32 {
      range 1..255;
    }
  }
  typedef ddt-Lrat_Rrc_t300NbIot {
    type int32 {
      range "2500..2500 | 4000..4000 | 6000..6000 | 10000..10000 | 15000..15000 | 25000..25000 | 40000..40000 | 60000..60000";
    }
  }
  typedef ddt-Lrat_EUtranCellTDD_hoOptStatTime {
    type int32 {
      range 1..32767;
    }
  }
  typedef ddt-Lrat_ExternalEUtranCellTDD_csgPhysCellId {
    type int32 {
      range "0..503 | 1000..1000";
    }
  }
  typedef ddt-Lrat_FreqGroupPrioGERAN_voicePrio {
    type int32 {
      range "-1000..-1000 | -1..7";
    }
  }
  typedef ddt-Lrat_TermPointToENB_interEnbCaProtVerActive {
    type int32 {
      range -1..2147483647;
    }
  }
  typedef ddt-Lrat_CarrierAggregationFunction_laaSCellActDeactDataThresHyst {
    type int32 {
      range 0..5000;
    }
  }
  typedef ddt-Lrat_EUtranFreqRelationUnlicensed_caFreqPriority {
    type int32 {
      range -1..7;
    }
  }
  typedef ddt-Lrat_SectorCarrier_digitalTilt {
    type int32 {
      range -300..300;
    }
  }
  typedef ddt-Lrat_EUtranCellTDD_lessPrbUsageThreshold {
    type int32 {
      range 0..100;
    }
  }
  typedef ddt-Lrat_ENodeBFunction_combCellSectorSelectThreshRx {
    type int32 {
      range 0..1800;
    }
  }
  typedef ddt-Lrat_EUtranCellTDD_rachRootSequence {
    type int32 {
      range 0..837;
    }
  }
  typedef ddt-Lrat_ExternalEUtranCellFDD_physicalLayerSubCellId {
    type int32 {
      range 0..2;
    }
  }
  typedef ddt-Lrat_EUtranCellTDD_prsPowerBoosting {
    type int32 {
      range 0..3;
    }
  }
  typedef ddt-Lrat_EUtranCellFDD_uncertAltitude {
    type int32 {
      range 0..127;
    }
  }
  typedef ddt-Lrat_ReportConfigEUtraIntraFreqPm_timeToTriggerPm {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_SubscriberProfileID_userLabel {
    type string {
      length 1..128;
    }
  }
  typedef ddt-Lrat_AdmissionControl_dlAdmOverloadThr {
    type int32 {
      range 0..1000;
    }
  }
  typedef ddt-Lrat_ReportConfigSCellA6_a6offset {
    type int32 {
      range -150..150;
    }
  }
  typedef ddt-Lrat_MeasReportConfigParams_a1ThresholdRsrqSecOffset {
    type int32 {
      range -240..240;
    }
  }
  typedef ddt-Lrat_EUtranCellFDD_highestSupportedCeLevelBr {
    type int32 {
      range 0..1;
    }
  }
  typedef ddt-Lrat_LoadBasedCaMsrThr_dlPrbUtilThreshHigh {
    type int32 {
      range 0..100;
    }
  }
  typedef ddt-Lrat_ReportConfigInterRatLb_utranB1ThresholdRscp {
    type int32 {
      range -120..-24;
    }
  }
  typedef ddt-Lrat_ReportConfigInterRatPm_b1ThresholdGeranPm {
    type int32 {
      range -110..-47;
    }
  }
  typedef ddt-Lrat_EUtranCellTDD_dlFrequencyAllocationProportion {
    type int32 {
      range 0..100;
    }
  }
  typedef ddt-Lrat_EUtranCellTDD_pdschTypeBGain {
    type int32 {
      range "0..0 | 1..1 | 2..2 | 3..3";
    }
  }
  typedef ddt-Lrat_EUtranCellFDD_nrOfPreallocatedSrRes {
    type int32 {
      range -1..20;
    }
  }
  typedef ddt-Lrat_DiffAdmCtrlFilteringProfile_firstPreEmptionSpidSet {
    type int32 {
      range "-1..-1 | 1..256";
    }
  }
  typedef ddt-Lrat_AnrFunction_prioHoRate {
    type int32 {
      range 0..100;
    }
  }
  typedef ddt-Lrat_EUtranCellTDD_pdcchPowerBoostMax {
    type int32 {
      range 0..6;
    }
  }
  typedef ddt-Lrat_Band46UnlicensedProfile_b46D54340MaxPower {
    type int32 {
      range 0..30;
    }
  }
  typedef ddt-Lrat_UeMeasControl_lowPrioMeasThresh {
    type int32 {
      range 0..7;
    }
  }
  typedef ddt-Lrat_ENodeBFunction_combCellSectorSelectThreshTx {
    type int32 {
      range 0..1800;
    }
  }
  typedef ddt-Lrat_EUtranCellTDD_pZeroNominalPusch {
    type int32 {
      range -126..24;
    }
  }
  typedef ddt-Lrat_SubFrameConfig_radioframeAllocationPeriod {
    type int32 {
      range "1..1 | 2..2 | 4..4 | 8..8 | 16..16 | 32..32";
    }
  }
  typedef ddt-Lrat_CellSleepNodeFunction_csmEutranInterFMeasReportMin {
    type int32 {
      range 0..1000;
    }
  }
  typedef ddt-Lrat_ReportConfigA5UlTrig_a5Threshold1Rsrp {
    type int32 {
      range -140..-44;
    }
  }
  typedef ddt-Lrat_ReportConfigA5UlTrig_a5Threshold1Rsrq {
    type int32 {
      range -195..-30;
    }
  }
  typedef ddt-Lrat_MACConfiguration_dlMaxHARQTx {
    type int32 {
      range "1..1 | 2..2 | 3..3 | 4..4 | 5..5 | 6..6 | 7..7 | 8..8 | 10..10 | 12..12 | 16..16 | 20..20 | 24..24 | 28..28";
    }
  }
  typedef ddt-Lrat_EUtranCellTDD_pdcchTargetBler {
    type int32 {
      range 1..200;
    }
  }
  typedef ddt-Lrat_AdmissionControl_resourceReservationForDifferentiation {
    type int32 {
      range 0..30;
    }
  }
  typedef ddt-Lrat_LoadBalancingFunction_lbUtranOffloadBackoffTime {
    type int32 {
      range 30..600;
    }
  }
  typedef ddt-Lrat_AnrFunction_probCellDetectMedHoSuccTime {
    type int32 {
      range 1..30;
    }
  }
  typedef ddt-Lrat_EUtranCellFDD_allocThrPucchFormat1 {
    type int32 {
      range 0..2000;
    }
  }
  typedef ddt-Lrat_ReportConfigB2Cdma20001xRtt_timeToTriggerB2 {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_ReportConfigA5_hysteresisA5 {
    type int32 {
      range 0..150;
    }
  }
  typedef ddt-Lrat_Cdma20001xRttFreqRelation_b2Thr1RsrpCdma20001xFreqOffset {
    type int32 {
      range -100..100;
    }
  }
  typedef ddt-Lrat_Paging_maxNoOfPagingRecordsNb {
    type int32 {
      range 1..16;
    }
  }
  typedef ddt-Lrat_WhiteListPlmnIdentity_mcc {
    type int32 {
      range -1..999;
    }
  }
  typedef ddt-Lrat_EUtranCellTDD_ulTxPsdDistrThr {
    type int32 {
      range 0..100;
    }
  }
  typedef ddt-Lrat_Cdma2000FreqRelation_b2Thr1RsrqCdma2000FreqOffset {
    type int32 {
      range -240..240;
    }
  }
  typedef ddt-Lrat_CarrierAggregationFunction_sCellActDeactUlDataThreshHyst {
    type int32 {
      range 0..5000;
    }
  }
  typedef ddt-Lrat_EUtranCellFDD_dlDynUeAdmCtrlOverloadThr {
    type int32 {
      range 0..1000;
    }
  }
  typedef ddt-Lrat_MdtConfiguration_timeToTriggerA2Mdt {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellFDD_prsMutingPattern {
    type string {
      length 1..16;
    }
  }
  typedef ddt-Lrat_UtranFreqRelation_threshXLow {
    type int32 {
      range 0..62;
    }
  }
  typedef ddt-Lrat_EUtranCellTDD_pdcchAdmThreshold {
    type int32 {
      range 0..1000;
    }
  }
  typedef ddt-Lrat_FreqPrioUTRAN_arfcnValueUtranDl {
    type int32 {
      range "-1000..-1000 | 0..16383";
    }
  }
  typedef ddt-Lrat_GeranFreqRelQciB2ThrOffsets_b2Thr1RsrqGeranFreqQciOffset {
    type int32 {
      range -240..240;
    }
  }
  typedef ddt-Lrat_NbIdleModeLoadDistr_nbFreqDistributionList {
    type int32 {
      range 0..100;
    }
  }
  typedef ddt-Lrat_ReportConfigEUtraBadCovPrim_a2ThrRsrpPrimOffsetCeABr {
    type int32 {
      range -100..100;
    }
  }
  typedef ddt-Lrat_EutranCellArea_posCellOpeningAngle {
    type int32 {
      range -1..3599;
    }
  }
  typedef ddt-Lrat_GeranFreqGroup_userLabel {
    type string {
      length 1..128;
    }
  }
  typedef ddt-Lrat_EUtranCellTDD_noOfUlImprovedUe {
    type int32 {
      range 0..5;
    }
  }
  typedef ddt-Lrat_NotificationConfig_notificationRepetitionCoeff {
    type int32 {
      range "2..2 | 4..4";
    }
  }
  typedef ddt-ExternalGeranCell_changeFrequency_arfcnValueGeranDl {
    type int32 {
      range 0..1023;
    }
  }
  typedef ddt-Lrat_SIB7_tReselectionGeran {
    type int32 {
      range 0..7;
    }
  }
  typedef ddt-Lrat_GtpPath_samplingInterval {
    type int32;
  }
  typedef ddt-Lrat_InterNodalProtocolVerRO_interEnbCaProtVerExact {
    type int32 {
      range -1..2147483647;
    }
  }
  typedef ddt-Lrat_EUtranCellFDD_lessPrbUsageThreshold {
    type int32 {
      range 0..100;
    }
  }
  typedef ddt-Lrat_ReportConfigInterRatPm_timeToTriggerPm {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_EUtranCellTDD_lbEUtranCellOffloadCapacity {
    type int32 {
      range 0..1000000;
    }
  }
  typedef ddt-Lrat_UeMeasControl_maxMeasUtraTdd {
    type int32 {
      range 1..5;
    }
  }
  typedef ddt-Lrat_EUtranCellTDD_ulFrequencyAllocationProportion {
    type int32 {
      range 0..100;
    }
  }
  typedef ddt-Lrat_EUtranCellTDD_iuaMaxPrbsPerUe {
    type int32 {
      range 0..100;
    }
  }
  typedef ddt-Lrat_ReportConfigInterRatPm_b2Threshold1RsrpPm {
    type int32 {
      range -140..-44;
    }
  }
  typedef ddt-Lrat_Cdma2000FreqRelation_connectedModeMobilityPrio {
    type int32 {
      range -1..7;
    }
  }
  typedef ddt-Lrat_ReportConfigB2Geran_hysteresisB2 {
    type int32 {
      range 0..150;
    }
  }
  typedef ddt-Lrat_EUtranCellTDD_latencyLongThreshold {
    type int32 {
      range 125..1200;
    }
  }
  typedef ddt-Lrat_ReportConfigSCellA6_hysteresisA6 {
    type int32 {
      range 0..150;
    }
  }
  typedef ddt-Lrat_EUtranFreqRelation_allowedMeasBandwidth {
    type int32 {
      range "6..6 | 15..15 | 25..25 | 50..50 | 75..75 | 100..100";
    }
  }
  typedef ddt-Lrat_EUtranFreqRelation_caFreqProportion {
    type int32 {
      range 0..100;
    }
  }
  typedef ddt-Lrat_EUtranCellFDD_altitude {
    type int32 {
      range -32768..32767;
    }
  }
  typedef ddt-Lrat_EUtranCellFDD_ulHarqVolteBlerTarget {
    type int32 {
      range 0..10;
    }
  }
  typedef ddt-Lrat_QciProfileOperatorDefined_inactivityTimerOffset {
    type int32 {
      range 0..65535;
    }
  }
  typedef ddt-Lrat_ReportConfigB2CdmaUlTrig_hysteresisB2 {
    type int32 {
      range 0..150;
    }
  }
  typedef ddt-Lrat_ReportConfigA1A2Br_timeToTriggerA1UlIntraFSearch {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-Lrat_ENodeBFunction_timePhaseMaxDeviationOtdoa {
    type int32 {
      range 9..100;
    }
  }
  typedef ddt-Lrat_PmchMch_mchSchedulingPeriod {
    type int32 {
      range "8..8 | 16..16 | 32..32 | 64..64 | 128..128 | 256..256 | 512..512 | 1024..1024";
    }
  }
  typedef ddt-Lrat_EUtranCellTDD_pdcchOuterLoopUpStepVolte {
    type int32 {
      range 0..100;
    }
  }
  typedef ddt-Lrat_FreqPrioUTRAN_voicePrio {
    type int32 {
      range "-1000..-1000 | -1..7";
    }
  }
  typedef ddt-Lrat_InterNodalProtocolVerRO_commonProtVerRel {
    type int32 {
      range -1..2147483647;
    }
  }
  typedef ddt-Lrat_EUtranCellTDD_pdcchOuterLoopInitialAdj {
    type int32 {
      range -200..200;
    }
  }
  typedef ddt-Lrat_Band46UnlicensedProfile_b46C51690MaxPower {
    type int32 {
      range 0..30;
    }
  }
  typedef ddt-Lrat_LoadBalancingFunction_lbUeEvaluationTimer {
    type int32 {
      range 0..360;
    }
  }
  typedef ddt-Lrat_ReportConfigEUtraIntraFreqPm_a5ThresholdRsrpPm1 {
    type int32 {
      range -140..-44;
    }
  }
  typedef ddt-Lrat_ReportConfigEUtraIntraFreqPm_a5ThresholdRsrpPm2 {
    type int32 {
      range -140..-44;
    }
  }
  typedef ddt-Lrat_SIB3_threshServingLowQ {
    type int32 {
      range "0..31 | 1000..1000";
    }
  }
  typedef ddt-Lrat_ExternalEUtranCellTDD_channelBandwidth {
    type int32 {
      range "0..0 | 1400..1400 | 3000..3000 | 5000..5000 | 10000..10000 | 15000..15000 | 20000..20000";
    }
  }
  typedef ddt-Lrat_ExternalEUtranCellTDD_lbEUtranCellOffloadCapacity {
    type int32 {
      range 0..1000000;
    }
  }
  typedef ddt-Lrat_EUtranCellTDD_orientMajorAxis {
    type int32 {
      range 0..179;
    }
  }
  typedef ddt-Lrat_GeranFreqGroupRelation_threshXHigh {
    type int32 {
      range 0..62;
    }
  }
  typedef ddt-Lrat_AcBarringConfig1xRtt_acBarring13R9 {
    type int32 {
      range 0..7;
    }
  }
  typedef ddt-Lrat_EUtranCellFDD_prsConfigIndexMapped {
    type int32 {
      range 0..4095;
    }
  }
  typedef ddt-Lrat_EUtranCellFDD_crsGain {
    type int32 {
      range "-300..-300 | -200..-200 | -100..-100 | 0..0 | 177..177 | 300..300 | 477..477 | 600..600";
    }
  }
  grouping struct-GlobalEnbId {
    leaf mnc {
      description "Mobile Network Code (a part of the PLMN identity) for a cell that is served by a neighbor eNB.\n";
      type erienmnrmlrat:ddt-Lrat_GlobalEnbId_mnc;
      default 1;
    }
    leaf enbId {
      description "ENodeB Id\n";
      type erienmnrmlrat:ddt-Lrat_GlobalEnbId_enbId;
      default 0;
    }
    leaf mncLength {
      description "This parameter defines the number of digits for the Mobile Network Code (a part of the PLMN identity) for a cell that is served by a neighbor eNB.\nThe PLMN identity combines the following two parts:\n1. MobileCountryCode, MCC, 3 digits\n2. MobileNetworkCode, MNC, 2 or 3 digits\nExample: If MCC=125 and MNC=46, then plmnId=12546.\n";
      type erienmnrmlrat:ddt-Lrat_GlobalEnbId_mncLength;
      default 2;
    }
    leaf mcc {
      description "Mobile Country Code (a part of the PLMN identity) for a cell that is served by a neighbor eNB.\n";
      type erienmnrmlrat:ddt-Lrat_GlobalEnbId_mcc;
      default 1;
    }
  } // end 'grouping struct-GlobalEnbId'
  grouping struct-InterNodalProtocolVerRO {
    leaf eRanUlCompProtVerExact {
      description "Protocol version the software uses if two eNodeBs have matching versions for Elastic RAN UL CoMP.";
      type erienmnrmlrat:ddt-Lrat_InterNodalProtocolVerRO_eRanUlCompProtVerExact;
      mandatory true;
    }
    leaf interEnbCaProtVerExact {
      description "Protocol version the software uses if two eNodeBs have matching versions for inter-eNodeB CA.";
      type erienmnrmlrat:ddt-Lrat_InterNodalProtocolVerRO_interEnbCaProtVerExact;
      mandatory true;
    }
    leaf eRanCaProtVerExact {
      description "Protocol version the software uses if two eNodeBs have matching versions for Elastic RAN CA.";
      type erienmnrmlrat:ddt-Lrat_InterNodalProtocolVerRO_eRanCaProtVerExact;
      mandatory true;
    }
    leaf commonProtVerRelMinus1 {
      description "Latest common protocol version minus 1 release that can be used.";
      type erienmnrmlrat:ddt-Lrat_InterNodalProtocolVerRO_commonProtVerRelMinus1;
      mandatory true;
    }
    leaf commonProtVerRelMinus2 {
      description "Latest common protocol version minus 2 releases that can be used.";
      type erienmnrmlrat:ddt-Lrat_InterNodalProtocolVerRO_commonProtVerRelMinus2;
      mandatory true;
    }
    leaf interEnbUlCompProtVerExact {
      description "Protocol version the software uses if two eNodeBs have matching versions for inter-eNodeB UL CoMP.";
      type erienmnrmlrat:ddt-Lrat_InterNodalProtocolVerRO_interEnbUlCompProtVerExact;
      mandatory true;
    }
    leaf commonProtVerRelMinus3 {
      description "Latest common protocol version minus 3 releases that can be used.";
      type erienmnrmlrat:ddt-Lrat_InterNodalProtocolVerRO_commonProtVerRelMinus3;
      mandatory true;
    }
    leaf commonProtVerRel {
      description "Latest common protocol version that can be used.";
      type erienmnrmlrat:ddt-Lrat_InterNodalProtocolVerRO_commonProtVerRel;
      mandatory true;
    }
  } // end 'grouping struct-InterNodalProtocolVerRO'
  grouping struct-IfoConfig {
    leaf-list subscriberGroupRefList {
      min-elements 0;
      max-elements 12;
      status deprecated {
        yexte:status-information "Since 18.Q4. Has no functional behavior. Planned to be removed.";
      }
      description "Order of PTM Subscriber Group offload from cell, using IFO feature.\nUEs not assigned to any group are offloaded in first group.\nIf list is empty, functionality is disabled.\nNo effect when cellType is set to NON_PRIORITY.";
      erienmyext:enm-type MOREF;
      type string;
    }
  } // end 'grouping struct-IfoConfig'
  grouping struct-BearerTriggerElement {
    leaf qci {
      description "The QCI of the bearer that is evaluated against this bearerTriggerElement. Value 0 indicates that all QCIs are considered matching.";
      type erienmnrmlrat:ddt-Lrat_BearerTriggerElement_qci;
      default 0;
    }
    leaf arp {
      description "The ARP of the bearer that is evaluated against this bearerTriggerElement. Value 0 indicates that all ARPs are considered matching.";
      type erienmnrmlrat:ddt-Lrat_BearerTriggerElement_arp;
      default 0;
    }
  } // end 'grouping struct-BearerTriggerElement'
  grouping struct-MbsfnSubframeConfigRO {
    leaf subframeAllocation {
      status deprecated {
        yexte:status-information "Since 17.Q2. Replaced by SubFrameConfig::subframeAllocation. Planned to be removed.";
      }
      description "Defines the subframes that are allocated for MBSFN within the radio frame allocation period defined by the radioFrameAllocationPeriod and the radioFrameAllocationOffset. Two options are possible, that is, if set to 1 the subframe allocation is set by the subframeAllocationOneFrame attribute, and if set to 4 the subframe allocation is set by the subframeAllocationFourFrame attribute.";
      type erienmnrmlrat:ddt-Lrat_MbsfnSubframeConfigRO_subframeAllocation;
      mandatory true;
    }
    leaf subframeAllocationFourFrame {
      status deprecated {
        yexte:status-information "Since 17.Q2. Replaced by SubFrameConfig::sfAllocationFourFrame. Planned to be removed.";
      }
      description "A bitmap that indicates MBSFN subframe allocation in four consecutive radio frames, \"1\" denotes that the corresponding subframe is allocated for MBSFN. \"0\" denotes that the corresponding subframe is not allocated for MBSFN. The bitmap is interpreted as follows:\nFDD: Starting from the first radio frame and from the first or leftmost bit in the bitmap, the allocation applies to subframes #1, #2, #3 , #6, #7, and #8 in the sequence of the four radio frames.\nTDD: Starting from the first radio frame and from the first or leftmost bit in the bitmap, the allocation applies to subframes #3, #4, #7, #8, and #9 in the sequence of the four radio frames. The last four bits are not used. UL subframes are not allocated.";
      type erienmnrmlrat:ddt-Lrat_MbsfnSubframeConfigRO_subframeAllocationFourFrame;
      mandatory true;
    }
    leaf radioframeAllocationOffset {
      status deprecated {
        yexte:status-information "Since 17.Q2. Replaced by SubFrameConfig::radioframeAllocationOffset. Planned to be removed.";
      }
      description "Radio frames that contain MBSFN subframes occur when equation SFN mod radioFrameAllocationPeriod = radioFrameAllocationOffset is satisfied.";
      yexte:dependencies "It is required that radioframeAllocationOffset < radioframeAllocationPeriod.";
      type erienmnrmlrat:ddt-Lrat_MbsfnSubframeConfigRO_radioframeAllocationOffset;
      mandatory true;
    }
    leaf subframeAllocationOneFrame {
      status deprecated {
        yexte:status-information "Since 17.Q2. Replaced by SubFrameConfig::sfAllocationOneFrame. Planned to be removed.";
      }
      description "A bitmap that indicates MBSFN subframe allocation in one radio frame.\n\"1\" denotes that the corresponding subframe is allocated for MBSFN. \"0\" denotes that the corresponding subframe is not allocated for MBSFN.The following mapping applies:\nFDD: The first or leftmost bit defines the MBSFN allocation for subframe #1, the second bit for #2, third bit for #3 , fourth bit for #6, fifth bit for #7, sixth bit for #8.\nTDD: The first or leftmost bit defines the allocation for subframe #3, the second bit for #4, third bit for #7, fourth bit for #8, fifth bit for #9. UL subframes are not allocated. The last bit is not used.";
      type erienmnrmlrat:ddt-Lrat_MbsfnSubframeConfigRO_subframeAllocationOneFrame;
      mandatory true;
    }
    leaf radioframeAllocationPeriod {
      status deprecated {
        yexte:status-information "Since 17.Q2. Replaced by SubFrameConfig::radioframeAllocationPeriod. Planned to be removed.";
      }
      description "Radio frames that contain MBSFN subframes occur when equation SFN mod radioFrameAllocationPeriod = radioFrameAllocationOffset is satisfied. When fourFrames is used for subframeAllocation, the equation defines the first radio frame referred to in the description below. Values 1 and 2 are not applicable when fourFrames is used for subframeAllocation.";
      yexte:dependencies "Values 1 and 2 are not applicable when fourFrames is used for subframeAllocation. It is required that radioframeAllocationOffset < radioframeAllocationPeriod.";
      type erienmnrmlrat:ddt-Lrat_MbsfnSubframeConfigRO_radioframeAllocationPeriod;
      mandatory true;
    }
  } // end 'grouping struct-MbsfnSubframeConfigRO'
  grouping struct-MeasReportConfigParams {
    leaf b2Threshold2RscpUtraOffset {
      description "QCI dependent offset for the absolute threshold b2Threshold2RscpUtra. If the value of the offset is 0, then the threshold corresponding to this QCI profile will be the same as the \"base\" value in the MO class, namely b2Threshold2RscpUtra.\nThe rule is that the threshold for a certain QCI profile is computed as ReportConfigB2Utra.b2Threshold2RscpUtra+QciProfilePredefined.measReportConfigParams.b2Threshold2RscpUtraOffset";
      type erienmnrmlrat:ddt-Lrat_MeasReportConfigParams_b2Threshold2RscpUtraOffset;
      default 0;
    }
    leaf timeToTriggerInterA3Rsrq {
      description "QCI-depended specific time-to-trigger value for event A3 with trigger quantity RSRQ. Used for inter-frequency.\nIf timeToTriggerInterA3Rsrq has value different than -1 this value is used instead of QciProfilePredefined::measReportConfigParams.timeToTriggerInterA3 or QciProfileOperatorDefined::measReportConfigParams.timeToTriggerInterA3.";
      type erienmnrmlrat:ddt-Lrat_MeasReportConfigParams_timeToTriggerInterA3Rsrq;
      default -1;
    }
    leaf b2Threshold1RsrqGeranOffset {
      description "QCI dependent offset for the absolute threshold ReportConfigB2Geran.b2Threshold1Rsrq. If the value of the offset is 0, then the threshold corresponding to this QCI profile will be the same as the \"base\" value in the MO class, namely ReportConfigB2Geran.b2Threshold1Rsrq.\nThe rule is that the threshold for a certain QCI profile is computed as ReportConfigB2Geran.b2Threshold1Rsrq+QciProfilePredefined.measReportConfigParams.b2Threshold1RsrqGeranOffset";
      type erienmnrmlrat:ddt-Lrat_MeasReportConfigParams_b2Threshold1RsrqGeranOffset;
      default 0;
    }
    leaf b2Threshold1RsrpUtraOffset {
      description "QCI dependent offset for the absolute threshold ReportConfigB2Utra.b2Threshold1Rsrp. If the value of the offset is 0, then the threshold corresponding to this QCI profile will be the same as the \"base\" value in the MO class, namely ReportConfigB2Utra.b2Threshold1Rsrp.\nThe rule is that the threshold for a certain QCI profile is computed as ReportConfigB2Utra.b2Threshold1Rsrp+QciProfilePredefined.measReportConfigParams.b2Threshold1RsrpUtraOffset";
      type erienmnrmlrat:ddt-Lrat_MeasReportConfigParams_b2Threshold1RsrpUtraOffset;
      default 0;
    }
    leaf a5Threshold1RsrpOffset {
      description "QCI dependent offset for the absolute threshold a5Threshold1Rsrp. If the value of the offset is 0, then the threshold corresponding to this QCI profile will be the same as the \"base\" value in the MO class, namely ReportConfigA5.a5Threshold1Rsrp.\nThe rule is that the threshold for a certain QCI profile is computed as ReportConfigA5.a5Threshold1Rsrp+QciProfilePredefined.measReportConfigParams.a5Threshold1RsrpOffset";
      type erienmnrmlrat:ddt-Lrat_MeasReportConfigParams_a5Threshold1RsrpOffset;
      default 0;
    }
    leaf b2Threshold2GeranOffset {
      description "QCI dependent offset for the absolute threshold b2Threshold2Geran. If the value of the offset is 0, then the threshold corresponding to this QCI profile will be the same as the \"base\" value in the MO class, namely b2Threshold2Geran.\nThe rule is that the threshold for a certain QCI profile is computed as ReportConfigB2Geran.b2Threshold2Geran+QciProfilePredefined.measReportConfigParams.b2Threshold2GeranOffset";
      type erienmnrmlrat:ddt-Lrat_MeasReportConfigParams_b2Threshold2GeranOffset;
      default 0;
    }
    leaf timeToTriggerInterA3 {
      description "QCI-depended specific time-to-trigger value for event A3. Used for inter-frequency.\nIf timeToTriggerInterA3 has value different than -1 this value is used instead of ReportConfigEUtraIFBestCell.timeToTriggerA3.";
      type erienmnrmlrat:ddt-Lrat_MeasReportConfigParams_timeToTriggerInterA3;
      default -1;
    }
    leaf a1ThresholdRsrqPrimOffset {
      description "QCI dependent offset for the absolute threshold a1ThresholdRsrpPrim. If the value of the offset is 0, then the threshold corresponding to this QCI profile will be the same as the \"base\" value in the MO class, namely ReportConfigA1Prim.a1ThresholdRsrqPrim.\nThe rule is that the threshold for a certain QCI profile is computed as ReportConfigA1Prim.a1ThresholdRsrqPrim+QciProfilePredefined.measReportConfigParams.a1ThresholdRsrqPrimOffset";
      type erienmnrmlrat:ddt-Lrat_MeasReportConfigParams_a1ThresholdRsrqPrimOffset;
      default 0;
    }
    leaf b2Threshold2EcNoUtraOffset {
      description "QCI dependent offset for the absolute threshold b2Threshold2EcNoUtra. If the value of the offset is 0, then the threshold corresponding to this QCI profile will be the same as the \"base\" value in the MO class, namely b2Threshold2EcNoUtra.\nThe rule is that the threshold for a certain QCI profile is computed as ReportConfigB2Utra.b2Threshold2EcNoUtra+QciProfilePredefined.measReportConfigParams.b2Threshold2EcNoUtraOffset";
      type erienmnrmlrat:ddt-Lrat_MeasReportConfigParams_b2Threshold2EcNoUtraOffset;
      default 0;
    }
    leaf a2ThresholdRsrqSecOffset {
      description "QCI dependent offset for the absolute threshold a2ThresholdRsqSec. If the value of the offset is 0, then the threshold corresponding to this QCI profile will be the same as the \"base\" value in the MO class, namely ReportConfigA2Sec.a2ThresholdRsrqSec.\nThe rule is that the threshold for a certain QCI profile is computed as ReportConfigA2Sec.a2ThresholdRsrqSec+QciProfilePredefined.measReportConfigParams.a2ThresholdRsrqSecOffset\nIf Mobility Control at Poor Coverage feature is enabled, \"a1a2SearchThresholdRsrq\" replaces \"a2ThresholdRsrqSec\" and\"ReportConfigSearch\" replaces \"ReportConfigA2Sec\" in the above description.";
      type erienmnrmlrat:ddt-Lrat_MeasReportConfigParams_a2ThresholdRsrqSecOffset;
      default 0;
    }
    leaf a2ThresholdRsrpPrimOffset {
      description "QCI dependent offset for the absolute threshold a2ThresholdRsrpPrim. If the value of the offset is 0, then the threshold corresponding to this QCI profile will be the same as the \"base\" value in the MO class, namely ReportConfigA2Prim.a2ThresholdRsrpPrim.\nThe rule is that the threshold for a certain QCI profile is computed as ReportConfigA2Prim.a2ThresholdRsrpPrim+QciProfilePredefined.measReportConfigParams.a2ThresholdRsrpPrimOffset\nIf Mobility Control at Poor Coverage feature is enabled, \"a1a2SearchThresholdRsrp\" replaces \"a2ThresholdRsrpPrim\" and\"ReportConfigSearch\" replaces \"ReportConfigA2Prim\" in the above description.";
      type erienmnrmlrat:ddt-Lrat_MeasReportConfigParams_a2ThresholdRsrpPrimOffset;
      default 0;
    }
    leaf b2Threshold2Cdma2000Offset {
      description "QCI dependent offset for the absolute threshold b2Threshold2Cdma2000. If the value of the offset is 0, then the threshold corresponding to this QCI profile will be the same as the \"base\" value in the MO class, namely b2Threshold2Cdma2000.\nThe rule is that the threshold for a certain QCI profile is computed as ReportConfigB2Cdma2000.b2Threshold2Cdma2000+QciProfilePredefined.measReportConfigParams.b2Threshold2Cdma2000Offset";
      type erienmnrmlrat:ddt-Lrat_MeasReportConfigParams_b2Threshold2Cdma2000Offset;
      default 0;
    }
    leaf a2ThresholdRsrqPrimOffset {
      description "QCI dependent offset for the absolute threshold a2ThresholdRsrqPrim. If the value of the offset is 0, then the threshold corresponding to this QCI profile will be the same as the \"base\" value in the MO class, namely ReportConfigA2Prim.a2ThresholdRsrqPrim.\nThe rule is that the threshold for a certain QCI profile is computed as ReportConfigA2Prim.a2ThresholdRsrqPrim+QciProfilePredefined.measReportConfigParams.a2ThresholdRsrqPrimOffset";
      type erienmnrmlrat:ddt-Lrat_MeasReportConfigParams_a2ThresholdRsrqPrimOffset;
      default 0;
    }
    leaf b2Threshold1RsrpGeranOffset {
      description "QCI dependent offset for the absolute threshold ReportConfigB2Geran.b2Threshold1Rsrp. If the value of the offset is 0, then the threshold corresponding to this QCI profile will be the same as the \"base\" value in the MO class, namely ReportConfigB2Geran.b2Threshold1Rsrp.\nThe rule is that the threshold for a certain QCI profile is computed as ReportConfigB2Geran.b2Threshold1Rsrp+QciProfilePredefined.measReportConfigParams.b2Threshold1RsrpGeranOffset";
      type erienmnrmlrat:ddt-Lrat_MeasReportConfigParams_b2Threshold1RsrpGeranOffset;
      default 0;
    }
    leaf a2ThresholdRsrpSecOffset {
      description "QCI dependent offset for the absolute threshold a2ThresholdRsrpPrim. If the value of the offset is 0, then the threshold corresponding to this QCI profile will be the same as the \"base\" value in the MO class, namely ReportConfigA2Sec.a2ThresholdRsrpSec.\nThe rule is that the threshold for a certain QCI profile is computed as ReportConfigA2Sec.a2ThresholdRsrpSec+QciProfilePredefined.measReportConfigParams.a2ThresholdRsrpSecOffset";
      type erienmnrmlrat:ddt-Lrat_MeasReportConfigParams_a2ThresholdRsrpSecOffset;
      default 0;
    }
    leaf b2Threshold1RsrpCdma2000Offset {
      description "QCI dependent offset for the absolute threshold ReportConfigB2Cdma2000.b2Threshold1Rsrp. If the value of the offset is 0, then the threshold corresponding to this QCI profile will be the same as the \"base\" value in the MO class, namely ReportConfigB2Cdma2000.b2Threshold1Rsrp.\nThe rule is that the threshold for a certain QCI profile is computed as ReportConfigB2Cdma2000.b2Threshold1Rsrp+QciProfilePredefined.measReportConfigParams.b2Threshold1RsrpCdma2000Offset";
      type erienmnrmlrat:ddt-Lrat_MeasReportConfigParams_b2Threshold1RsrpCdma2000Offset;
      default 0;
    }
    leaf a3IntraOffsetAdjustmentRsrp {
      description "QCI-dependent offset adjustment for the absolute offset a3offset. If value is 0, then offset corresponding to this QCI profile is the same as \"base\" value in MO class (ReportConfigEUtraBestCell.a3offset).\nOffset for a QCI profile is computed as\nReportConfigEUtraBestCell.a3offset+QciProfilePredefined.measReportConfigParams.a3IntraOffsetAdjustmentRsrp.";
      type erienmnrmlrat:ddt-Lrat_MeasReportConfigParams_a3IntraOffsetAdjustmentRsrp;
      default 0;
    }
    leaf a5Threshold2RsrqOffset {
      description "QCI dependent offset for the absolute threshold a5Threshold2Rsrq. If the value of the offset is 0, then the threshold corresponding to this QCI profile will be the same as the \"base\" value in the MO class, namely ReportConfigA5.a5Threshold2Rsrq.\nThe rule is that the threshold for a certain QCI profile is computed as ReportConfigA5.a5Threshold2Rsrq+QciProfilePredefined.measReportConfigParams.a5Threshold2RsrqOffset";
      type erienmnrmlrat:ddt-Lrat_MeasReportConfigParams_a5Threshold2RsrqOffset;
      default 0;
    }
    leaf a1ThresholdRsrqSecOffset {
      description "QCI dependent offset for the absolute threshold a1ThresholdRsrqSec. If the value of the offset is 0, then the threshold corresponding to this QCI profile will be the same as the \"base\" value in the MO class, namely ReportConfigA1Sec.a1ThresholdRsrqSec.\nThe rule is that the threshold for a certain QCI profile is computed as ReportConfigA1Sec.a1ThresholdRsrqSec+QciProfilePredefined.measReportConfigParams.a1ThresholdRsrqSecOffset\nIf Mobility Control at Poor Coverage feature is enabled, \"a1a2SearchThresholdRsrq\" replaces \"a1ThresholdRsrqSec\" and\"ReportConfigSearch\" replaces \"ReportConfigA1Sec\" in the above description.";
      type erienmnrmlrat:ddt-Lrat_MeasReportConfigParams_a1ThresholdRsrqSecOffset;
      default 0;
    }
    leaf a3IntraOffsetAdjustmentRsrq {
      description "QCI-dependent offset adjustment for the absolute offset a3offset. If value is 0, then offset corresponding to this QCI profile is the same as \"base\" value in MO class (ReportConfigEUtraBestCell.a3offset).\nOffset for a QCI profile is computed as\nReportConfigEUtraBestCell.a3offset+QciProfilePredefined.measReportConfigParams.a3IntraOffsetAdjustmentRsrq.";
      type erienmnrmlrat:ddt-Lrat_MeasReportConfigParams_a3IntraOffsetAdjustmentRsrq;
      default 0;
    }
    leaf a5Threshold2RsrpOffset {
      description "QCI dependent offset for the absolute threshold a5Threshold2Rsrp. If the value of the offset is 0, then the threshold corresponding to this QCI profile will be the same as the \"base\" value in the MO class, namely ReportConfigA5.a5Threshold2Rsrp.\nThe rule is that the threshold for a certain QCI profile is computed as ReportConfigA5.a5Threshold2Rsrp+QciProfilePredefined.measReportConfigParams.a5Threshold2RsrpOffset";
      type erienmnrmlrat:ddt-Lrat_MeasReportConfigParams_a5Threshold2RsrpOffset;
      default 0;
    }
    leaf a1ThresholdRsrpSecOffset {
      description "QCI dependent offset for the absolute threshold a1ThresholdRsrpSec. If the value of the offset is 0, then the threshold corresponding to this QCI profile will be the same as the \"base\" value in the MO class, namely ReportConfigA1Sec.a1ThresholdRsrpSec.\nThe rule is that the threshold for a certain QCI profile is computed as ReportConfigA1Sec.a1ThresholdRsrpSec+QciProfilePredefined.measReportConfigParams.a1ThresholdRsrpSecOffset";
      type erienmnrmlrat:ddt-Lrat_MeasReportConfigParams_a1ThresholdRsrpSecOffset;
      default 0;
    }
    leaf a1ThresholdRsrpPrimOffset {
      description "QCI dependent offset for the absolute threshold a1ThresholdRsrpPrim. If the value of the offset is 0, then the threshold corresponding to this QCI profile will be the same as the \"base\" value in the MO class, namely ReportConfigA1Prim.a1ThresholdRsrpPrim.\nThe rule is that the threshold for a certain QCI profile is computed as ReportConfigA1Prim.a1ThresholdRsrpPrim+QciProfilePredefined.measReportConfigParams.a1ThresholdRsrpPrimOffset\nIf Mobility Control at Poor Coverage feature is enabled, \"a1a2SearchThresholdRsrp\" replaces \"a1ThresholdRsrpPrim\" and \"ReportConfigSearch\" replaces \"ReportConfigA1Prim\" in the above description.";
      type erienmnrmlrat:ddt-Lrat_MeasReportConfigParams_a1ThresholdRsrpPrimOffset;
      default 0;
    }
    leaf b2Threshold1RsrqUtraOffset {
      description "QCI dependent offset for the absolute threshold ReportConfigB2Utra.b2Threshold1Rsrq. If the value of the offset is 0, then the threshold corresponding to this QCI profile will be the same as the \"base\" value in the MO class, namely ReportConfigB2Utra.b2Threshold1Rsrq.\nThe rule is that the threshold for a certain QCI profile is computed as ReportConfigB2Utra.b2Threshold1Rsrq+QciProfilePredefined.measReportConfigParams.b2Threshold1RsrqUtraOffset";
      type erienmnrmlrat:ddt-Lrat_MeasReportConfigParams_b2Threshold1RsrqUtraOffset;
      default 0;
    }
    leaf b2Threshold1RsrqCdma2000Offset {
      description "QCI dependent offset for the absolute threshold ReportConfigB2Cdma2000.b2Threshold1Rsrq. If the value of the offset is 0, then the threshold corresponding to this QCI profile will be the same as the \"base\" value in the MO class, namely ReportConfigB2Cdma2000.b2Threshold1Rsrq.\nThe rule is that the threshold for a certain QCI profile is computed as ReportConfigB2Cdma2000.b2Threshold1Rsrq+QciProfilePredefined.measReportConfigParams.b2Threshold1RsrqCdma2000Offset";
      type erienmnrmlrat:ddt-Lrat_MeasReportConfigParams_b2Threshold1RsrqCdma2000Offset;
      default 0;
    }
    leaf a3InterOffsetAdjustmentRsrp {
      description "QCI-dependent offset adjustment for the absolute offset a3offset. If value is 0, then offset corresponding to this QCI profile is the same as \"base\" value in MO class (ReportConfigEUtraIFBestCell.a3offset).\nOffset for a QCI profile is computed as ReportConfigEUtraIFBestCell.a3offset+QciProfilePredefined.measReportConfigParams.a3InterOffsetAdjustmentRsrp.";
      type erienmnrmlrat:ddt-Lrat_MeasReportConfigParams_a3InterOffsetAdjustmentRsrp;
      default 0;
    }
    leaf offsetPerQciPrio {
      description "QCI-depended priority of the offset. Offset with maximum priority is taken into calculation for absolute offset/threshold for mobility purpose.\nValue -1 means offset is excluded from selection.\nValue 0 means lowest priority.\nValue 7 means highest priority.";
      type erienmnrmlrat:ddt-Lrat_MeasReportConfigParams_offsetPerQciPrio;
      default 0;
    }
    leaf a3InterOffsetAdjustmentRsrq {
      description "QCI-dependent offset adjustment for the absolute offset a3offset. If value is 0, then offset corresponding to this QCI profile is the same as \"base\" value in the MO class (ReportConfigEUtraIFBestCell::a3offset).\nOffset for a QCI profile is computed as ReportConfigEUtraIFBestCell::a3offset+QciProfilePredefined::measReportConfigParams.a3InterOffsetAdjustmentRsrq.";
      type erienmnrmlrat:ddt-Lrat_MeasReportConfigParams_a3InterOffsetAdjustmentRsrq;
      default 0;
    }
    leaf a5Threshold1RsrqOffset {
      description "QCI dependent offset for the absolute threshold a5Threshold1Rsrq. If the value of the offset is 0, then the threshold corresponding to this QCI profile will be the same as the \"base\" value in the MO class, namely ReportConfigA5.a5Threshold1Rsrq.\nThe rule is that the threshold for a certain QCI profile is computed as ReportConfigA5.a5Threshold1Rsrq+QciProfilePredefined.measReportConfigParams.a5Threshold1RsrqOffset";
      type erienmnrmlrat:ddt-Lrat_MeasReportConfigParams_a5Threshold1RsrqOffset;
      default 0;
    }
    leaf timeToTriggerIntraA3 {
      description "QCI-depended specific time-to-trigger value for event A3. Used for intra-frequency.\nIf timeToTriggerIntraA3 has value different than -1 this value is used instead of ReportConfigEUtraBestCell.timeToTriggerA3.";
      type erienmnrmlrat:ddt-Lrat_MeasReportConfigParams_timeToTriggerIntraA3;
      default -1;
    }
  } // end 'grouping struct-MeasReportConfigParams'
  grouping struct-StmConfig {
    leaf sendInhibitImpEnabled {
      status deprecated {
        yexte:status-information "Since 18.Q4. Has no functional behavior. Planned to be removed.";
      }
      description "If cellType is set to PRIORITY, enables sending Inhibit Idle Mode Prioritization Traffic Load State when subscription ratio in cell exceeds EUtranCellFDD/EUtranCellTDD::lbEUtranTriggerOffloadThreshold.\nNo effect when cellType is set to NON_PRIORITY.";
      type boolean;
      default false;
    }
    leaf-list subscriberGroupRefList {
      min-elements 0;
      max-elements 12;
      status deprecated {
        yexte:status-information "Since 18.Q4. Has no functional behavior. Planned to be removed.";
      }
      description "If cellType is set to NON_PRIORITY, specifies PTM Subscriber Groups inhibited for Idle Mode Prioritization.\nIf empty, functionality is disabled.\nNo effect when cellType is set to PRIORITY.";
      erienmyext:enm-type MOREF;
      type string;
    }
  } // end 'grouping struct-StmConfig'
  grouping struct-ReportConfigParamsQciOffset {
    leaf a1a2ThrRsrpQciOffset {
      description "The QCI specific offset on cell level for the absolute threshold a1a2ThresholdRsrp, RSRP threshold value for events A1Search and A2Search, used for Multi-Layer Service-Triggered Mobility.";
      type erienmnrmlrat:ddt-Lrat_ReportConfigParamsQciOffset_a1a2ThrRsrpQciOffset;
      default 0;
    }
    leaf a1a2ThrRsrqQciOffset {
      description "The QCI specific offset on cell level for the absolute threshold a1a2ThresholdRsrq, RSRQ threshold value for events A1Search and A2Search, used for Multi-Layer Service-Triggered Mobility.";
      type erienmnrmlrat:ddt-Lrat_ReportConfigParamsQciOffset_a1a2ThrRsrqQciOffset;
      default 0;
    }
    leaf qciProfileRef {
      description "Refers to the QCI profile MO, QciProfilePredefined or QciProfileOperatorDefined.";
      erienmyext:enm-type MOREF;
      type string;
    }
  } // end 'grouping struct-ReportConfigParamsQciOffset'
  grouping struct-ChangeNotificationSIBs {
    leaf changeNotificationSIB13 {
      description "Indicates, when the SIB13 content is changed, if SI Change Notification shall be broadcasted prior to broadcast of updated SI.";
      type boolean;
      default true;
    }
    leaf changeNotificationSIB16 {
      description "Indicates, when the SIB16 content is changed, if SI Change Notification shall be broadcasted prior to broadcast of updated SI.";
      type boolean;
      default true;
    }
    leaf changeNotificationSIB15 {
      description "Indicates, when the SIB15 content is changed, if SI Change Notification shall be broadcasted prior to broadcast of updated SI.";
      type boolean;
      default true;
    }
    leaf changeNotificationSIB3 {
      description "Indicates, when the SIB3 content is changed, if SI Change Notification shall be broadcasted prior to broadcast of updated SI.\n";
      type boolean;
      default true;
    }
    leaf changeNotificationSIB4 {
      description "Indicates, when the SIB4 content is changed, if SI Change Notification shall be broadcasted prior to broadcast of updated SI.\n";
      type boolean;
      default true;
    }
    leaf changeNotificationSIB1 {
      description "Indicates, when the SIB1 content is changed, if SI Change Notification shall be broadcasted prior to broadcast of updated SI.\n";
      type boolean;
      default true;
    }
    leaf changeNotificationSIB2 {
      description "Indicates, when the SIB2 content is changed, if SI Change Notification shall be broadcasted prior to broadcast of updated SI.\n";
      type boolean;
      default true;
    }
    leaf changeNotificationSIB7 {
      description "Indicates, when the SIB7 content is changed, if SI Change Notification shall be broadcasted prior to broadcast of updated SI.\n";
      type boolean;
      default true;
    }
    leaf changeNotificationSIB8 {
      description "Indicates, when the SIB8 content is changed, if SI Change Notification shall be broadcasted prior to broadcast of updated SI.\n";
      type boolean;
      default true;
    }
    leaf changeNotificationSIB5 {
      description "Indicates, when the SIB5 content is changed, if SI Change Notification shall be broadcasted prior to broadcast of updated SI.\n";
      type boolean;
      default true;
    }
    leaf changeNotificationSIB6 {
      description "Indicates, when the SIB6 content is changed, if SI Change Notification shall be broadcasted prior to broadcast of updated SI.\n";
      type boolean;
      default true;
    }
  } // end 'grouping struct-ChangeNotificationSIBs'
  grouping struct-A2CriticalPCOffsetMCPC {
    leaf a2CriticalThrRsrqPCOffset {
      description "The high power UE specific offset for the absolute threshold a2CriticalThresholdRsrq, RSRQ threshold value for event A2Critical.";
      type erienmnrmlrat:ddt-Lrat_A2CriticalPCOffsetMCPC_a2CriticalThrRsrqPCOffset;
      default 0;
    }
    leaf powerClass {
      description "Indicate the power class. Value should be unique in the structure.";
      type erienmnrmlrat:enum-PowerClass;
      default PC_2;
    }
    leaf a2CriticalThrRsrpPCOffset {
      description "The high power UE specific offset for the absolute threshold a2CriticalThresholdRsrp, RSRP threshold value for event A2Critical.";
      type erienmnrmlrat:ddt-Lrat_A2CriticalPCOffsetMCPC_a2CriticalThrRsrpPCOffset;
      default 0;
    }
  } // end 'grouping struct-A2CriticalPCOffsetMCPC'
  grouping struct-MappingInfoNbSIBs {
    leaf mappingInfoNbSIB14 {
      description "Mapping of NB-SIB14.";
      type erienmnrmlrat:enum-MappingInfo;
      default NOT_MAPPED;
    }
    leaf mappingInfoNbSIB3 {
      description "Mapping of NB-SIB3.";
      type erienmnrmlrat:enum-MappingInfo;
      default MAPPED_SI_1;
    }
    leaf mappingInfoNbSIB4 {
      description "Mapping of NB-SIB4.";
      type erienmnrmlrat:enum-MappingInfo;
      default NOT_MAPPED;
    }
    leaf mappingInfoNbSIB16 {
      description "Mapping of NB-SIB16.";
      type erienmnrmlrat:enum-MappingInfo;
      default NOT_MAPPED;
    }
    leaf mappingInfoNbSIB5 {
      description "Mapping of NB-SIB5.";
      type erienmnrmlrat:enum-MappingInfo;
      default NOT_MAPPED;
    }
  } // end 'grouping struct-MappingInfoNbSIBs'
  grouping struct-BandClassPrioCdma1xRtt {
    leaf cdma1xRttBandClass {
      description "1xRTT frequency band in which the 1xRTT Carrier can be found";
      type erienmnrmlrat:enum-HrpdBandClass;
      default BAND_CLASS_0;
    }
    leaf csFallbackPrio {
      description "CDMA2000 1xRTT CSFB frequency priority.\nThis parameter prioritizes CDMA2000 1xRTT frequencies among all frequencies related to the cell for UE in connected mode.\nSets the priority to which frequency  to make CS Fallback to (0 means the lowest priority). This parameter is only valid for normal CS Fallback calls.\nWhen value is configured to -1000, the parameter is ignored.";
      type erienmnrmlrat:ddt-Lrat_BandClassPrioCdma1xRtt_csFallbackPrio;
      default -1000;
    }
    leaf voicePrio {
      description "This attribute prioritizes CDMA 1xRtt frequencies among all frequencies related to the cell for User Equipments (UEs) in connected mode. It sets the priority value for the frequency to which the mobility action for a voice session is performed.\nThe value -1 means the frequency is excluded.\nThe value 0 means the lowest priority.\nThe value 7 means the highest priority.";
      type erienmnrmlrat:ddt-Lrat_BandClassPrioCdma1xRtt_voicePrio;
      default 0;
    }
    leaf cellReselectionPriority {
      description "CellReselectionPriority concerns the absolute priority of the concerned carrier frequency, as transmitted to the UE in the IE idleModeMobilityControlInfo in the RRCConnectionRelease message, and used by the cell reselection procedure. Corresponds with parameter \"priority\" in TS 36.304.\nValue 0 means: lowest priority. The UE behaviour for the case the field is absent, if applicable, is specified in TS 36.304.\nWhen value is configured to -1000, the frequency is not included in the idleModeMobilityControlInfo of the RRCConnectionRelease message.";
      type erienmnrmlrat:ddt-Lrat_BandClassPrioCdma1xRtt_cellReselectionPriority;
      default -1000;
    }
    leaf freqCdma {
      description "Carrier frequency within a CDMA2000 1xRTT band\nWhen the value is configured to -1000, the parameter is ignored and the csFallbackPrio and csFallbackPrioEC apply to all frequencies within one band.";
      type erienmnrmlrat:ddt-Lrat_BandClassPrioCdma1xRtt_freqCdma;
      default -1000;
    }
    leaf csFallbackPrioEC {
      description "CDMA2000 1xRTT CSFB frequency priority\nThis parameter prioritizes CDMA2000 1xRTT frequencies among all frequencies related to the cell for UE in connected mode. It also sets the priority to which frequency to make CS Fallback to (0 means the lowest priority). This parameter is only valid for emergency CS Fallback calls.\nWhen value is configured to -1000, the parameter is ignored.";
      type erienmnrmlrat:ddt-Lrat_BandClassPrioCdma1xRtt_csFallbackPrioEC;
      default -1000;
    }
  } // end 'grouping struct-BandClassPrioCdma1xRtt'
  grouping struct-WhiteListPlmnIdentity {
    leaf mnc {
      description "The MNC part of a PLMN identity used in the radio network.";
      type erienmnrmlrat:ddt-Lrat_WhiteListPlmnIdentity_mnc;
      default 1;
    }
    leaf mncLength {
      description "The length of the MNC part of a PLMN identity used in the radio network.";
      type erienmnrmlrat:ddt-Lrat_WhiteListPlmnIdentity_mncLength;
      default 2;
    }
    leaf mcc {
      description "The MCC part of a PLMN identity used in the radio network.";
      type erienmnrmlrat:ddt-Lrat_WhiteListPlmnIdentity_mcc;
      default 1;
    }
  } // end 'grouping struct-WhiteListPlmnIdentity'
  grouping struct-NotificationConfig {
    leaf notificationSFIndex {
      status deprecated {
        yexte:status-information "Since L16B. Planned to be removed.";
      }
      description "The notification SF index\nNote: Specifies the subframe used to transmit MCCH change notifications on PDCCH.\nFDD: Value 1, 2, 3, 4, 5 and 6 correspond with subframe #1, #2, #3 #6, #7, and #8 respectively.\nTDD: Value 1, 2, 3, 4, and 5 correspond with subframe #3, #4, #7, #8, and #9  respectively.";
      type erienmnrmlrat:ddt-Lrat_NotificationConfig_notificationSFIndex;
      default 1;
    }
    leaf notificationOffset {
      status deprecated {
        yexte:status-information "Since L16B. Planned to be removed.";
      }
      description "The notification offset\nNote:Specifies, together with the notificationRepetitionCoeff, the radio frames in which the MCCH information change notification is scheduled i.e. the MCCH information change notification is scheduled in radio frames for which: SFN mod notification repetition period = notificationOffset";
      type erienmnrmlrat:ddt-Lrat_NotificationConfig_notificationOffset;
      default 0;
    }
    leaf notificationRepetitionCoeff {
      status deprecated {
        yexte:status-information "Since L16B. Planned to be removed.";
      }
      description "The notification repetition coefficient\nNote: Actual change notification repetition period common for all MCCHs that are configured= shortest modification period/ notificationRepetitionCoeff. The 'shortest modificaton period' corresponds with the lowest value of mcch-ModificationPeriod of all MCCHs that are configured. Value n2 corresponds to coefficient 2, and so on.";
      type erienmnrmlrat:ddt-Lrat_NotificationConfig_notificationRepetitionCoeff;
      default 2;
    }
    leaf notificationConfigurationPriority {
      status deprecated {
        yexte:status-information "Since L16B. Planned to be removed.";
      }
      description "The absolute notification configuration priority\nValue 0 means lowest priority.";
      type erienmnrmlrat:ddt-Lrat_NotificationConfig_notificationConfigurationPriority;
      default 0;
    }
  } // end 'grouping struct-NotificationConfig'
  grouping struct-FrameStartOffset {
    leaf subFrameOffset {
      description "Frame synch offset measured in subframes.\n";
      type erienmnrmlrat:ddt-Lrat_FrameStartOffset_subFrameOffset;
      default 0;
    }
  } // end 'grouping struct-FrameStartOffset'
  grouping struct-Tmgi {
    leaf mnc {
      description "The MNC part of a PLMN identity used in the radio network.";
      type erienmnrmlrat:ddt-Lrat_Tmgi_mnc;
      mandatory true;
    }
    leaf mncLength {
      description "The length of the MNC part of a PLMN identity used in the radio network.";
      type erienmnrmlrat:ddt-Lrat_Tmgi_mncLength;
      mandatory true;
    }
    leaf mcc {
      description "The MCC part of a PLMN identity used in the radio network.";
      type erienmnrmlrat:ddt-Lrat_Tmgi_mcc;
      mandatory true;
    }
    leaf serviceId {
      description "Uniquely identifies the identity of an MBMS service within a PLMN. The field contains octet 3- 5 of the IE Temporary Mobile Group Identity (TMGI) as defined in TS 24.008 [49]. The first octet of the serviceId is set to 0. The second octet contains the third octet of the TMGI, the third octet contains the fourth octet of the TMGI and so on. ";
      type erienmnrmlrat:ddt-Lrat_Tmgi_serviceId;
      mandatory true;
    }
  } // end 'grouping struct-Tmgi'
  grouping struct-SubFrameConfig {
    leaf subframeAllocation {
      description "Defines the subframes that are allocated for MBSFN within the radio frame allocation period defined by the radioFrameAllocationPeriod and the radioFrameAllocationOffset. Two options are possible, i.e. if set to 1 the subframe allocation is set by the subframeAllocationOneFrame attribute, and if set to 4 the subframe allocation is set by the subframeAllocationFourFrame attribute.";
      type erienmnrmlrat:ddt-Lrat_SubFrameConfig_subframeAllocation;
      default 1;
    }
    leaf subframeAllocationFourFrame {
      status deprecated {
        yexte:status-information "Since 17.Q2. Replaced by sfAllocationFourFrame. Planned to be removed.";
      }
      description "A bit-map indicating MBSFN subframe allocation in four consecutive radio frames, \"1\" denotes that the corresponding subframe is allocated for MBSFN. \"0\" denotes that the corresponding subframe is not allocated for MBSFN. The bitmap is interpreted as follows:\nFDD: Starting from the first radioframe and from the first/leftmost bit in the bitmap, the allocation applies to subframes #1, #2, #3 , #6, #7, and #8 in the sequence of the four radio-frames.\nTDD: Starting from the first radioframe and from the first/leftmost bit in the bitmap, the allocation applies to subframes #3, #4, #7, #8, and #9 in the sequence of the four radio-frames. The last four bits are not used. Uplink subframes are not allocated.";
      type string;
      default 000000000000000000000000;
    }
    leaf radioframeAllocationOffset {
      description "Radio-frames that contain MBSFN subframes occur when equation SFN mod radioFrameAllocationPeriod = radioFrameAllocationOffset is satisfied.";
      yexte:dependencies "It is required that radioframeAllocationOffset < radioframeAllocationPeriod.";
      type erienmnrmlrat:ddt-Lrat_SubFrameConfig_radioframeAllocationOffset;
      default 0;
    }
    leaf subframeAllocationOneFrame {
      status deprecated {
        yexte:status-information "Since 17.Q2. Replaced by sfAllocationOneFrame. Planned to be removed.";
      }
      description "A bit-map indicating MBSFN subframe allocation in one radio frame.\n\"1\" denotes that the corresponding subframe is allocated for MBSFN. \"0\" denotes that the corresponding subframe is not allocated for MBSFN.The following mapping applies:\nFDD: The first/leftmost bit defines the MBSFN allocation for subframe #1, the second bit for #2, third bit for #3 , fourth bit for #6, fifth bit for #7, sixth bit for #8.\nTDD: The first/leftmost bit defines the allocation for subframe #3, the second bit for #4, third bit for #7, fourth bit for #8, fifth bit for #9. Uplink subframes are not allocated. The last bit is not used.";
      type string;
      default 000000;
    }
    leaf sfAllocationOneFrame {
      description "Bitmap for MBSFN subframe allocation in one radio frame.\nIf \"1\", corresponding subframe is allocated for MBSFN.\nIf \"0\", corresponding subframe is not allocated for MBSFN.\nBitmap pattern is:\nFDD: First bit (most left) defines MBSFN allocation for subframe #1.\nSecond bit for #2, third bit for #3, fourth bit for #6, fifth bit for #7, sixth bit for #8.\nTDD: First bit (most left) defines allocation for subframe #3, second bit for #4, third bit for #7, fourth bit for #8, fifth bit for #9. UL subframes are not allocated. Last bit is not used.";
      type erienmnrmlrat:ddt-Lrat_SubFrameConfig_sfAllocationOneFrame;
      default 0;
    }
    leaf radioframeAllocationPeriod {
      description "Radio-frames that contain MBSFN subframes occur when equation SFN mod radioFrameAllocationPeriod = radioFrameAllocationOffset is satisfied. When fourFrames is used for subframeAllocation, the equation defines the first radio frame referred to in the description below. Values 1 and 2 are not applicable when fourFrames is used for subframeAllocation.";
      yexte:dependencies "Values 1 and 2 are not applicable when 4 is used for subframeAllocation. It is required that radioframeAllocationOffset < radioframeAllocationPeriod.";
      type erienmnrmlrat:ddt-Lrat_SubFrameConfig_radioframeAllocationPeriod;
      default 1;
    }
    leaf sfAllocationFourFrame {
      description "Bitmap for MBSFN subframe allocation in four consecutive radio frames.\nIf \"1\", corresponding subframe is allocated for MBSFN.\nIf \"0\", corresponding subframe is not allocated for MBSFN.\nBitmap pattern is:\nFDD: First radio frame and first bit (most left) in bitmap, allocation applies to subframes #1, #2, #3, #6, #7, and #8 in sequence of four radio frames.\nTDD: First radio frame and first bit (most left) in bitmap, allocation applies to subframes #3, #4, #7, #8, and #9 in sequence of four radio frames. Last four bits are not used. UL subframes are not allocated.";
      type erienmnrmlrat:ddt-Lrat_SubFrameConfig_sfAllocationFourFrame;
      default 0;
    }
  } // end 'grouping struct-SubFrameConfig'
  grouping struct-MultipleNSPmaxReqMapping {
    leaf additionalFreqBand {
      description "A list of additional frequency bands the cell belongs to, not including the frequency band indicated by the EARFCN value of the cell.";
      type erienmnrmlrat:ddt-Lrat_MultipleNSPmaxReqMapping_additionalFreqBand;
      default 1;
    }
    leaf additionalPMax {
      description "The attribute is broadcast in SIB1 multiple Nspmax list for additional band. Value 1000 means the parameter is not included in system information.";
      type erienmnrmlrat:ddt-Lrat_MultipleNSPmaxReqMapping_additionalPMax;
      default 1000;
    }
    leaf additionalNSvalue {
      description "An additional spectrum emission requirement, as specified in 3GPP TS 36.101, table 6.2.4-1.";
      type erienmnrmlrat:enum-NetworkSignallingValue;
      default NS_01;
    }
  } // end 'grouping struct-MultipleNSPmaxReqMapping'
  grouping struct-NbIotFrequencyInfo {
    leaf pMax {
      description "Calculates the parameter Pcompensation (defined in 3GPP TS 36.304), at cell reselection to a NbIot Cell.\nValue 1000 means the parameter is not sent in the system information block.";
      type erienmnrmlrat:ddt-Lrat_NbIotFrequencyInfo_pMax;
      default 1000;
    }
    leaf freqOffset {
      description "Offset of the NB-IoT channel number to EARFCN. Value V_10 means -10, V_9 means -9, and so on.";
      type erienmnrmlrat:enum-NbIotFrequencyOffset;
      default V0;
    }
    leaf carrierFreq {
      description "The ARFCN of the downlink carrier frequency (intra and inter frequency neighbors).";
      type erienmnrmlrat:ddt-Lrat_NbIotFrequencyInfo_carrierFreq;
      default 0;
    }
    leaf tReselectionNb {
      description "The cell reselection timer.";
      type erienmnrmlrat:ddt-Lrat_NbIotFrequencyInfo_tReselectionNb;
      default 6;
    }
    leaf tReselection {
      status deprecated {
        yexte:status-information "Since 17.Q2. Planned to be removed";
      }
      description "The cell reselection timer.";
      type erienmnrmlrat:ddt-Lrat_NbIotFrequencyInfo_tReselection;
      default 2;
    }
    leaf-list freqBandList {
      min-elements 0;
      max-elements 8;
      description "Frequency bands containing the frequency.";
      type erienmnrmlrat:ddt-Lrat_NbIotFrequencyInfo_freqBandList;
    }
    leaf qRxLevMin {
      description "The required minimum received Reference Symbol Received Power\n(RSRP) level in the frequency for cell reselection. Corresponds to parameter Qrxlevmin in 3GPP TS 36.304. This attribute is broadcast in NB-SIB5.";
      type erienmnrmlrat:ddt-Lrat_NbIotFrequencyInfo_qRxLevMin;
      default -140;
    }
    leaf qQualMin {
      description "Parameter \"Qqualmin\" in TS 36.304. Value 0 means that it is not sent and UE applies in such case the (default) value of negative infinity for Qqualmin. Broadcast in NB-SIB5.";
      type erienmnrmlrat:ddt-Lrat_NbIotFrequencyInfo_qQualMin;
      default 0;
    }
    leaf qOffsetFreq {
      description "Frequency specific offset for frequencies used in connected mode. In idle mode, the negative value of this offset is used.";
      type erienmnrmlrat:ddt-Lrat_NbIotFrequencyInfo_qOffsetFreq;
      default 0;
    }
  } // end 'grouping struct-NbIotFrequencyInfo'
  grouping struct-SIB3 {
    leaf threshServingLowQ {
      description "Parameter \"ThreshServing, LowQ\" in TS 36.304.\nValue 1000 means the parameter is not included in system information.";
      type erienmnrmlrat:ddt-Lrat_SIB3_threshServingLowQ;
      default 1000;
    }
    leaf sIntraSearch {
      description "Specifies the threshold when intra-frequency measurements are required.\nCorresponds to SIntraSearchP in TS 36.304\nValue 1000 means that the parameter is not present in System Information Block 3 and the UE applies the default value of infinity for SIntraSearchP.";
      type erienmnrmlrat:ddt-Lrat_SIB3_sIntraSearch;
      default 1000;
    }
    leaf sNonIntraSearchP {
      description "Parameter \"SnonIntraSearchP\" in TS 36.304. See descriptions under s-NonIntraSearch.";
      yexte:dependencies "Including in system information depends on parameter sNonIntraSearchv920Active.";
      type erienmnrmlrat:ddt-Lrat_SIB3_sNonIntraSearchP;
      default 0;
    }
    leaf sNonIntraSearchQ {
      description "s-NonIntraSearchQ-r9\nParameter \"SnonIntraSearchQ\" in TS 36.304. If the field is not present, the UE applies the (default) value of 0 dB for SnonIntraSearch.";
      yexte:dependencies "Including in system information depends on parameter sNonIntraSearchv920Active.";
      type erienmnrmlrat:ddt-Lrat_SIB3_sNonIntraSearchQ;
      default 0;
    }
    leaf tHystNormal {
      description "The additional duration for evaluating criteria to enter Normal-mobility state.\nCorresponds to TCRmaxHyst in TS 36.304.";
      type erienmnrmlrat:ddt-Lrat_SIB3_tHystNormal;
      default 240;
    }
    leaf sNonIntraSearchv920Active {
      description "Enables sending of sNonIntraSearch v920 parameters in SIB3";
      type boolean;
      default false;
    }
    leaf tEvaluation {
      description "The duration for evaluating criteria to enter mobility states.\nCorresponds to TCRmax in TS 36.304.";
      type erienmnrmlrat:ddt-Lrat_SIB3_tEvaluation;
      default 240;
    }
    leaf nCellChangeHigh {
      description "The number of cell reselections during tEvaluation to enter High-mobility state.\nCorresponds to NCR_H in TS 36.304.";
      type erienmnrmlrat:ddt-Lrat_SIB3_nCellChangeHigh;
      default 16;
    }
    leaf qHystSfMedium {
      description "\nThe additional hysteresis to be added, in Medium-mobility state, to qHyst.\nCorresponds to 'Speed dependent ScalingFactor for Qhyst' in TS 36.304.";
      type erienmnrmlrat:ddt-Lrat_SIB3_qHystSfMedium;
      default 0;
    }
    leaf nCellChangeMedium {
      description "The number of cell reselections during tEvaluation to enter Medium-mobility state.\nCorresponds to NCR_M in TS 36.304.";
      type erienmnrmlrat:ddt-Lrat_SIB3_nCellChangeMedium;
      default 16;
    }
    leaf qHystSfHigh {
      description "The additional hysteresis to be added, in High-mobility state, to qHyst.\nCorresponds to 'Speed dependent ScalingFactor for Qhyst' in TS 36.304.";
      type erienmnrmlrat:ddt-Lrat_SIB3_qHystSfHigh;
      default 0;
    }
    leaf sIntraSearchv920Active {
      description "Enables sending of sIntraSearch v920 parameters in SIB3";
      type boolean;
      default false;
    }
    leaf sIntraSearchQ {
      description "Parameter \"SIntraSearchQ\" in TS 36.304. If the field is not present, the UE applies the (default) value of 0 dB for SIntraSearchQ.";
      yexte:dependencies "Including in system information depends on parameter sIntraSearchv920Active.";
      type erienmnrmlrat:ddt-Lrat_SIB3_sIntraSearchQ;
      default 0;
    }
    leaf qHyst {
      description "Cell reselection parameter that defines the hysteresis value for ranking criteria.\nCorresponds to Qhyst in TS 36.304.";
      type erienmnrmlrat:ddt-Lrat_SIB3_qHyst;
      default 4;
    }
    leaf sIntraSearchP {
      description "Parameter \"SIntraSearchP\" in TS 36.304. See descriptions under s-IntraSearch.";
      yexte:dependencies "Including in system information depends on parameter sIntraSearchv920Active.";
      type erienmnrmlrat:ddt-Lrat_SIB3_sIntraSearchP;
      default 62;
    }
    leaf sNonIntraSearch {
      description "Specifies the threshold when inter-frequency and inter RAT measurements are required.\nCorresponds to SNonIntraSearchP in TS 36.304\nValue 1000 means that the parameter is not present in System Information Block 3 and the UE applies the default value of infinity for SNonIntraSearchP.";
      type erienmnrmlrat:ddt-Lrat_SIB3_sNonIntraSearch;
      default 0;
    }
  } // end 'grouping struct-SIB3'
  grouping struct-CellIdentityUtra {
    leaf rncId {
      description "RNC identity used in the radio network. The RNC identity is a part of the RNTI.";
      type erienmnrmlrat:ddt-Lrat_CellIdentityUtra_rncId;
      mandatory true;
    }
    leaf cId {
      description "Cell Identity. Unique in the RNC.\ncId is the identifier of a cell in one RNC, and is used together with the rncId in the RNC as cell id at system information broadcast.";
      type erienmnrmlrat:ddt-Lrat_CellIdentityUtra_cId;
      mandatory true;
    }
  } // end 'grouping struct-CellIdentityUtra'
  grouping struct-MobilityStatusIratRO {
    leaf-list reason {
      min-elements 0;
      max-elements 5;
      description "Reason why HO is not allowed.";
      yexte:dependencies "If MobilityStatusIrat.available is false, MobilityStatusIrat.reason has one or more values. If MobilityStatusIrat.available is true, MobilityStatusIrat.reason has no value.";
      type erienmnrmlrat:enum-ReasonIrat;
    }
    leaf available {
      description "If true, HO is allowed. If false, HO is not allowed. Attribute changes based on node decision.";
      yexte:dependencies "If MobilityStatusIrat.available is false, MobilityStatusIrat.reason has one or more values. If MobilityStatusIrat.available is true, MobilityStatusIrat.reason has no value.";
      type boolean;
      mandatory true;
    }
  } // end 'grouping struct-MobilityStatusIratRO'
  grouping struct-UtranFreqToQciProfileRelation {
    leaf b2Thr1RsrpUtraFreqQciOffset {
      description "The frequency-relation dependent and QCI specific offset for the absolute threshold b2Threshold1Rsrp, used for Multi-Layer Service-Triggered Mobility.";
      type erienmnrmlrat:ddt-Lrat_UtranFreqToQciProfileRelation_b2Thr1RsrpUtraFreqQciOffset;
      default 0;
    }
    leaf lbQciProfileHandling {
      description "QCI profile handling with regard to load management";
      type erienmnrmlrat:enum-LbQciProfileHandling;
      default ALLOWED;
    }
    leaf b2Thr1RsrqUtraFreqQciOffset {
      description "The frequency-relation dependent and QCI specific offset for the absolute threshold b2Threshold1Rsrq, used for Multi-Layer Service-Triggered Mobility.";
      type erienmnrmlrat:ddt-Lrat_UtranFreqToQciProfileRelation_b2Thr1RsrqUtraFreqQciOffset;
      default 0;
    }
    leaf lbUtranB1ThresholdEcNoOffset {
      description "QCI specific offset to the threshold b1ThresholdEcNo used for load management.\nNot applicable for UTRA TDD.";
      type erienmnrmlrat:ddt-Lrat_UtranFreqToQciProfileRelation_lbUtranB1ThresholdEcNoOffset;
      default 0;
    }
    leaf atoThresh2QciProfileHandling {
      description "QCI profile handling with regard to Admission-Triggered Offload (ATO), when ATO level2 threshold is exceeded";
      type erienmnrmlrat:enum-AtoQciProfileHandling;
      default ALLOWED;
    }
    leaf atoThresh1QciProfileHandling {
      description "QCI profile handling with regard to Admission-Triggered Offload (ATO), when ATO Level1 threshold is exceeded.";
      type erienmnrmlrat:enum-AtoQciProfileHandling;
      default ALLOWED;
    }
    leaf lbUtranB1ThresholdRscpOffset {
      description "QCI specific offset to the threshold b1ThresholdRscp used for load management";
      type erienmnrmlrat:ddt-Lrat_UtranFreqToQciProfileRelation_lbUtranB1ThresholdRscpOffset;
      default 0;
    }
    leaf b2Thr2RscpUtraFreqQciOffset {
      description "The frequency-relation dependent and QCI specific offset for the absolute threshold b2Threshold2RscpUtra, used for Multi-Layer Service-Triggered Mobility.";
      type erienmnrmlrat:ddt-Lrat_UtranFreqToQciProfileRelation_b2Thr2RscpUtraFreqQciOffset;
      default 0;
    }
    leaf qciProfileRef {
      description "QCI profile MO: QciProfilePredefined or QciProfileOperatorDefined";
      erienmyext:enm-type MOREF;
      type string;
    }
    leaf b2Thr2EcNoUtraFreqQciOffset {
      description "The frequency-relation dependent and QCI specific offset for the absolute threshold b2Threshold2EcNoUtra, used for Multi-Layer Service-Triggered Mobility.\nNot applicable for UTRA TDD.";
      type erienmnrmlrat:ddt-Lrat_UtranFreqToQciProfileRelation_b2Thr2EcNoUtraFreqQciOffset;
      default 0;
    }
  } // end 'grouping struct-UtranFreqToQciProfileRelation'
  grouping struct-BlackListEntry {
    leaf physicalLayerSubCellId {
      description "The subidentity within the physical layer cell ID group. Physical-layer cell IDs are grouped into 168 unique physical-layer cell-identity groups, each group containing 3 unique subidentities.\nThis attribute together with physicalLayerCellIdGroup is used to calculate physical layer cell identity (see 3GPP TS 36.211).\nSpecial Value: -1 is not a valid value and used as default.";
      type erienmnrmlrat:ddt-Lrat_BlackListEntry_physicalLayerSubCellId;
      default -1;
    }
    leaf range {
      description "Indicates the number of physical layer cell identities in the range based on the start value derived form physicalLayerCellIdGroup and physicalLayerSubCellId.";
      type erienmnrmlrat:ddt-Lrat_BlackListEntry_range;
      default 1;
    }
    leaf physicalLayerCellIdGroup {
      description "The physical layer cell ID group. Physical-layer cell IDs are grouped into 168 unique physical-layer cell-identity groups, each group containing 3 unique subidentities.\nThis attribute together with physicalLayerSubCellId is used to calculate physical layer cell ID (see 3GPP TS 36.211).\nSpecial Value: -1 is not a valid value and used as default.";
      type erienmnrmlrat:ddt-Lrat_BlackListEntry_physicalLayerCellIdGroup;
      default -1;
    }
  } // end 'grouping struct-BlackListEntry'
  grouping struct-LoadBasedCaMsrThr {
    leaf dlPrbUtilThreshHigh {
      description "High threshold for DL PRB use.";
      yexte:dependencies "dlPrbUtilThreshHigh > dlPrbUtilThreshLow.";
      type erienmnrmlrat:ddt-Lrat_LoadBasedCaMsrThr_dlPrbUtilThreshHigh;
      default 55;
    }
    leaf ulPrbUtilThreshHigh {
      description "High threshold for UL PRB use.";
      yexte:dependencies "ulPrbUtilThreshHigh > ulPrbUtilThreshLow.";
      type erienmnrmlrat:ddt-Lrat_LoadBasedCaMsrThr_ulPrbUtilThreshHigh;
      default 55;
    }
    leaf ulSeUtilThreshLow {
      description "Low threshold for UL SE for each TTI.";
      yexte:dependencies "ulSeUtilThreshHigh > ulSeUtilThreshLow.";
      type erienmnrmlrat:ddt-Lrat_LoadBasedCaMsrThr_ulSeUtilThreshLow;
      default 40;
    }
    leaf cceUtilThreshLow {
      description "Low threshold for CCE use.";
      yexte:dependencies "cceUtilThreshHigh > cceUtilThreshLow.";
      type erienmnrmlrat:ddt-Lrat_LoadBasedCaMsrThr_cceUtilThreshLow;
      default 40;
    }
    leaf cceUtilThreshHigh {
      description "High threshold for CCE use.";
      yexte:dependencies "cceUtilThreshHigh > cceUtilThreshLow.";
      type erienmnrmlrat:ddt-Lrat_LoadBasedCaMsrThr_cceUtilThreshHigh;
      default 55;
    }
    leaf dlSeUtilThreshLow {
      description "Low threshold for DL SE for each TTI.";
      yexte:dependencies "dlSeUtilThreshHigh > dlSeUtilThreshLow.";
      type erienmnrmlrat:ddt-Lrat_LoadBasedCaMsrThr_dlSeUtilThreshLow;
      default 40;
    }
    leaf ulPrbUtilThreshLow {
      description "Low threshold for UL PRB use.";
      yexte:dependencies "ulPrbUtilThreshHigh > ulPrbUtilThreshLow.";
      type erienmnrmlrat:ddt-Lrat_LoadBasedCaMsrThr_ulPrbUtilThreshLow;
      default 40;
    }
    leaf dlPrbUtilThreshLow {
      description "Low threshold for DL PRB use.";
      yexte:dependencies "dlPrbUtilThreshHigh > dlPrbUtilThreshLow.";
      type erienmnrmlrat:ddt-Lrat_LoadBasedCaMsrThr_dlPrbUtilThreshLow;
      default 40;
    }
    leaf dlSeUtilThreshHigh {
      description "High threshold for DL SE for each TTI.";
      yexte:dependencies "dlSeUtilThreshHigh > dlSeUtilThreshLow.";
      type erienmnrmlrat:ddt-Lrat_LoadBasedCaMsrThr_dlSeUtilThreshHigh;
      default 55;
    }
    leaf ulSeUtilThreshHigh {
      description "High threshold for UL SE for each TTI.";
      yexte:dependencies "ulSeUtilThreshHigh > ulSeUtilThreshLow.";
      type erienmnrmlrat:ddt-Lrat_LoadBasedCaMsrThr_ulSeUtilThreshHigh;
      default 55;
    }
  } // end 'grouping struct-LoadBasedCaMsrThr'
  grouping struct-MultipleNSPmaxListRO {
    leaf multipleNSvalue {
      description "An additional spectrum emission requirement, as specified in 3GPP TS 36.101, table 6.2.4-1.";
      type erienmnrmlrat:enum-NetworkSignallingValue;
      mandatory true;
    }
    leaf multiplePmax {
      description "The attribute is broadcast in SIB1 multiple Nspmax list for additional band. Value 1000 means the parameter is not included in system information.";
      type erienmnrmlrat:ddt-Lrat_MultipleNSPmaxListRO_multiplePmax;
      mandatory true;
    }
  } // end 'grouping struct-MultipleNSPmaxListRO'
  grouping struct-Cdma1xRttCellId {
    leaf sectorNumber {
      description "Sector number.\nNormal range is 0 to 15.\nIf Ericsson Extended Cell Range is used [0..8191], the sectorNumber value of CellID's > 4095 will follow the following conversion:\nsectorNumber = 8 + <sectorNumber>";
      type erienmnrmlrat:ddt-Lrat_Cdma1xRttCellId_sectorNumber;
      mandatory true;
    }
    leaf cellId {
      description "Cell identity.\nNormal range is 0 to 4095.\nIf Ericsson Extended Cell Range is used [0..8191], for CellID values >4095 the CellID value to set shall follow the below conversion:\nNew CellID = <CellID> - 4096";
      type erienmnrmlrat:ddt-Lrat_Cdma1xRttCellId_cellId;
      mandatory true;
    }
  } // end 'grouping struct-Cdma1xRttCellId'
  grouping struct-SIB8 {
    leaf tReselectionCdma1xRtt {
      description "Cell reselection timer value applicable when evaluating cell reselection towards CDMA2000 1xRTT.\nThe value corresponds to TreselectionCDMA_1xRTT in 3GPP TS 36.304.";
      type erienmnrmlrat:ddt-Lrat_SIB8_tReselectionCdma1xRtt;
      default 2;
    }
    leaf tReselectionCdma1xRttSfMedium {
      description "Scaling factor for TreselectionCDMA_1xRTT for medium-mobility state .\nThe value of the tReselectionCdma1xRtt parameter is multiplied with this factor if the UE is in Medium-mobility state.\nValue mapping:\n25 = 0.25\n50 = 0.5\n75 = 0.75\n100 = 1.0\nCorresponds to \"Speed dependent ScalingFactor for TreselectionCDMA_1xRTT\" in 3GPP TS 36.304\nIf both tReselectionCdma1xRttSfMedium and tReselectionCdma1xRttSfHigh are set to 100 they will not be broadcast in System Information.";
      type erienmnrmlrat:ddt-Lrat_SIB8_tReselectionCdma1xRttSfMedium;
      default 100;
    }
    leaf tReselectionCdmaHrpd {
      description "Specifies the cell reselection timer value which is applicable when evaluating cell reselection towards CDMA2000 HRPD.\nCorresponds to TreselectionCDMA_HRPD in TS 36.304.";
      type erienmnrmlrat:ddt-Lrat_SIB8_tReselectionCdmaHrpd;
      default 2;
    }
    leaf tReselectionCdmaHrpdSfMedium {
      description "Specifies scaling factor for TreselectionCDMA_HRPD for Medium-mobility state.The parameter tReselectionCdmaHrpd is multiplied with this factor if the UE is in Medium-mobility state.\nValue mapping:\n25 = 0.25\n50 = 0.5\n75 = 0.75\n100 = 1.0\nCorresponds to \"Speed dependent ScalingFactor for TreselectionCDMA_HRPD\" in TS 36.304\nIf both tReselectionCdmaHrpdSfMedium and tReselectionCdmaHrpdSfHigh is set to 100 they will not be broadcasted in System Information.";
      type erienmnrmlrat:ddt-Lrat_SIB8_tReselectionCdmaHrpdSfMedium;
      default 100;
    }
    leaf tReselectionCdmaHrpdSfHigh {
      description "Specifies scaling factor for TreselectionCDMA_HRPD for High-mobility state. The parameter tReselectionCdmaHrpd is multiplied with this factor if the UE is in High-mobility state.\nValue mapping:\n25 = 0.25\n50 = 0.5\n75 = 0.75\n100 = 1.0\nCorresponds to \"Speed dependent ScalingFactor for TreselectionCDMA_HRPD\" in TS 36.304\nIf both tReselectionHrpdSfMedium and tReselectionHrpdSfHigh is set to 100 they will not be broadcasted in System Information.";
      type erienmnrmlrat:ddt-Lrat_SIB8_tReselectionCdmaHrpdSfHigh;
      default 100;
    }
    leaf tReselectionCdma1xRttSfHigh {
      description "Scaling factor for TreselectionCDMA_1xRTT for high-mobility state.\nThis parameter specifies the scaling factor to be used with TreselectionCDMA_1xRTT for High-mobility state. The parameter tReselectionCdma1xRtt is multiplied with this factor if the UE is in High-mobility state.\nValue mapping:\n25 = 0.25\n50 = 0.5\n75 = 0.75\n100 = 1.0\nCorresponds to \"Speed dependent ScalingFactor for TreselectionCDMA_1xRTT\" in 3GPP TS 36.304\nIf both tReselection1xRttSfMedium and tReselection1xRttSfHigh parameters are set to 100 they will not be broadcast in System Information.";
      type erienmnrmlrat:ddt-Lrat_SIB8_tReselectionCdma1xRttSfHigh;
      default 100;
    }
    leaf searchWindowSizeCdma {
      description "Specifies the search window size for assisting in the search for neighboring pilots in a CDMA2000 network.";
      type erienmnrmlrat:ddt-Lrat_SIB8_searchWindowSizeCdma;
      default 8;
    }
  } // end 'grouping struct-SIB8'
  grouping struct-PmUeMeasInterRat {
    leaf geranFrequencyRef {
      description "Reference to MO GeranFrequency instance, which contains measurement object parameters to use for inter-Rat GERAN measurement.";
      erienmyext:enm-type MOREF;
      type string;
    }
    leaf utranFrequencyRef {
      description "Reference to MO UtranFrequency instance, which contains measurement object parameters to use for inter-Rat UTRAN measurement.";
      erienmyext:enm-type MOREF;
      type string;
    }
    leaf reportConfigInterRatPmRef {
      description "Reference to MO ReportConfigInterRatPm instance, which contains report configuration parameters to use for inter-Rat UTRAN or GERAN measurement.";
      erienmyext:enm-type MOREF;
      type string;
    }
  } // end 'grouping struct-PmUeMeasInterRat'
  grouping struct-SIB6 {
    leaf tReselectionUtraSfHigh {
      description "Specifies scaling factor for TreselectionUTRA for High-mobility state. The parameter tReselectionUtra is multiplied with this factor if the UE is in High-mobility state.\nValue mapping:\n25 = 0.25\n50 = 0.5\n75 = 0.75\n100 = 1.0\nCorresponds to \"Speed dependent ScalingFactor for TreselectionUTRA\" in TS 36.304\nIf both tReselectionUtraSfMedium and tReselectionUtraSfHigh is set to 100 they will not be broadcasted in System Information.\n";
      type erienmnrmlrat:ddt-Lrat_SIB6_tReselectionUtraSfHigh;
      default 100;
    }
    leaf tReselectionUtraSfMedium {
      description "Specifies scaling factor for TreselectionUTRA for Medium-mobility state.The parameter tReselectionUtra is multiplied with this factor if the UE is in Medium-mobility state.\nValue mapping:\n25 = 0.25\n50 = 0.5\n75 = 0.75\n100 = 1.0\nCorresponds to \"Speed dependent ScalingFactor for TreselectionUTRA\" in TS 36.304\nIf both tReselectionUtraSfMedium and tReselectionUtraSfHigh is set to 100 they will not be broadcasted in System Information.\n";
      type erienmnrmlrat:ddt-Lrat_SIB6_tReselectionUtraSfMedium;
      default 100;
    }
    leaf tReselectionUtra {
      description "Specifies the cell reselection timer value which is applicable when evaluating cell reselection towards UTRAN.\nCorresponds to TreselectionUTRA in TS 36.304.";
      type erienmnrmlrat:ddt-Lrat_SIB6_tReselectionUtra;
      default 2;
    }
  } // end 'grouping struct-SIB6'
  grouping struct-FrameStartOffsetTDD {
    leaf subFrameOffset {
      description "Frame synch offset measured in subframes.\n";
      type erienmnrmlrat:ddt-Lrat_FrameStartOffsetTDD_subFrameOffset;
      default 0;
    }
    leaf timeOffset {
      description "Frame synch offset measured in nano seconds.\n";
      type erienmnrmlrat:ddt-Lrat_FrameStartOffsetTDD_timeOffset;
      default 0;
    }
  } // end 'grouping struct-FrameStartOffsetTDD'
  grouping struct-SIB7 {
    leaf tReselectionGeranSfMedium {
      description "Specifies scaling factor for TreselectionGERA for Medium-mobility state.The parameter tReselectionGera is multiplied with this factor if the UE is in Medium-mobility state.\nValue mapping:\n25 = 0.25\n50 = 0.5\n75 = 0.75\n100 = 1.0\nCorresponds to \"Speed dependent ScalingFactor for TreselectionGERA\" in TS 36.304\nIf both tReselectionGeraSfMedium and tReselectionGeraSfHigh is set to 100 they will not be broadcasted in System Information.\n";
      type erienmnrmlrat:ddt-Lrat_SIB7_tReselectionGeranSfMedium;
      default 100;
    }
    leaf tReselectionGeranSfHigh {
      description "Specifies scaling factor for TreselectionGERA for High-mobility state. The parameter tReselectionGera is multiplied with this factor if the UE is in High-mobility state.\nValue mapping:\n25 = 0.25\n50 = 0.5\n75 = 0.75\n100 = 1.0\nCorresponds to \"Speed dependent ScalingFactor for TreselectionGERA\" in TS 36.304\nIf both tReselectionGeraSfMedium and tReselectionGeraSfHigh is set to 100 they will not be broadcasted in System Information.\n";
      type erienmnrmlrat:ddt-Lrat_SIB7_tReselectionGeranSfHigh;
      default 100;
    }
    leaf tReselectionGeran {
      description "Specifies the cell reselection timer value which is applicable when evaluating cell reselection towards GERAN.\nCorresponds to TreselectionGERA in TS 36.304.";
      type erienmnrmlrat:ddt-Lrat_SIB7_tReselectionGeran;
      default 2;
    }
  } // end 'grouping struct-SIB7'
  grouping struct-SIPeriodicityNB {
    leaf siPeriodicitySI1 {
      status deprecated {
        yexte:status-information "Since 17.Q2. Planned to be removed.";
      }
      description "The periodicity of SI message 1. If no SIB is mapped to the SI message, the SI message will not be transmitted.";
      type erienmnrmlrat:ddt-Lrat_SIPeriodicityNB_siPeriodicitySI1;
      default 64;
    }
    leaf siPeriodicitySI2 {
      status deprecated {
        yexte:status-information "Since 17.Q2. Planned to be removed.";
      }
      description "The periodicity of SI message 2. If no SIB is mapped to the SI message, the SI message will not be transmitted.";
      type erienmnrmlrat:ddt-Lrat_SIPeriodicityNB_siPeriodicitySI2;
      default 512;
    }
    leaf siPeriodicitySI116 {
      status deprecated {
        yexte:status-information "Since 17.Q2. Planned to be removed";
      }
      description "The periodicity of SI message 16. If no SIB is mapped to the SI message, the SI message will not be transmitted.";
      type erienmnrmlrat:ddt-Lrat_SIPeriodicityNB_siPeriodicitySI116;
      default 512;
    }
    leaf siPeriodicitySI7 {
      status deprecated {
        yexte:status-information "Since 17.Q2. Planned to be removed.";
      }
      description "The periodicity of SI message 7. If no SIB is mapped to the SI message, the SI message will not be transmitted.";
      type erienmnrmlrat:ddt-Lrat_SIPeriodicityNB_siPeriodicitySI7;
      default 512;
    }
    leaf siPeriodicitySI5 {
      status deprecated {
        yexte:status-information "Since 17.Q2. Planned to be removed.";
      }
      description "The periodicity of SI message 5. If no SIB is mapped to the SI message, the SI message will not be transmitted.";
      type erienmnrmlrat:ddt-Lrat_SIPeriodicityNB_siPeriodicitySI5;
      default 512;
    }
    leaf siPeriodicitySI14 {
      status deprecated {
        yexte:status-information "Since 17.Q2. Planned to be removed";
      }
      description "The periodicity of SI message 14. If no SIB is mapped to the SI message, the SI message will not be transmitted.";
      type erienmnrmlrat:ddt-Lrat_SIPeriodicityNB_siPeriodicitySI14;
      default 512;
    }
    leaf siPeriodicitySI6 {
      status deprecated {
        yexte:status-information "Since 17.Q2. Planned to be removed.";
      }
      description "The periodicity of SI message 6. If no SIB is mapped to the SI message, the SI message will not be transmitted.";
      type erienmnrmlrat:ddt-Lrat_SIPeriodicityNB_siPeriodicitySI6;
      default 512;
    }
    leaf siPeriodicitySI3 {
      status deprecated {
        yexte:status-information "Since 17.Q2. Planned to be removed.";
      }
      description "The periodicity of SI message 3. If no SIB is mapped to the SI message, the SI message will not be transmitted.";
      type erienmnrmlrat:ddt-Lrat_SIPeriodicityNB_siPeriodicitySI3;
      default 512;
    }
    leaf siPeriodicitySI4 {
      status deprecated {
        yexte:status-information "Since 17.Q2. Planned to be removed.";
      }
      description "The periodicity of SI message 4. If no SIB is mapped to the SI message, the SI message will not be transmitted.";
      type erienmnrmlrat:ddt-Lrat_SIPeriodicityNB_siPeriodicitySI4;
      default 512;
    }
  } // end 'grouping struct-SIPeriodicityNB'
  grouping struct-ReportConfigParamsUlQciOffset {
    leaf a1a2UlThrQciOffset {
      description "QCI-specific offset on cell level for the UL absolute threshold a1a2UlSearchThreshold for events A1 UL and A2 UL search, used for Multi-Layer Service-Triggered Mobility.";
      type erienmnrmlrat:ddt-Lrat_ReportConfigParamsUlQciOffset_a1a2UlThrQciOffset;
      default 0;
    }
    leaf qciProfileRef {
      description "Refers to the QCI profile MO, QciProfilePredefined or QciProfileOperatorDefined.";
      erienmyext:enm-type MOREF;
      type string;
    }
  } // end 'grouping struct-ReportConfigParamsUlQciOffset'
  grouping struct-MappingInfoSIBs {
    leaf mappingInfoSIB8 {
      description "Defines to which SI message SIB8 is mapped";
      yexte:dependencies "See siWindowLength for further information.";
      type erienmnrmlrat:enum-MappingInfo;
      default NOT_MAPPED;
    }
    leaf mappingInfoSIB15 {
      description "Defines to which SI message SIB15 is mapped.";
      yexte:dependencies "See siWindowLength for further information";
      type erienmnrmlrat:enum-MappingInfo;
      default NOT_MAPPED;
    }
    leaf mappingInfoSIB16 {
      description "Defines to which SI message SIB16 is mapped.";
      yexte:dependencies "See siWindowLength for further information";
      type erienmnrmlrat:enum-MappingInfo;
      default NOT_MAPPED;
    }
    leaf mappingInfoSIB13 {
      description "Defines to which SI message SIB13 is mapped.";
      yexte:dependencies "See siWindowLength for further information";
      type erienmnrmlrat:enum-MappingInfo;
      default NOT_MAPPED;
    }
    leaf mappingInfoSIB11 {
      description "Defines to which SI message SIB11 is mapped";
      yexte:dependencies "See siWindowLength for further information";
      type erienmnrmlrat:enum-MappingInfo;
      default NOT_MAPPED;
    }
    leaf mappingInfoSIB12 {
      description "Defines to which SI message SIB12 is mapped";
      yexte:dependencies "See siWindowLength for further information";
      type erienmnrmlrat:enum-MappingInfo;
      default NOT_MAPPED;
    }
    leaf mappingInfoSIB3 {
      description "Defines to which SI message SIB3 is mapped";
      yexte:dependencies "See siWindowLength for further information.";
      type erienmnrmlrat:enum-MappingInfo;
      default MAPPED_SI_1;
    }
    leaf mappingInfoSIB10 {
      description "Defines to which SI message SIB10 is mapped";
      yexte:dependencies "See siWindowLength for further information";
      type erienmnrmlrat:enum-MappingInfo;
      default MAPPED_SI_1;
    }
    leaf mappingInfoSIB6 {
      description "Defines to which SI message SIB6 is mapped";
      yexte:dependencies "See siWindowLength for further information.";
      type erienmnrmlrat:enum-MappingInfo;
      default NOT_MAPPED;
    }
    leaf mappingInfoSIB7 {
      description "Defines to which SI message SIB7 is mapped";
      yexte:dependencies "See siWindowLength for further information.";
      type erienmnrmlrat:enum-MappingInfo;
      default NOT_MAPPED;
    }
    leaf mappingInfoSIB4 {
      description "Defines to which SI message SIB4 is mapped";
      yexte:dependencies "See siWindowLength for further information.";
      type erienmnrmlrat:enum-MappingInfo;
      default NOT_MAPPED;
    }
    leaf mappingInfoSIB5 {
      description "Defines to which SI message SIB5 is mapped";
      yexte:dependencies "See siWindowLength for further information.";
      type erienmnrmlrat:enum-MappingInfo;
      default NOT_MAPPED;
    }
  } // end 'grouping struct-MappingInfoSIBs'
  grouping struct-FreqGroupPrioGERAN {
    leaf frequencyGroupId {
      description "This ID identifies the GeranFreqGroup in the network.\nWhen value is configured to -1000, the parameter is ignored.";
      type erienmnrmlrat:ddt-Lrat_FreqGroupPrioGERAN_frequencyGroupId;
      default -1000;
    }
    leaf csFallbackPrio {
      description "Prioritizes GERAN frequencies among all frequencies related to the cell for UEs in connected mode.\nThe value -1 means the frequency is excluded.\nThe value 0 means the lowest priority.\nWhen value is configured to -1000, the parameter is ignored and the value of csFallbackPrio in MO: GeranFreqGroupRelation is applied.";
      type erienmnrmlrat:ddt-Lrat_FreqGroupPrioGERAN_csFallbackPrio;
      default -1000;
    }
    leaf connectedModeMobilityPrio {
      description "Prioritizes GERAN frequencies among all frequencies related to the cell for UEs in connected mode (0 means the lowest priority. -1 means the frequency is excluded.)\nWhen value is configured to -1000, the parameter is ignored and the value of connectedModeMobilityPrio in MO: GeranFreqGroupRelation is applied.";
      type erienmnrmlrat:ddt-Lrat_FreqGroupPrioGERAN_connectedModeMobilityPrio;
      default -1000;
    }
    leaf altCsfbTargetPrioEc {
      description "Prioritizes GERAN frequencies among all frequencies related to the cell for UEs in connected mode. Sets the priority to which alternative target frequency group to make CS Fallback to. This parameter is only valid for emergency CS Fallback calls.\nValue -1 means the frequency is excluded.\nValue 0 means the lowest priority.\nWhen value is configured to -1000, the parameter is ignored and the value of altCsfbTargetPrioEC in MO: GeranFreqGroupRelation is applied.";
      type erienmnrmlrat:ddt-Lrat_FreqGroupPrioGERAN_altCsfbTargetPrioEc;
      default -1000;
    }
    leaf voicePrio {
      description "This struct prioritizes GSM/EDGE Radio Access Network (GERAN) frequencies among all frequencies related to the cell for User Equipments (UEs) in connected mode. It sets the priority for which frequency to perform mobility to for a voice session.\nThe value -1 means the frequency is excluded.\nThe value 0 means the lowest priority and the value 7 means the highest priority.\nWhen a value is configured to -1000, the parameter is ignored and the value of voicePrio in Managed Object (MO): GeranFreqGroupRelation is applied.";
      type erienmnrmlrat:ddt-Lrat_FreqGroupPrioGERAN_voicePrio;
      default -1000;
    }
    leaf cellReselectionPriority {
      description "CellReselectionPriority concerns the absolute priority of the concerned carrier frequency, as transmitted to the UE in the IE idleModeMobilityControlInfo in the RRCConnectionRelease message, and used by the cell reselection procedure. Corresponds with parameter \"priority\" in TS 36.304.\nValue 0 means: lowest priority. The UE behaviour for the case the field is absent, if applicable, is specified in TS 36.304.\nWhen value is configured to -1000, the frequency is not included in the idleModeMobilityControlInfo of the RRCConnectionRelease message.";
      type erienmnrmlrat:ddt-Lrat_FreqGroupPrioGERAN_cellReselectionPriority;
      default -1000;
    }
    leaf altCsfbTargetPrio {
      description "Prioritizes GERAN frequencies among all frequencies related to the cell for UEs in connected mode. Sets the priority to which alternative target frequency group to make CS Fallback to.\nValue -1 means the frequency is excluded.\nValue 0 means the lowest priority.\nWhen value is configured to -1000, the parameter is ignored and the value of altCsfbTargetPrio in MO: GeranFreqGroupRelation is applied.";
      type erienmnrmlrat:ddt-Lrat_FreqGroupPrioGERAN_altCsfbTargetPrio;
      default -1000;
    }
    leaf csFallbackPrioEC {
      description "Prioritizes GERAN frequencies among all frequencies related to the cell for UEs in connected mode. Sets the priority to which frequency/frequency group to make CS Fallback to. This parameter is only valid for emergency CS Fallback calls.\nThe value -1 means the frequency is excluded.\nThe value 0 means the lowest priority.\nWhen value is configured to -1000, the parameter is ignored and the value of csFallbackPrioEC in MO: GeranFreqGroupRelation is applied.";
      type erienmnrmlrat:ddt-Lrat_FreqGroupPrioGERAN_csFallbackPrioEC;
      default -1000;
    }
    leaf bandIndicatorGERAN {
      description "GERAN-BandIndicator is used as an indication of how to interpret an associated GERAN carrier ARFCN. More specifically, the attribute indicates the GERAN frequency band in case the ARFCN value can concern either a DCS 1800 or a PCS 1900 carrier frequency. For ARFCN values not associated with one of these bands, the indicator has no meaning.";
      type erienmnrmlrat:enum-BandIndicator;
      default DCS_1800;
    }
  } // end 'grouping struct-FreqGroupPrioGERAN'
  grouping struct-NbIotIntraFrequencyInfo {
    leaf pMax {
      description "Maximum output power in UL. Applicable for the intra-frequency neighbouring cells.";
      type erienmnrmlrat:ddt-Lrat_NbIotIntraFrequencyInfo_pMax;
      default 1000;
    }
    leaf tReselection {
      description "Parameter \"TreselectionNB-IoT_Intra\" in TS 36.304.";
      type erienmnrmlrat:ddt-Lrat_NbIotIntraFrequencyInfo_tReselection;
      default 6;
    }
    leaf qRxLevMin {
      description "Parameter \"Qrxlevmin\" in TS 36.304, applicable for intra-frequency neighbour cells.";
      type erienmnrmlrat:ddt-Lrat_NbIotIntraFrequencyInfo_qRxLevMin;
      default -140;
    }
    leaf qQualMin {
      description "Parameter \"Qqualmin\" in TS 36.304, applicable for intra-frequency neighbour cells.";
      type erienmnrmlrat:ddt-Lrat_NbIotIntraFrequencyInfo_qQualMin;
      default 0;
    }
  } // end 'grouping struct-NbIotIntraFrequencyInfo'
  grouping struct-GUGroupIdRO {
    leaf mnc {
      description "Mobile Network Code (a part of the PLMN identity) for a cell that is served by a neighboring eNB.";
      type erienmnrmlrat:ddt-Lrat_GUGroupIdRO_mnc;
      mandatory true;
    }
    leaf mmeGI {
      description "The MME Group ID (a part of a MME Id) for a cell that is served by a neighboring eNB.";
      type erienmnrmlrat:ddt-Lrat_GUGroupIdRO_mmeGI;
      mandatory true;
    }
    leaf mncLength {
      description "This parameter defines the number of digits for the Mobile Network Code (a part of the PLMN identity) for a cell that is served by a neighboring eNB.\nThe PLMN identity combines the following two parts:\n1. MobileCountryCode, MCC, 3 digits\n2. MobileNetworkCode, MNC, 2 or 3 digits\nExample: If MCC=125 and MNC=46, then plmnId=12546.";
      type erienmnrmlrat:ddt-Lrat_GUGroupIdRO_mncLength;
      mandatory true;
    }
    leaf mcc {
      description "Mobile Country Code (a part of the PLMN identity) for a cell that is served by a neighboring eNB.";
      type erienmnrmlrat:ddt-Lrat_GUGroupIdRO_mcc;
      mandatory true;
    }
  } // end 'grouping struct-GUGroupIdRO'
  grouping struct-UlCalibrationDataRO {
    leaf ulCalibrationStatus {
      description "Describes the current uplink antenna calibration status.";
      yexte:dependencies "If sequence ulCalibrationSupportedMethods is empty then the value of ulCalibrationStatus will be 0 (INACTIVE).";
      type erienmnrmlrat:enum-UlCalibrationStatus;
      mandatory true;
    }
    leaf-list ulCalibrationSupportedMethods {
      min-elements 0;
      max-elements 2;
      description "Describes which types of uplink antenna calibration are supported. An empty list means there is no support.";
      type erienmnrmlrat:enum-UlCalibrationMethod;
    }
    leaf ulCalibrationActiveMethod {
      description "Describes which uplink antenna calibration method is active (if any).";
      yexte:dependencies "If sequence ulCalibrationSupportedMethods is empty then the value of ulCalibrationActiveMethod will be 0 (NONE).";
      type erienmnrmlrat:enum-UlCalibrationMethod;
      mandatory true;
    }
  } // end 'grouping struct-UlCalibrationDataRO'
  grouping struct-EutranCellCorner {
    leaf cornerLongitude {
      description "The longitude of a cell polygon corner expressed in 10^(-6) degrees. Positive values are used for the eastern hemisphere while negative values are used for the western hemisphere.";
      type erienmnrmlrat:ddt-Lrat_EutranCellCorner_cornerLongitude;
      default 0;
    }
    leaf cornerLatitude {
      description "The latitude of a cell polygon corner expressed in 10^(-6) degrees. Positive values are used for the northen hemisphereare while negative values are used for the southern hemisphere.";
      type erienmnrmlrat:ddt-Lrat_EutranCellCorner_cornerLatitude;
      default 0;
    }
  } // end 'grouping struct-EutranCellCorner'
  grouping struct-TraceStreamStructRO {
    leaf fileStatus {
      description "Status of ROP file writing.\n";
      type erienmnrmlrat:enum-TracePmFileStatusEnum;
      mandatory true;
    }
    leaf traceReference {
      description "Customer used reference to the trace of Cell Trace or UE Trace.";
      type int64;
      mandatory true;
    }
    leaf scannerId {
      description "Id for the allocation of the trace (example Cell Scanner Id).\n";
      type int32;
      mandatory true;
    }
    leaf ipAddress {
      description "IPv4 or IPv6 address to the event stream receiver.";
      type erienmnrmlrat:ddt-Lrat_TraceStreamStructRO_ipAddress;
      mandatory true;
    }
    leaf streamStatus {
      description "Status of event stream\n";
      type erienmnrmlrat:enum-TracePmStreamStatusEnum;
      mandatory true;
    }
    leaf portNumber {
      description "Port number on the event stream receiver.\n";
      type erienmnrmlrat:ddt-Lrat_TraceStreamStructRO_portNumber;
      mandatory true;
    }
  } // end 'grouping struct-TraceStreamStructRO'
  grouping struct-OcngPrbSerie {
    leaf prbFirst {
      description "First PRB in the serie\nResolution: 1\nTakes effect: Feature start";
      type erienmnrmlrat:ddt-Lrat_OcngPrbSerie_prbFirst;
      default 0;
    }
    leaf pdschModType {
      description "The supported data modulation scheme for PDSCH\nTakes effect: Feature start";
      type erienmnrmlrat:enum-DataModSchemes;
      default QPSK_MOD_SCH;
    }
    leaf prbLast {
      description "Last PRB in the serie\nResolution: 1\nTakes effect: Feature start";
      type erienmnrmlrat:ddt-Lrat_OcngPrbSerie_prbLast;
      default 0;
    }
    leaf-list usedSubFrameNo {
      min-elements 0;
      max-elements 10;
      description "Indicates which subframes follow the OCNG pattern. For instance if indexes 3, 4 and 5 are set to TRUE in the array it means that subframe numbers 3, 4  and 5 use the OCNG pattern.\nTakes effect: Feature start";
      type boolean;
      default true;
      default true;
      default true;
      default true;
      default true;
      default true;
      default true;
      default true;
      default true;
      default true;
    }
  } // end 'grouping struct-OcngPrbSerie'
  grouping struct-PmUeMeasInterFreq {
    leaf reportConfigEUtraInterFreqPmRef {
      description "Reference to MO ReportConfigEUtraInterFreqPm instance, which contains report configuration parameters to use for EUTRAN inter-frequency measurement.";
      erienmyext:enm-type MOREF;
      type string;
    }
    leaf eutranFrequencyRef {
      description "Reference to MO EUtranFrequency instance, which contains measurement object parameters to use for EUTRAN inter-frequency measurement.";
      erienmyext:enm-type MOREF;
      type string;
    }
  } // end 'grouping struct-PmUeMeasInterFreq'
  grouping struct-SIRepetitionNB {
    leaf siRepetitionSI16 {
      status deprecated {
        yexte:status-information "Since 17.Q2. Planned to be removed.";
      }
      description "The repetition interval of SI message 16.";
      type erienmnrmlrat:ddt-Lrat_SIRepetitionNB_siRepetitionSI16;
      default 4;
    }
    leaf siRepetitionSI14 {
      status deprecated {
        yexte:status-information "Since 17.Q2. Planned to be removed.";
      }
      description "The repetition interval of SI message 14.";
      type erienmnrmlrat:ddt-Lrat_SIRepetitionNB_siRepetitionSI14;
      default 4;
    }
    leaf siRepetitionSI5 {
      status deprecated {
        yexte:status-information "Since 17.Q2. Planned to be removed.";
      }
      description "The repetition interval of SI message 5.";
      type erienmnrmlrat:ddt-Lrat_SIRepetitionNB_siRepetitionSI5;
      default 4;
    }
    leaf siRepetitionSI4 {
      status deprecated {
        yexte:status-information "Since 17.Q2. Planned to be removed.";
      }
      description "The repetition interval of SI message 4.";
      type erienmnrmlrat:ddt-Lrat_SIRepetitionNB_siRepetitionSI4;
      default 4;
    }
    leaf siRepetitionSI3 {
      status deprecated {
        yexte:status-information "Since 17.Q2. Planned to be removed.";
      }
      description "The repetition interval of SI message 3.";
      type erienmnrmlrat:ddt-Lrat_SIRepetitionNB_siRepetitionSI3;
      default 4;
    }
    leaf siRepetitionSI2 {
      status deprecated {
        yexte:status-information "Since 17.Q2. Planned to be removed.";
      }
      description "The repetition interval of SI message 2.";
      type erienmnrmlrat:ddt-Lrat_SIRepetitionNB_siRepetitionSI2;
      default 4;
    }
    leaf siRepetitionSI1 {
      status deprecated {
        yexte:status-information "Since 17.Q2. Planned to be removed.";
      }
      description "The repetition interval of SI message 1.";
      type erienmnrmlrat:ddt-Lrat_SIRepetitionNB_siRepetitionSI1;
      default 4;
    }
  } // end 'grouping struct-SIRepetitionNB'
  grouping struct-AtoConfig {
    leaf-list subscriberGroupRefList {
      min-elements 0;
      max-elements 12;
      status deprecated {
        yexte:status-information "Since 18.Q4. Has no functional behavior. Planned to be removed.";
      }
      description "Order of PTM Subscriber Group offload from cell, using ATO feature.\nUEs not assigned to any group are offloaded in first group.\nIf list is empty, functionality is disabled.\nNo effect when cellType is set to NON_PRIORITY.";
      erienmyext:enm-type MOREF;
      type string;
    }
    leaf minSuccRateThreshold {
      status deprecated {
        yexte:status-information "Since 18.Q4. Has no functional behavior. Planned to be removed.";
      }
      description "If ATO candidate selection success ratio during a selection interval is below threshold, cell enlarges the set of PTM Subscriber Groups that can be offloaded by the ATO feature.\nNo effect when cellType is set to NON_PRIORITY.";
      type erienmnrmlrat:ddt-Lrat_AtoConfig_minSuccRateThreshold;
      default 50;
    }
  } // end 'grouping struct-AtoConfig'
  grouping struct-BandClassPrioCDMA2000 {
    leaf hrpdBandClass {
      description "Identifies the HRPD Frequency Band in which the HRPD Carrier can be found.";
      type erienmnrmlrat:enum-HrpdBandClass;
      default BAND_CLASS_0;
    }
    leaf connectedModeMobilityPrio {
      description "Prioritizes CDMA2000 bandclasses among all bandclasses related to the cell for UEs in connected mode (0 means the lowest priority. -1 means the frequency is excluded.)\nWhen value is configured to -1000, the parameter is ignored and the value of connectedModeMobilityPrio in MO: Cdma2000FreqRelation is applied.";
      type erienmnrmlrat:ddt-Lrat_BandClassPrioCDMA2000_connectedModeMobilityPrio;
      default -1000;
    }
    leaf cellReselectionPriority {
      description "CellReselectionPriority concerns the absolute priority of the concerned carrier frequency, as transmitted to the UE in the IE idleModeMobilityControlInfo in the RRCConnectionRelease message, and used by the cell reselection procedure. Corresponds with parameter \"priority\" in TS 36.304.\nValue 0 means: lowest priority. The UE behaviour for the case the field is absent, if applicable, is specified in TS 36.304.\nWhen value is configured to -1000, the frequency is not included in the idleModeMobilityControlInfo of the RRCConnectionRelease message. Note: The CellReselectionPriority within a hrpdBandClass must be the same.";
      type erienmnrmlrat:ddt-Lrat_BandClassPrioCDMA2000_cellReselectionPriority;
      default -1000;
    }
    leaf freqCdma {
      description "Identifies the carrier frequency within a CDMA2000 Band. When value is configured to -1000, the parameter is ignored.";
      type erienmnrmlrat:ddt-Lrat_BandClassPrioCDMA2000_freqCdma;
      default -1000;
    }
  } // end 'grouping struct-BandClassPrioCDMA2000'
  grouping struct-ResOpUseConfig {
    leaf unresMsrUsageThreshold {
      status deprecated {
        yexte:status-information "Since 18.Q4. Has no functional behavior. Planned to be removed.";
      }
      description "If usage of Monitored System Resources is below threshold and subscription ratio is below unresSRatioThreshold, PLMN IDs specified in subscriberGroupRefList are broadcast as \"unreserved\" and incoming HOs of users with SPIDs specified in subscriberGroupRefList are allowed.\nNo effect when cellType is set to NON_PRIORITY.";
      yexte:dependencies resMsrUsageThreshold>=unresMsrUsageThreshold;
      type erienmnrmlrat:ddt-Lrat_ResOpUseConfig_unresMsrUsageThreshold;
      default 40;
    }
    leaf resMsrUsageThreshold {
      status deprecated {
        yexte:status-information "Since 18.Q4. Has no functional behavior. Planned to be removed.";
      }
      description "If Monitored System Resources on a cell exceed threshold, PLMN IDs specified in subscriberGroupRefList are broadcast as \"reserved for operator use\" and incoming HOs of users with SPIDs specified in the subscriberGroupRefList are blocked.\nNo effect when cellType is set to NON_PRIORITY.";
      yexte:dependencies resMsrUsageThreshold>=unresMsrUsageThreshold;
      type erienmnrmlrat:ddt-Lrat_ResOpUseConfig_resMsrUsageThreshold;
      default 70;
    }
    leaf unresSRatioThreshold {
      status deprecated {
        yexte:status-information "Since 18.Q4. Has no functional behavior. Planned to be removed.";
      }
      description "If subscription ratio is below threshold, and usage of all Monitored System Resources is below unresMsrUsageThreshold, PLMN IDs specified in subscriberGroupRefList are broadcast as \"unreserved\" and incoming HOs of users with SPIDs specified in subscriberGroupRefList are allowed.\nNo effect when cellType is set to NON_PRIORITY.";
      yexte:dependencies resSRatioThreshold>=unresSRatioThreshold;
      type erienmnrmlrat:ddt-Lrat_ResOpUseConfig_unresSRatioThreshold;
      default 55;
    }
    leaf-list subscriberGroupRefList {
      min-elements 0;
      max-elements 12;
      status deprecated {
        yexte:status-information "Since 18.Q4. Has no functional behavior. Planned to be removed.";
      }
      description "PTM Subscriber Groups affected by Cell Reserved For Operator Use.\nIf empty, functionality is disabled.\nNo effect when cellType is set to NON_PRIORITY.";
      erienmyext:enm-type MOREF;
      type string;
    }
    leaf resSRatioThreshold {
      status deprecated {
        yexte:status-information "Since 18.Q4. Has no functional behavior. Planned to be removed.";
      }
      description "If subscription ratio on a cell exceeds threshold, PLMN IDs specified in subscriberGroupRefList are broadcast as \"reserved for operator use\" and incoming HOs of users with SPIDs specified in subscriberGroupRefList are blocked.\nNo effect when cellType is set to NON_PRIORITY.";
      yexte:dependencies resSRatioThreshold>=unresSRatioThreshold;
      type erienmnrmlrat:ddt-Lrat_ResOpUseConfig_resSRatioThreshold;
      default 70;
    }
  } // end 'grouping struct-ResOpUseConfig'
  grouping struct-ParameterChangeRequestRO {
    leaf timeOfChange {
      description "The date and time the request was changed. Format: YYYY-MM-DD HH:MM:SS";
      type erienmnrmlrat:ddt-Lrat_ParameterChangeRequestRO_timeOfChange;
      mandatory true;
    }
    leaf objectRef {
      description "Refererence to the MO instance containing the attribute to be changed.";
      type string;
      mandatory true;
    }
    leaf seqNo {
      description "The sequence number of the change request. This is unique for each change request. The number 0 is used only as initial value before the structure has been assigned valid values.";
      type int32;
      mandatory true;
    }
    leaf timeOfCreation {
      description "The date and time the request was created. Format: YYYY-MM-DD HH:MM:SS";
      type erienmnrmlrat:ddt-Lrat_ParameterChangeRequestRO_timeOfCreation;
      mandatory true;
    }
    leaf causeCode {
      description "The cause of the change request.";
      type erienmnrmlrat:enum-ParameterChangeCause;
      mandatory true;
    }
    leaf causeString {
      description "The cause as the change request in free text description. Any trade-off between different functions is described here.";
      type erienmnrmlrat:ddt-Lrat_ParameterChangeRequestRO_causeString;
      mandatory true;
    }
    leaf originalValue {
      description "The original value of the attribute, in string format.";
      type erienmnrmlrat:ddt-Lrat_ParameterChangeRequestRO_originalValue;
      mandatory true;
    }
    leaf attributeName {
      description "The name of the attribute to be changed.";
      type erienmnrmlrat:ddt-Lrat_ParameterChangeRequestRO_attributeName;
      mandatory true;
    }
    leaf requestedValue {
      description "The requested value of the attribute, in string format.";
      type erienmnrmlrat:ddt-Lrat_ParameterChangeRequestRO_requestedValue;
      mandatory true;
    }
    leaf state {
      description "The state of the request. The initial state is Pending. If the request is rejected, the state is set to Rejected. If the request is approved, the state is set to Approved. If the eNodeB cancels the request, the state is set to Cancelled.";
      type erienmnrmlrat:enum-ParameterChangeState;
      mandatory true;
    }
  } // end 'grouping struct-ParameterChangeRequestRO'
  grouping struct-A5PCOffsetMCPC {
    leaf a5Thr1RsrpPCOffset {
      description "The frequency-relation specific offset for the absolute threshold a5Threshold1Rsrp, RSRP threshold1 for event A5, used for Multi-Layer Service-Triggered Mobility and high power UE.";
      type erienmnrmlrat:ddt-Lrat_A5PCOffsetMCPC_a5Thr1RsrpPCOffset;
      default 0;
    }
    leaf powerClass {
      description "Indicate the power class. Value should be unique in the structure.";
      type erienmnrmlrat:enum-PowerClass;
      default PC_2;
    }
    leaf a5Thr2RsrqPCOffset {
      description "The frequency-relation specific offset for the absolute threshold a5Threshold2Rsrq, RSRQ threshold2 for event A5, used for Multi-Layer Service-Triggered Mobility and high power UE.";
      type erienmnrmlrat:ddt-Lrat_A5PCOffsetMCPC_a5Thr2RsrqPCOffset;
      default 0;
    }
    leaf a5Thr2RsrpPCOffset {
      description "The frequency-relation specific offset for the absolute threshold a5Threshold2Rsrp, RSRP threshold2 for event A5, used for Multi-Layer Service-Triggered Mobility and high power UE.";
      type erienmnrmlrat:ddt-Lrat_A5PCOffsetMCPC_a5Thr2RsrpPCOffset;
      default 0;
    }
    leaf a5Thr1RsrqPCOffset {
      description "The frequency-relation specific offset for the absolute threshold a5Threshold1Rsrq, RSRQ threshold1 for event A5, used for Multi-Layer Service-Triggered Mobility and high power UE.";
      type erienmnrmlrat:ddt-Lrat_A5PCOffsetMCPC_a5Thr1RsrqPCOffset;
      default 0;
    }
  } // end 'grouping struct-A5PCOffsetMCPC'
  grouping struct-Cdma2000FreqRelQciB2ThrOffsets {
    leaf b2Thr1RsrpCdma2000FreqQciOffset {
      description "The frequency-relation dependent and QCI specific offset for the absolute threshold b2Threshold1Rsrp, used for Multi-Layer Service-Triggered Mobility.";
      type erienmnrmlrat:ddt-Lrat_Cdma2000FreqRelQciB2ThrOffsets_b2Thr1RsrpCdma2000FreqQciOffset;
      default 0;
    }
    leaf b2Thr2Cdma2000FreqQciOffset {
      description "The frequency-relation dependent and QCI specific offset for the absolute threshold b2Threshold2Cdma2000, used for Multi-Layer Service-Triggered Mobility.";
      type erienmnrmlrat:ddt-Lrat_Cdma2000FreqRelQciB2ThrOffsets_b2Thr2Cdma2000FreqQciOffset;
      default 0;
    }
    leaf b2Thr1RsrqCdma2000FreqQciOffset {
      description "The frequency-relation dependent and QCI specific offset for the absolute threshold b2Threshold1Rsrq, used for Multi-Layer Service-Triggered Mobility.";
      type erienmnrmlrat:ddt-Lrat_Cdma2000FreqRelQciB2ThrOffsets_b2Thr1RsrqCdma2000FreqQciOffset;
      default 0;
    }
    leaf qciProfileRef {
      description "Refers to the QCI profile MO, QciProfilePredefined or QciProfileOperatorDefined.";
      erienmyext:enm-type MOREF;
      type string;
    }
  } // end 'grouping struct-Cdma2000FreqRelQciB2ThrOffsets'
  grouping struct-PlmnIdentityRO {
    leaf mnc {
      description "The MNC part of a PLMN identity used in the radio network.\n";
      type erienmnrmlrat:ddt-Lrat_PlmnIdentityRO_mnc;
      mandatory true;
    }
    leaf mncLength {
      description "The length of the MNC part of a PLMN identity used in the radio network.\n";
      type erienmnrmlrat:ddt-Lrat_PlmnIdentityRO_mncLength;
      mandatory true;
    }
    leaf mcc {
      description "The MCC part of a PLMN identity used in the radio network.\n";
      type erienmnrmlrat:ddt-Lrat_PlmnIdentityRO_mcc;
      mandatory true;
    }
  } // end 'grouping struct-PlmnIdentityRO'
  grouping struct-FreqPrioUTRAN {
    leaf arfcnValueUtranDl {
      description "The arfcnValueUtran is used to indicate the ARFCN applicable for a downlink UTRAN carrier frequency, as defined in TS 25.331.\nWhen value is configured to -1000, the parameter is ignored.";
      type erienmnrmlrat:ddt-Lrat_FreqPrioUTRAN_arfcnValueUtranDl;
      default -1000;
    }
    leaf atoAllowed {
      description "Indicates if the related UTRAN frequency is allowed as a target frequency for Admission-Triggered Offload feature.";
      type boolean;
      default false;
    }
    leaf csFallbackPrio {
      description "Prioritizes UTRAN frequencies among all frequencies related to the cell for UEs in connected mode.\nThe value -1 means the frequency is excluded.\nThe value 0 means the lowest priority.\nWhen value is configured to -1000, the parameter is ignored and the value of csFallbackPrio in MO: UtranFreqRelation is applied.";
      type erienmnrmlrat:ddt-Lrat_FreqPrioUTRAN_csFallbackPrio;
      default -1000;
    }
    leaf connectedModeMobilityPrio {
      description "Prioritizes UTRAN frequencies among all frequencies related to the cell for UEs in connected mode. (0 means the lowest priority. -1 means the frequency is excluded.)\nWhen value is configured to -1000, the parameter is ignored and the value of connectedModeMobilityPrio in MO: UtranFreqRelation is applied.";
      type erienmnrmlrat:ddt-Lrat_FreqPrioUTRAN_connectedModeMobilityPrio;
      default -1000;
    }
    leaf altCsfbTargetPrioEc {
      description "Prioritizes UTRAN frequencies among all frequencies related to the cell for UEs in connected mode. Sets the priority to which alternative target frequency to make CS Fallback to. This parameter is only valid for emergency CS Fallback calls.\nValue -1 means the frequency is excluded.\nValue 0 means the lowest priority.\nWhen value is configured to -1000, the parameter is ignored and the value of altCsfbTargetPrioEC in MO: UtranFreqRelation is applied.";
      type erienmnrmlrat:ddt-Lrat_FreqPrioUTRAN_altCsfbTargetPrioEc;
      default -1000;
    }
    leaf voicePrio {
      description "Prioritizes UTRAN frequencies among all frequencies related to the cell for UEs in connected mode. Sets the priority to which frequency to perform mobility to for a voice session.\nThe value -1 means the frequency is excluded.\nThe value 0 means the lowest priority.\nWhen value is configured to -1000, the parameter is ignored and the value of voicePrio in MO: UtranFreqRelation is applied.";
      type erienmnrmlrat:ddt-Lrat_FreqPrioUTRAN_voicePrio;
      default -1000;
    }
    leaf cellReselectionPriority {
      description "CellReselectionPriority concerns the absolute priority of the concerned carrier frequency, as transmitted to the UE in the IE idleModeMobilityControlInfo in the RRCConnectionRelease message, and used by the cell reselection procedure. Corresponds with parameter \"priority\" in TS 36.304.\nValue 0 means: lowest priority. The UE behaviour for the case the field is absent, if applicable, is specified in TS 36.304.\nWhen value is configured to -1000, the frequency is not included in the idleModeMobilityControlInfo of the RRCConnectionRelease message.";
      type erienmnrmlrat:ddt-Lrat_FreqPrioUTRAN_cellReselectionPriority;
      default -1000;
    }
    leaf altCsfbTargetPrio {
      description "Prioritizes UTRAN frequencies among all frequencies related to the cell for UEs in connected mode.  Sets the priority to which alternative target frequency to make CS Fallback to.\nValue -1 means the frequency is excluded.\nValue 0 means the lowest priority.\nWhen value is configured to -1000, the parameter is ignored and the value of altCsfbTargetPrio in MO: UtranFreqRelation is applied.";
      type erienmnrmlrat:ddt-Lrat_FreqPrioUTRAN_altCsfbTargetPrio;
      default -1000;
    }
    leaf csFallbackPrioEC {
      description "Prioritizes UTRAN frequencies among all frequencies related to the cell for UEs in connected mode. Sets the priority to which frequency/frequency group to make CS Fallback to. This parameter is only valid for emergency CS Fallback calls.\nThe value -1 means the frequency is excluded.\nThe value 0 means the lowest priority.\nWhen value is configured to -1000, the parameter is ignored and the value of csFallbackPrioEC in MO: UtranFreqRelation is applied.";
      type erienmnrmlrat:ddt-Lrat_FreqPrioUTRAN_csFallbackPrioEC;
      default -1000;
    }
    leaf loadBalancingAllowed {
      description "Indicates if the related UTRAN frequency is allowed as a target frequency for load-balancing and offload features.";
      type boolean;
      default true;
    }
  } // end 'grouping struct-FreqPrioUTRAN'
  grouping struct-B2GeranPCOffsetMCPC {
    leaf powerClass {
      description "Indicate the power class. Value should be unique in the structure.";
      type erienmnrmlrat:enum-PowerClass;
      default PC_2;
    }
    leaf b2Thr1RsrqGeranPCOffset {
      description "The frequency group relation specific offset for the absolute threshold b2Threshold1Rsrq, RSRQ threshold1 value for event B2, used for Multi-Layer Service-Triggered Mobility and HighPower UE.";
      type erienmnrmlrat:ddt-Lrat_B2GeranPCOffsetMCPC_b2Thr1RsrqGeranPCOffset;
      default 0;
    }
    leaf b2Thr1RsrpGeranPCOffset {
      description "The frequency group relation specific offset for the absolute threshold b2Threshold1Rsrp, RSRP threshold1 value for event B2, used for Multi-Layer Service-Triggered Mobility and HighPower UE.";
      type erienmnrmlrat:ddt-Lrat_B2GeranPCOffsetMCPC_b2Thr1RsrpGeranPCOffset;
      default 0;
    }
  } // end 'grouping struct-B2GeranPCOffsetMCPC'
  grouping struct-DlCalibrationDataRO {
    leaf-list dlCalibrationSupportedMethods {
      min-elements 0;
      max-elements 2;
      description "Describes which types of downlink antenna calibration are supported. An empty list means there is no support.";
      type erienmnrmlrat:enum-DlCalibrationMethod;
    }
    leaf dlCalibrationStatus {
      description "Describes the current downlink antenna calibration status.";
      yexte:dependencies "If sequence dlCalibrationSupportedMethods is empty then the value of dlCalibrationStatus will be 0 (INACTIVE).";
      type erienmnrmlrat:enum-DlCalibrationStatus;
      mandatory true;
    }
    leaf dlCalibrationActiveMethod {
      description "Describes which downlink antenna calibration method is active (if any).";
      yexte:dependencies "If sequence dlCalibrationSupportedMethods is empty then the value of dlCalibrationActiveMethod will be 0 (NONE).";
      type erienmnrmlrat:enum-DlCalibrationMethod;
      mandatory true;
    }
  } // end 'grouping struct-DlCalibrationDataRO'
  grouping struct-PeriodicitySI {
    leaf siPeriodicitySI1 {
      description "The periodicity of SI message. If no SIB is mapped to this SI message, the SI message will not be transmitted. Note: SIB2 is always mapped to SI message 1 according to TS 36.331.";
      yexte:dependencies "See siWindowLength for further information.";
      type erienmnrmlrat:ddt-Lrat_PeriodicitySI_siPeriodicitySI1;
      default 8;
    }
    leaf siPeriodicitySI2 {
      description "The periodicity of SI message 2. If no SIB is mapped to the SI message, the SI message will not be transmitted. ";
      yexte:dependencies "See siWindowLength for further information.";
      type erienmnrmlrat:ddt-Lrat_PeriodicitySI_siPeriodicitySI2;
      default 64;
    }
    leaf siPeriodicitySI9 {
      description "The periodicity of SI message 9. If no SIB is mapped to the SI message, the SI message will not be transmitted.";
      yexte:dependencies "See siWindowLength for further information";
      type erienmnrmlrat:ddt-Lrat_PeriodicitySI_siPeriodicitySI9;
      default 64;
    }
    leaf siPeriodicitySI10 {
      description "The periodicity of SI message 10. If no SIB is mapped to the SI message, the SI message will not be transmitted.";
      yexte:dependencies "See siWindowLength for further information";
      type erienmnrmlrat:ddt-Lrat_PeriodicitySI_siPeriodicitySI10;
      default 64;
    }
    leaf siPeriodicitySI7 {
      description "The periodicity of SI message 7. If no SIB is mapped to the SI message, the SI message will not be transmitted.";
      yexte:dependencies "See siWindowLength for further information.";
      type erienmnrmlrat:ddt-Lrat_PeriodicitySI_siPeriodicitySI7;
      default 64;
    }
    leaf siPeriodicitySI8 {
      description "The periodicity of SI message 8. If no SIB is mapped to the SI message, the SI message will not be transmitted.";
      yexte:dependencies "See siWindowLength for further information";
      type erienmnrmlrat:ddt-Lrat_PeriodicitySI_siPeriodicitySI8;
      default 64;
    }
    leaf siPeriodicitySI5 {
      description "The periodicity of SI message 5. If no SIB is mapped to the SI message, the SI message will not be transmitted.";
      yexte:dependencies "See siWindowLength for further information.";
      type erienmnrmlrat:ddt-Lrat_PeriodicitySI_siPeriodicitySI5;
      default 64;
    }
    leaf siPeriodicitySI6 {
      description "The periodicity of SI message 6. If no SIB is mapped to the SI message, the SI message will not be transmitted.";
      yexte:dependencies "See siWindowLength for further information.";
      type erienmnrmlrat:ddt-Lrat_PeriodicitySI_siPeriodicitySI6;
      default 64;
    }
    leaf siPeriodicitySI3 {
      description "The periodicity of SI message 3. If no SIB is mapped to the SI message, the SI message will not be transmitted.\n";
      yexte:dependencies "See siWindowLength for further information.";
      type erienmnrmlrat:ddt-Lrat_PeriodicitySI_siPeriodicitySI3;
      default 64;
    }
    leaf siPeriodicitySI4 {
      description "The periodicity of SI message 4. If no SIB is mapped to the SI message, the SI message will not be transmitted.";
      yexte:dependencies "See siWindowLength for further information.";
      type erienmnrmlrat:ddt-Lrat_PeriodicitySI_siPeriodicitySI4;
      default 64;
    }
  } // end 'grouping struct-PeriodicitySI'
  grouping struct-MappingInfoSIBsBr {
    leaf mappingInfoSIB15 {
      description "Defines to which SI message SIB15 is mapped";
      yexte:dependencies "See siWindowLength for further information";
      type erienmnrmlrat:enum-MappingInfo;
      default NOT_MAPPED;
    }
    leaf mappingInfoSIB8 {
      description "Defines to which SI message SIB8 is mapped";
      yexte:dependencies "See siWindowLength for further information";
      type erienmnrmlrat:enum-MappingInfo;
      default NOT_MAPPED;
    }
    leaf mappingInfoSIB16 {
      description "Defines to which SI message SIB16 is mapped";
      yexte:dependencies "See siWindowLength for further information";
      type erienmnrmlrat:enum-MappingInfo;
      default NOT_MAPPED;
    }
    leaf mappingInfoSIB13 {
      description "Defines to which SI message SIB13 is mapped";
      yexte:dependencies "See siWindowLength for further information";
      type erienmnrmlrat:enum-MappingInfo;
      default NOT_MAPPED;
    }
    leaf mappingInfoSIB11 {
      description "Defines to which SI message SIB11 is mapped";
      yexte:dependencies "See siWindowLength for further information";
      type erienmnrmlrat:enum-MappingInfo;
      default NOT_MAPPED;
    }
    leaf mappingInfoSIB12 {
      description "Defines to which SI message SIB12 is mapped";
      yexte:dependencies "See siWindowLength for further information";
      type erienmnrmlrat:enum-MappingInfo;
      default NOT_MAPPED;
    }
    leaf mappingInfoSIB10 {
      description "Defines to which SI message SIB10 is mapped";
      yexte:dependencies "See siWindowLength for further information";
      type erienmnrmlrat:enum-MappingInfo;
      default NOT_MAPPED;
    }
    leaf mappingInfoSIB3 {
      description "Defines to which SI message SIB3 is mapped";
      yexte:dependencies "See siWindowLength for further information";
      type erienmnrmlrat:enum-MappingInfo;
      default NOT_MAPPED;
    }
    leaf mappingInfoSIB6 {
      description "Defines to which SI message SIB6 is mapped";
      yexte:dependencies "See siWindowLength for further information";
      type erienmnrmlrat:enum-MappingInfo;
      default NOT_MAPPED;
    }
    leaf mappingInfoSIB7 {
      description "Defines to which SI message SIB7 is mapped";
      yexte:dependencies "See siWindowLength for further information";
      type erienmnrmlrat:enum-MappingInfo;
      default NOT_MAPPED;
    }
    leaf mappingInfoSIB4 {
      description "Defines to which SI message SIB4 is mapped";
      yexte:dependencies "See siWindowLength for further information";
      type erienmnrmlrat:enum-MappingInfo;
      default NOT_MAPPED;
    }
    leaf mappingInfoSIB5 {
      description "Defines to which SI message SIB5 is mapped";
      yexte:dependencies "See siWindowLength for further information";
      type erienmnrmlrat:enum-MappingInfo;
      default NOT_MAPPED;
    }
  } // end 'grouping struct-MappingInfoSIBsBr'
  grouping struct-SubFrameConfigRO {
    leaf subframeAllocation {
      description "Defines the subframes that are allocated for MBSFN within the radio frame allocation period defined by the radioFrameAllocationPeriod and the radioFrameAllocationOffset. Two options are possible, i.e. if set to 1 the subframe allocation is set by the subframeAllocationOneFrame attribute, and if set to 4 the subframe allocation is set by the subframeAllocationFourFrame attribute.";
      type erienmnrmlrat:ddt-Lrat_SubFrameConfigRO_subframeAllocation;
      mandatory true;
    }
    leaf subframeAllocationFourFrame {
      status deprecated {
        yexte:status-information "Since 17.Q2. Replaced by sfAllocationFourFrame. Planned to be removed.";
      }
      description "A bit-map indicating MBSFN subframe allocation in four consecutive radio frames, \"1\" denotes that the corresponding subframe is allocated for MBSFN. \"0\" denotes that the corresponding subframe is not allocated for MBSFN. The bitmap is interpreted as follows:\nFDD: Starting from the first radioframe and from the first/leftmost bit in the bitmap, the allocation applies to subframes #1, #2, #3 , #6, #7, and #8 in the sequence of the four radio-frames.\nTDD: Starting from the first radioframe and from the first/leftmost bit in the bitmap, the allocation applies to subframes #3, #4, #7, #8, and #9 in the sequence of the four radio-frames. The last four bits are not used. Uplink subframes are not allocated.";
      type string;
      mandatory true;
    }
    leaf radioframeAllocationOffset {
      description "Radio-frames that contain MBSFN subframes occur when equation SFN mod radioFrameAllocationPeriod = radioFrameAllocationOffset is satisfied.";
      yexte:dependencies "It is required that radioframeAllocationOffset < radioframeAllocationPeriod.";
      type erienmnrmlrat:ddt-Lrat_SubFrameConfigRO_radioframeAllocationOffset;
      mandatory true;
    }
    leaf subframeAllocationOneFrame {
      status deprecated {
        yexte:status-information "Since 17.Q2. Replaced by sfAllocationOneFrame. Planned to be removed.";
      }
      description "A bit-map indicating MBSFN subframe allocation in one radio frame.\n\"1\" denotes that the corresponding subframe is allocated for MBSFN. \"0\" denotes that the corresponding subframe is not allocated for MBSFN.The following mapping applies:\nFDD: The first/leftmost bit defines the MBSFN allocation for subframe #1, the second bit for #2, third bit for #3 , fourth bit for #6, fifth bit for #7, sixth bit for #8.\nTDD: The first/leftmost bit defines the allocation for subframe #3, the second bit for #4, third bit for #7, fourth bit for #8, fifth bit for #9. Uplink subframes are not allocated. The last bit is not used.";
      type string;
      mandatory true;
    }
    leaf sfAllocationOneFrame {
      description "Bitmap for MBSFN subframe allocation in one radio frame.\nIf \"1\", corresponding subframe is allocated for MBSFN.\nIf \"0\", corresponding subframe is not allocated for MBSFN.\nBitmap pattern is:\nFDD: First bit (most left) defines MBSFN allocation for subframe #1.\nSecond bit for #2, third bit for #3, fourth bit for #6, fifth bit for #7, sixth bit for #8.\nTDD: First bit (most left) defines allocation for subframe #3, second bit for #4, third bit for #7, fourth bit for #8, fifth bit for #9. UL subframes are not allocated. Last bit is not used.";
      type erienmnrmlrat:ddt-Lrat_SubFrameConfigRO_sfAllocationOneFrame;
      mandatory true;
    }
    leaf radioframeAllocationPeriod {
      description "Radio-frames that contain MBSFN subframes occur when equation SFN mod radioFrameAllocationPeriod = radioFrameAllocationOffset is satisfied. When fourFrames is used for subframeAllocation, the equation defines the first radio frame referred to in the description below. Values 1 and 2 are not applicable when fourFrames is used for subframeAllocation.";
      yexte:dependencies "Values 1 and 2 are not applicable when 4 is used for subframeAllocation. It is required that radioframeAllocationOffset < radioframeAllocationPeriod.";
      type erienmnrmlrat:ddt-Lrat_SubFrameConfigRO_radioframeAllocationPeriod;
      mandatory true;
    }
    leaf sfAllocationFourFrame {
      description "Bitmap for MBSFN subframe allocation in four consecutive radio frames.\nIf \"1\", corresponding subframe is allocated for MBSFN.\nIf \"0\", corresponding subframe is not allocated for MBSFN.\nBitmap pattern is:\nFDD: First radio frame and first bit (most left) in bitmap, allocation applies to subframes #1, #2, #3, #6, #7, and #8 in sequence of four radio frames.\nTDD: First radio frame and first bit (most left) in bitmap, allocation applies to subframes #3, #4, #7, #8, and #9 in sequence of four radio frames. Last four bits are not used. UL subframes are not allocated.";
      type erienmnrmlrat:ddt-Lrat_SubFrameConfigRO_sfAllocationFourFrame;
      mandatory true;
    }
  } // end 'grouping struct-SubFrameConfigRO'
  grouping struct-MSCid {
    leaf switchNumber {
      description "Switch Number in MSC identifier\nRefer to 3GPP2, A.S0014-C, table 4.2.17-4";
      type erienmnrmlrat:ddt-Lrat_MSCid_switchNumber;
      mandatory true;
    }
    leaf marketId {
      description "Market ID in MSC identifier\nRefer to 3GPP2, A.S0014-C, table 4.2.17-4";
      type erienmnrmlrat:ddt-Lrat_MSCid_marketId;
      mandatory true;
    }
  } // end 'grouping struct-MSCid'
  grouping struct-CandNeighborRelInfoRO {
    leaf mobilityStatusReason {
      description "Reason handover is not allowed.";
      type erienmnrmlrat:enum-Reason;
      mandatory true;
    }
    leaf physicalLayerSubCellId {
      description "The subidentity within the physical layer cell ID group (see 3GPP TS 36.211).";
      type erienmnrmlrat:ddt-Lrat_CandNeighborRelInfoRO_physicalLayerSubCellId;
      mandatory true;
    }
    leaf mnc {
      description "The MNC part of a PLMN identity used in the radio network.";
      type erienmnrmlrat:ddt-Lrat_CandNeighborRelInfoRO_mnc;
      mandatory true;
    }
    leaf enbId {
      description "The ENodeB ID that forms part of the Cell Global Identity.";
      type erienmnrmlrat:ddt-Lrat_CandNeighborRelInfoRO_enbId;
      mandatory true;
    }
    leaf tac {
      description "Tracking Area Code for EUtranCell.";
      type erienmnrmlrat:ddt-Lrat_CandNeighborRelInfoRO_tac;
      mandatory true;
    }
    leaf mncLength {
      description "The length of the MNC part of a PLMN identity used in the radio network.";
      type erienmnrmlrat:ddt-Lrat_CandNeighborRelInfoRO_mncLength;
      mandatory true;
    }
    leaf physicalLayerCellIdGroup {
      description "The physical layer cell ID group (see 3GPP TS 36.211).";
      type erienmnrmlrat:ddt-Lrat_CandNeighborRelInfoRO_physicalLayerCellIdGroup;
      mandatory true;
    }
    leaf cellId {
      description "RBS internal ID attribute for EUtranCell.";
      type erienmnrmlrat:ddt-Lrat_CandNeighborRelInfoRO_cellId;
      mandatory true;
    }
    leaf mcc {
      description "The MCC part of a PLMN identity used in the radio network.";
      type erienmnrmlrat:ddt-Lrat_CandNeighborRelInfoRO_mcc;
      mandatory true;
    }
  } // end 'grouping struct-CandNeighborRelInfoRO'
  grouping struct-MobilityStatusRO {
    leaf-list reason {
      min-elements 0;
      max-elements 5;
      description "Reason handover is not allowed.";
      type erienmnrmlrat:enum-Reason;
    }
    leaf available {
      description "TRUE means handover is allowed. FALSE means handover is not allowed. The attribute is changed  based on node decision.";
      yexte:dependencies "When available attribute is set to false, then enum reason list is created.";
      type boolean;
      mandatory true;
    }
  } // end 'grouping struct-MobilityStatusRO'
  grouping struct-PrioOffsetPerQci {
    leaf offsetPerQciPrio {
      description "QCI-depended priority of the offset. Offset with maximum priority is taken into calculation for absolute offset/threshold for mobility purpose.\nValue -1 means offset is excluded from selection.\nValue 0 means lowest priority.\nValue 7 means highest priority.";
      type erienmnrmlrat:ddt-Lrat_PrioOffsetPerQci_offsetPerQciPrio;
      default 0;
    }
    leaf qciProfileRef {
      description "Refers to the QCI profile MO, QciProfilePredefined or QciProfileOperatorDefined.";
      erienmyext:enm-type MOREF;
      type string;
    }
  } // end 'grouping struct-PrioOffsetPerQci'
  grouping struct-GeranFreqRelQciB2ThrOffsets {
    leaf b2Thr1RsrqGeranFreqQciOffset {
      description "The frequency group relation dependent and QCI specific offset for the absolute threshold b2Threshold1Rsrq, used for Multi-Layer Service-Triggered Mobility.";
      type erienmnrmlrat:ddt-Lrat_GeranFreqRelQciB2ThrOffsets_b2Thr1RsrqGeranFreqQciOffset;
      default 0;
    }
    leaf b2Thr2GeranFreqQciOffset {
      description "The frequency group relation dependent and QCI specific offset for the absolute threshold b2Threshold2Geran, used for Multi-Layer Service-Triggered Mobility.";
      type erienmnrmlrat:ddt-Lrat_GeranFreqRelQciB2ThrOffsets_b2Thr2GeranFreqQciOffset;
      default 0;
    }
    leaf b2Thr1RsrpGeranFreqQciOffset {
      description "The frequency group relation dependent and QCI specific offset for the absolute threshold b2Threshold1Rsrp, used for Multi-Layer Service-Triggered Mobility.";
      type erienmnrmlrat:ddt-Lrat_GeranFreqRelQciB2ThrOffsets_b2Thr1RsrpGeranFreqQciOffset;
      default 0;
    }
    leaf qciProfileRef {
      description "Refers to the QCI profile MO, QciProfilePredefined or QciProfileOperatorDefined.";
      erienmyext:enm-type MOREF;
      type string;
    }
  } // end 'grouping struct-GeranFreqRelQciB2ThrOffsets'
  grouping struct-TacSvAndSnRange {
    leaf maxSn {
      description "Maximum Masked Serial Number (end of SN range).";
      yexte:dependencies "minSn =< maxSn";
      type erienmnrmlrat:ddt-Lrat_TacSvAndSnRange_maxSn;
      default 99;
    }
    leaf minSv {
      description "Minimum Software Version (beginning of SV range).";
      yexte:dependencies "minSv =< maxSv";
      type erienmnrmlrat:ddt-Lrat_TacSvAndSnRange_minSv;
      default 0;
    }
    leaf tac {
      description "Type allocation code.";
      type erienmnrmlrat:ddt-Lrat_TacSvAndSnRange_tac;
      default -1;
    }
    leaf maxSv {
      description "Maximum Software Version (end of SV range).";
      yexte:dependencies "minSv =< maxSv";
      type erienmnrmlrat:ddt-Lrat_TacSvAndSnRange_maxSv;
      default 98;
    }
    leaf minSn {
      description "Minimum Masked Serial Number (beginning of SN range).";
      yexte:dependencies "minSn =< maxSn";
      type erienmnrmlrat:ddt-Lrat_TacSvAndSnRange_minSn;
      default 0;
    }
  } // end 'grouping struct-TacSvAndSnRange'
  grouping struct-AcBarringConfig1xRtt {
    leaf acBarring10R9 {
      description "Access class barring factor configuration.\nThis parameter used for calculating the access class barring factor for access overload class N (N = 10 to 15).  It is the parameter \"PSIST\" in 3GPP2 C.S0004-A v6.0 for access overload class 10.";
      type erienmnrmlrat:ddt-Lrat_AcBarringConfig1xRtt_acBarring10R9;
      default 0;
    }
    leaf acBarringMsgR9 {
      description "Access class barring factor configuration.\nThis parameter used for modifying the access class barring factor for message transmissions.  It is the parameter \"MSG_PSIST\" in 3GPP2 C.S0004-A v6.0.";
      type erienmnrmlrat:ddt-Lrat_AcBarringConfig1xRtt_acBarringMsgR9;
      default 0;
    }
    leaf acBarringEmgR9 {
      description "Access class barring factor configuration.\nThis parameter used for calculating the access class barring factor for emergency calls and emergency message transmissions for access overload classes 0 through 9.  It is the parameter \"PSIST_EMG\" in 3GPP2 C.S0004-A v6.0";
      type erienmnrmlrat:ddt-Lrat_AcBarringConfig1xRtt_acBarringEmgR9;
      default 0;
    }
    leaf acBarring0to9R9 {
      description "Access class barring factor configuration.\nThis parameter used for calculating the access class barring factor for access overload classes 0 through 9.  It is the parameter \"PSIST\" in 3GPP2 C.S0004-A v6.0 for access overload classes 0 through 9.";
      type erienmnrmlrat:ddt-Lrat_AcBarringConfig1xRtt_acBarring0to9R9;
      default 0;
    }
    leaf acBarring15R9 {
      description "Access class barring factor configuration.\nThis parameter used for calculating the access class barring factor for access overload class N (N = 10 to 15).  It is the parameter \"PSIST\" in 3GPP2 C.S0004-A v6.0 for access overload class 15.";
      type erienmnrmlrat:ddt-Lrat_AcBarringConfig1xRtt_acBarring15R9;
      default 0;
    }
    leaf acBarring14R9 {
      description "Access class barring factor configuration.\nThis parameter used for calculating the access class barring factor for access overload class N (N = 10 to 15).  It is the parameter \"PSIST\" in 3GPP2 C.S0004-A v6.0 for access overload class 14.";
      type erienmnrmlrat:ddt-Lrat_AcBarringConfig1xRtt_acBarring14R9;
      default 0;
    }
    leaf acBarringRegR9 {
      description "Access class barring factor configuration.\nThis parameter used for modifying the access class barring factor for autonomous registrations.  It is the parameter \"REG_PSIST\" in 3GPP2 C.S0004-A v6.0";
      type erienmnrmlrat:ddt-Lrat_AcBarringConfig1xRtt_acBarringRegR9;
      default 0;
    }
    leaf acBarring13R9 {
      description "Access class barring factor configuration.\nThis parameter is used for calculating the access class barring factor for access overload class N (N = 10 to 15). It is the parameter \"PSIST\" in 3GPP2 C.S0004-A v6.0 for access overload class 13.";
      type erienmnrmlrat:ddt-Lrat_AcBarringConfig1xRtt_acBarring13R9;
      default 0;
    }
    leaf acBarring12R9 {
      description "Access class barring factor configuration.\nThis parameter used for calculating the access class barring factor for access overload class N (N = 10 to 15).  It is the parameter \"PSIST\" in 3GPP2 C.S0004-A v6.0 for access overload class 12.";
      type erienmnrmlrat:ddt-Lrat_AcBarringConfig1xRtt_acBarring12R9;
      default 0;
    }
    leaf acBarring11R9 {
      description "Access class barring factor configuration.\nThis parameter used for calculating the access class barring factor for access overload class N (N = 10 to 15).  It is the parameter \"PSIST\" in 3GPP2 C.S0004-A v6.0 for access overload class 11.";
      type erienmnrmlrat:ddt-Lrat_AcBarringConfig1xRtt_acBarring11R9;
      default 0;
    }
  } // end 'grouping struct-AcBarringConfig1xRtt'
  grouping struct-Cgi {
    leaf mnc {
      description "The MNC part of a PLMN identity used in the radio network.";
      type erienmnrmlrat:ddt-Lrat_Cgi_mnc;
      default 1;
    }
    leaf enbId {
      description "The ENodeB ID that forms part of the Cell Global Identity.";
      type erienmnrmlrat:ddt-Lrat_Cgi_enbId;
      default 0;
    }
    leaf mncLength {
      description "The length of the MNC part of a PLMN identity used in the radio network.";
      type erienmnrmlrat:ddt-Lrat_Cgi_mncLength;
      default 2;
    }
    leaf cellId {
      description "RBS internal ID attribute for EUtranCell.";
      type erienmnrmlrat:ddt-Lrat_Cgi_cellId;
      default 0;
    }
    leaf mcc {
      description "The MCC part of a PLMN identity used in the radio network";
      type erienmnrmlrat:ddt-Lrat_Cgi_mcc;
      default 1;
    }
  } // end 'grouping struct-Cgi'
  grouping struct-B2Cdma2000PCOffsetMCPC {
    leaf powerClass {
      description "Indicate the power class. Value should be unique in the structure.";
      type erienmnrmlrat:enum-PowerClass;
      default PC_2;
    }
    leaf b2Thr1RsrpCdma2000PCOffset {
      description "The frequency-relation specific offset for the absolute threshold b2Threshold1Rsrp, RSRP threshold1 for event B2, used for Multi-Layer Service-Triggered Mobility and HighPower UE.";
      type erienmnrmlrat:ddt-Lrat_B2Cdma2000PCOffsetMCPC_b2Thr1RsrpCdma2000PCOffset;
      default 0;
    }
    leaf b2Thr1RsrqCdma2000PCOffset {
      description "The frequency-relation specific offset for the absolute threshold b2Threshold1Rsrq, RSRQ threshold1 for event B2, used for Multi-Layer Service-Triggered Mobility and HighPower UE.";
      type erienmnrmlrat:ddt-Lrat_B2Cdma2000PCOffsetMCPC_b2Thr1RsrqCdma2000PCOffset;
      default 0;
    }
  } // end 'grouping struct-B2Cdma2000PCOffsetMCPC'
  grouping struct-CsfbRegParams1xRtt {
    leaf homeReg {
      description "CDMA2000 1xRTT Home registration indicator";
      type boolean;
      default true;
    }
    leaf parameterReg {
      description "CDMA2000 1xRTT Parameter-change registration indicator";
      type boolean;
      default true;
    }
    leaf registrationPeriod {
      description "CDMA2000 1xRTT Registration period";
      type erienmnrmlrat:ddt-Lrat_CsfbRegParams1xRtt_registrationPeriod;
      default 80;
    }
    leaf foreignSidReg {
      description "CDMA2000 1xRTT SID roamer registration indicator";
      type boolean;
      default true;
    }
    leaf multipleSid {
      description "CDMA2000 1xRTT Multiple SID storage indicator";
      type boolean;
      default false;
    }
    leaf totalZone {
      description "CDMA2000 1xRTT number of registration zones to be retained\nThe maximum number of zones in which the MS may be considered registered. 0 disables zone registration. Value of at least 2 should be used for hysteresis when zone registration is enabled.  For MTX border sites, parameter registrations should always be disabled and zone registration should be enabled.";
      type erienmnrmlrat:ddt-Lrat_CsfbRegParams1xRtt_totalZone;
      default 0;
    }
    leaf foreignNidReg {
      description "CDMA2000 1xRTT NID roamer registration indicator";
      type boolean;
      default true;
    }
    leaf registrationZone {
      description "CDMA2000 1xRTT Registration zone\nThe range for zones is only 0-255.  Unique zones are identified by REG_ZONE, plus the SID/NID of the zone.  When a mobile moves into a new registration zone (uniquely identified by REG_ZONE + SID + NID with its own timer) not on its internally stored list (up to TOTAL_ZONES entries) of visited registration zones, zone registration causes the mobile to register.  Zones in the mobile are deleted upon expiration of a timer stored on mobile.  After system access, timers (ZONE_TIMER value) are enabled for every zone except the one where the registration attempt was successful.";
      type erienmnrmlrat:ddt-Lrat_CsfbRegParams1xRtt_registrationZone;
      default 0;
    }
    leaf powerDownRegR9 {
      description "CDMA2000 1xRTT Power-down registration indicator\nIf set to TRUE, the UE that has a valid / current CDMA2000 1xRTT pre-registration performs a CDMA2000 1xRTT power down registration when it is switched off.";
      type boolean;
      default true;
    }
    leaf powerUpReg {
      description "CDMA2000 1xRTT Power-up registration indicator.";
      type boolean;
      default true;
    }
    leaf zoneTimer {
      description "CDMA2000 1xRTT zone timer length.\nThe higher the value, the less frequent the registrations.";
      type erienmnrmlrat:ddt-Lrat_CsfbRegParams1xRtt_zoneTimer;
      default 1;
    }
    leaf multipleNid {
      description "CDMA2000 1xRTT Multiple NID storage indicator";
      type boolean;
      default false;
    }
  } // end 'grouping struct-CsfbRegParams1xRtt'
  grouping struct-SpectrumEmissionReqMapping {
    leaf freqBand {
      description "A frequency band";
      type erienmnrmlrat:ddt-Lrat_SpectrumEmissionReqMapping_freqBand;
      default 1;
    }
    leaf spectrumEmissionReq {
      description "An additional spectrum emission requirement, as specified in 3GPP TS 36.101, table 6.2.4-1";
      type erienmnrmlrat:enum-NetworkSignallingValue;
      default NS_01;
    }
  } // end 'grouping struct-SpectrumEmissionReqMapping'
  grouping struct-TrafficModelPrb {
    leaf-list ulDlRatioPerQci {
      min-elements 0;
      max-elements 9;
      description "UL bit rate related to DL bit rate, per QCI. The value 100% means that UL has same load as DL. The value 0% means that there is no UL load.\nResolution: 1\nTakes effect: Feature start";
      type erienmnrmlrat:ddt-Lrat_TrafficModelPrb_ulDlRatioPerQci;
      default 0;
      default 0;
      default 0;
      default 0;
      default 0;
      default 0;
      default 0;
      default 0;
      default 0;
    }
    leaf noOfArtificialUsers {
      description "Number of artificial users\nResolution: 1\nTakes effect: Feature start";
      type erienmnrmlrat:ddt-Lrat_TrafficModelPrb_noOfArtificialUsers;
      default 0;
    }
    leaf-list qciDistSinrLow {
      min-elements 0;
      max-elements 9;
      description "Distribution of UEs per QCI when SINR is LOW.\nUnit: %\nResolution: 1\nTakes effect: Feature start\nDependencies: The sum of all values through the distributions qciDistSinrHigh, qciDistSinrMedium and  qciDistSinrLow must be 100%.";
      type erienmnrmlrat:ddt-Lrat_TrafficModelPrb_qciDistSinrLow;
      default 0;
      default 0;
      default 0;
      default 0;
      default 0;
      default 0;
      default 0;
      default 0;
      default 0;
    }
    leaf-list bitRatePerQci {
      min-elements 0;
      max-elements 9;
      description "Average required bit rate needed by the service\nUnit: kbit/s\nResolution: 1\nTakes effect: Feature start";
      type erienmnrmlrat:ddt-Lrat_TrafficModelPrb_bitRatePerQci;
      default 0;
      default 0;
      default 0;
      default 0;
      default 0;
      default 0;
      default 0;
      default 0;
      default 0;
    }
    leaf-list qciDistSinrMedium {
      min-elements 0;
      max-elements 9;
      description "Distribution of UEs per QCI when SINR is MEDIUM\nUnit: %\nResolution: 1\nTakes effect: Feature start\nDependencies: The sum of all values through the distributions qciDistSinrHigh, qciDistSinrMedium and  qciDistSinrLow must be 100%.";
      type erienmnrmlrat:ddt-Lrat_TrafficModelPrb_qciDistSinrMedium;
      default 100;
      default 0;
      default 0;
      default 0;
      default 0;
      default 0;
      default 0;
      default 0;
      default 0;
    }
    leaf bufferStatus {
      description "The status of the RLC buffer\nTakes effect: Feature start";
      type erienmnrmlrat:enum-RlcBufferStatus;
      default FULL_BUFFER;
    }
    leaf-list qciDistSinrHigh {
      min-elements 0;
      max-elements 9;
      description "Distribution of UEs per QCI when SINR is HIGH\nUnit: %\nResolution: 1\nTakes effect: Feature start\nDependencies: The sum of all values through the distributions qciDistSinrHigh, qciDistSinrMedium and qciDistSinrLow must be 100%.";
      type erienmnrmlrat:ddt-Lrat_TrafficModelPrb_qciDistSinrHigh;
      default 0;
      default 0;
      default 0;
      default 0;
      default 0;
      default 0;
      default 0;
      default 0;
      default 0;
    }
  } // end 'grouping struct-TrafficModelPrb'
  grouping struct-EUtranFreqToQciProfileRelation {
    leaf a5Thr2RsrqFreqQciOffset {
      description "The frequency-relation dependent and QCI specific offset for the absolute threshold a5Threshold2Rsrq, used for Multi-Layer Service-Triggered Mobility.";
      type erienmnrmlrat:ddt-Lrat_EUtranFreqToQciProfileRelation_a5Thr2RsrqFreqQciOffset;
      default 0;
    }
    leaf lbA5Threshold2RsrqOffset {
      description "QCI specific offset for the absolute threshold a5Threshold2Rsrq used for load management.";
      type erienmnrmlrat:ddt-Lrat_EUtranFreqToQciProfileRelation_lbA5Threshold2RsrqOffset;
      default 0;
    }
    leaf atoThresh2QciProfileHandling {
      description "QCI profile handling with regard to Admission-Triggered Offload (ATO), when ATO Level2 threshold is exceeded.";
      type erienmnrmlrat:enum-AtoQciProfileHandling;
      default ALLOWED;
    }
    leaf a3RsrqFreqQciOffsetAdjustment {
      description "Frequency-relation dependent and QCI-specific offset adjustment for the absolute offset a3OffsetRsrq, used for Multi-Layer Service-Triggered Mobility.";
      type erienmnrmlrat:ddt-Lrat_EUtranFreqToQciProfileRelation_a3RsrqFreqQciOffsetAdjustment;
      default 0;
    }
    leaf a3RsrpFreqQciOffsetAdjustment {
      description "Frequency-relation dependent and QCI-specific offset adjustment for the absolute offset a3OffsetRsrp, used for Multi-Layer Service-Triggered Mobility.";
      type erienmnrmlrat:ddt-Lrat_EUtranFreqToQciProfileRelation_a3RsrpFreqQciOffsetAdjustment;
      default 0;
    }
    leaf qciProfileRef {
      description "Refers to the QCI profile MO, QciProfilePredefined or QciProfileOperatorDefined.";
      erienmyext:enm-type MOREF;
      type string;
    }
    leaf timeToTriggerA3 {
      description "Frequency-relation dependant and QCI-specific time-to-trigger value for event A3, used for Multi-Layer Service-Triggered Mobility.\nIf timeToTriggerA3 has value different than -1 then it is used instead of ReportConfigEUtraBestCell.timeToTriggerA3 (for Intra-frequency) or ReportConfigEUtraIFBestCell.timeToTriggerA3 (for Inter-frequency).";
      type erienmnrmlrat:ddt-Lrat_EUtranFreqToQciProfileRelation_timeToTriggerA3;
      default -1;
    }
    leaf timeToTriggerA3Rsrq {
      description "Frequency-relation dependant and QCI-specific time-to-trigger value for event A3 with trigger quantity RSRQ, used for Multi-Layer Service-Triggered Mobility. Used for inter-frequency.\nIf timeToTriggerA3Rsrq has value different than -1 then it is used instead of EutranFreqRelation::eutranFreqToQciProfileRelation.timeToTriggerA3.";
      type erienmnrmlrat:ddt-Lrat_EUtranFreqToQciProfileRelation_timeToTriggerA3Rsrq;
      default -1;
    }
    leaf lbQciProfileHandling {
      description "Specifies QCI profile handling with regard to load management.";
      type erienmnrmlrat:enum-LbQciProfileHandling;
      default ALLOWED;
    }
    leaf a5Thr1RsrpFreqQciOffset {
      description "The frequency-relation dependent and QCI specific offset for the absolute threshold a5Threshold1Rsrp, used for Multi-Layer Service-Triggered Mobility.";
      type erienmnrmlrat:ddt-Lrat_EUtranFreqToQciProfileRelation_a5Thr1RsrpFreqQciOffset;
      default 0;
    }
    leaf a5Thr1RsrqFreqQciOffset {
      description "The frequency-relation dependent and QCI specific offset for the absolute threshold a5Threshold1Rsrq, used for Multi-Layer Service-Triggered Mobility.";
      type erienmnrmlrat:ddt-Lrat_EUtranFreqToQciProfileRelation_a5Thr1RsrqFreqQciOffset;
      default 0;
    }
    leaf a5Thr2RsrpFreqQciOffset {
      description "The frequency-relation dependent and QCI specific offset for the absolute threshold a5Threshold2Rsrp, used for Multi-Layer Service-Triggered Mobility.";
      type erienmnrmlrat:ddt-Lrat_EUtranFreqToQciProfileRelation_a5Thr2RsrpFreqQciOffset;
      default 0;
    }
    leaf atoThresh1QciProfileHandling {
      description "QCI profile handling with regard to Admission-Triggered Offload (ATO), when ATO Level1 threshold is exceeded.";
      type erienmnrmlrat:enum-AtoQciProfileHandling;
      default ALLOWED;
    }
    leaf lbA5Threshold2RsrpOffset {
      description "QCI specific offset for the absolute threshold a5Threshold2Rsrp used for load management.";
      type erienmnrmlrat:ddt-Lrat_EUtranFreqToQciProfileRelation_lbA5Threshold2RsrpOffset;
      default 0;
    }
  } // end 'grouping struct-EUtranFreqToQciProfileRelation'
  grouping struct-DistributionInfo {
    leaf-list eUtranFreqRefList {
      min-elements 0;
      max-elements 8;
      description "UEs shall be distributed between these frequencies. The position of the elements in this list must correspond to the position of the elements in the freqDistributionList.";
      yexte:dependencies "Must have the same length as the freqDistributionList.";
      erienmyext:enm-type MOREF;
      type string;
    }
    leaf-list freqDistributionList {
      min-elements 0;
      max-elements 8;
      description "The percentage of the UEs to be released to a certain frequency. The position of the elements in this list must correspond to the position of the elements in the eUtranFreqRefList.";
      yexte:dependencies "Must have the same length as the eUtranFreqRefList. The sum of the percentages must be equal or less than 100%.";
      type erienmnrmlrat:ddt-Lrat_DistributionInfo_freqDistributionList;
    }
  } // end 'grouping struct-DistributionInfo'
  grouping struct-IflbConfig {
    leaf stopIncomingIflbThreshold {
      status deprecated {
        yexte:status-information "Since 18.Q4. Has no functional behavior. Planned to be removed.";
      }
      description "If cellType is set to PRIORITY and this threshold is exceeded by cell subscription ratio, the cell notifies neighboring cells to stop IFLB towards the cell.\nNo effect when cellType is set to NON_PRIORITY.";
      yexte:dependencies stopIncomingIFLBThreshold<=lbEUtranTriggerOffloadThreshold;
      type erienmnrmlrat:ddt-Lrat_IflbConfig_stopIncomingIflbThreshold;
      default 60;
    }
    leaf stopOutgoingIflbEnabled {
      status deprecated {
        yexte:status-information "Since 18.Q4. Has no functional behavior. Planned to be removed.";
      }
      description "If cellType is set to NON_PRIORITY and this parameter is set to TRUE, the cell stops outgoing load balancing towards cells that broadcast Stop Incoming IFLB Traffic Load State.\nNo effect when cellType is set to PRIORITY.";
      type boolean;
      default false;
    }
  } // end 'grouping struct-IflbConfig'
  grouping struct-UnlicensedFrequencyProperties {
    leaf channelCharacteristic {
      description "If this EARFCN can be used or if there are any restrictions.";
      type erienmnrmlrat:enum-ChannelCharacteristicList;
      default CHANNEL_DISABLED;
    }
    leaf unlicensedBand {
      description "Unlicensed band number according to 3GPP TS 36.104. For band 46; 4 sub-bands are defined with a sub-set of allowed EARFCN. This needs to be checked when adding new carriers.";
      type erienmnrmlrat:enum-UnlicensedBandList;
      default NONE;
    }
    leaf unlicensedEarfcn {
      description "EARFCN of the unlicensed channel in the unlicensedBand.";
      type erienmnrmlrat:enum-UnlicensedEarfcnList;
      default NONE;
    }
    leaf maxUnlicensedTxPower {
      description "Max allowed output power for LAA EARFCN. Below local or county regulations for unlincensed bands and subbands.";
      type erienmnrmlrat:ddt-Lrat_UnlicensedFrequencyProperties_maxUnlicensedTxPower;
      default 0;
    }
  } // end 'grouping struct-UnlicensedFrequencyProperties'
  grouping struct-AcBarringConfig {
    leaf acBarringTime {
      description "Mean access barring time in seconds for mobile originating signalling.";
      type erienmnrmlrat:ddt-Lrat_AcBarringConfig_acBarringTime;
      default 64;
    }
    leaf acBarringFactor {
      description "If the random number drawn by the UE is lower than this value, access is allowed. Otherwise the access is barred.";
      yexte:dependencies "AC Barring Factor is automatically adjusted in SIB2, regardless of values in this struct, if corresponding AcBarringMode is set to AUTO and one of the following features is activated:\n- Load-Based Access Barring\n- Progressive Access Barring\n- Progressive Barring of Special Access Classes\n- PLMN-Specific Access Barring";
      type erienmnrmlrat:ddt-Lrat_AcBarringConfig_acBarringFactor;
      default 95;
    }
    leaf-list acBarringForSpecialAC {
      min-elements 0;
      max-elements 5;
      description "Access class barring for AC 11-15. The first instance in the list is for AC 11, second is for AC 12, and so on.";
      yexte:dependencies "AC Barring for AC 11-15 is automatically adjusted in SIB2, regardless of values in this struct, if corresponding AcBarringMode is set to AUTO and Progressive Barring of Special Access Classes is activated.";
      type boolean;
      default false;
      default false;
      default false;
      default false;
      default false;
    }
  } // end 'grouping struct-AcBarringConfig'
  grouping struct-PlmnIdentity {
    leaf mnc {
      description "The MNC part of a PLMN identity used in the radio network.\n";
      type erienmnrmlrat:ddt-Lrat_PlmnIdentity_mnc;
      mandatory true;
    }
    leaf mncLength {
      description "The length of the MNC part of a PLMN identity used in the radio network.\n";
      type erienmnrmlrat:ddt-Lrat_PlmnIdentity_mncLength;
      mandatory true;
    }
    leaf mcc {
      description "The MCC part of a PLMN identity used in the radio network.\n";
      type erienmnrmlrat:ddt-Lrat_PlmnIdentity_mcc;
      mandatory true;
    }
  } // end 'grouping struct-PlmnIdentity'
  grouping struct-EutranCellArea {
    leaf posCellBearing {
      description "Defines the cell bearing in deci-degrees clockwise from north.";
      type erienmnrmlrat:ddt-Lrat_EutranCellArea_posCellBearing;
      default -1;
    }
    leaf posCellOpeningAngle {
      description "Defines the opening angle of a cell (3 dB beam width) in deci-degrees.\nThe value 0 is used to define an omni cell.";
      type erienmnrmlrat:ddt-Lrat_EutranCellArea_posCellOpeningAngle;
      default -1;
    }
    leaf posCellRadius {
      description "Defines the cell radius in meters.\n\n";
      type erienmnrmlrat:ddt-Lrat_EutranCellArea_posCellRadius;
      default 0;
    }
  } // end 'grouping struct-EutranCellArea'
  grouping struct-PmUeMeasIntraFreq {
    leaf reportConfigEUtraIntraFreqPmRef {
      description "Reference to an instance of a ReportConfigEUtraIntraFreqPm MO containing the report configuration parameters to use for this intra frequency measurement.\nTakes effect: New connection\nDisturbance: None\n";
      erienmyext:enm-type MOREF;
      type string;
    }
    leaf eutranFrequencyRef {
      description "The reference to an instance of a EUtranFrequency MO containing the measurement object parameters to use for this intra frequency measurement.\nTakes effect: New connection\nDisturbance: None\n";
      erienmyext:enm-type MOREF;
      type string;
    }
  } // end 'grouping struct-PmUeMeasIntraFreq'
  grouping struct-B2UtranPCOffsetMCPC {
    leaf b2Thr1RsrqUtranPCOffset {
      description "The frequency-relation specific offset for the absolute threshold b2Threshold1Rsrq, RSRQ threshold1 for event B2, used for Multi-Layer Service-Triggered Mobility and HighPower UE.";
      type erienmnrmlrat:ddt-Lrat_B2UtranPCOffsetMCPC_b2Thr1RsrqUtranPCOffset;
      default 0;
    }
    leaf b2Thr1RsrpUtranPCOffset {
      description "The frequency-relation specific offset for the absolute threshold b2Threshold1Rsrp, RSRP threshold1 for event B2, used for Multi-Layer Service-Triggered Mobility and HighPower UE.";
      type erienmnrmlrat:ddt-Lrat_B2UtranPCOffsetMCPC_b2Thr1RsrpUtranPCOffset;
      default 0;
    }
    leaf powerClass {
      description "Indicate the power class. Value should be unique in the structure.";
      type erienmnrmlrat:enum-PowerClass;
      default PC_2;
    }
  } // end 'grouping struct-B2UtranPCOffsetMCPC'
  grouping struct-FreqPrioEUTRA {
    leaf arpPrio {
      description "Prioritizes EUTRAN frequencies among all frequencies related to the cell. When the feature Service or Priority-Triggered Inter-Frequency Handover is activated, sets the priority value to the frequency to perform mobility for a bearer with specific ARP Priority Level.\nThe value -1 means the frequency is excluded.\nThe value 0 means the lowest priority.\nThe value 7 means the highest priority.";
      type erienmnrmlrat:ddt-Lrat_FreqPrioEUTRA_arpPrio;
      default 0;
    }
    leaf atoAllowed {
      description "Indicates if the related EUTRAN frequency is allowed as a target frequency for Admission-Triggered Offload feature.";
      type boolean;
      default false;
    }
    leaf connectedModeMobilityPrio {
      description "Prioritizes EUTRAN frequencies among all frequencies related to the cell for UEs in connected mode. (0 means the lowest priority. -1 means the frequency is excluded.)\nWhen value is configured to -1000, the parameter is ignored and the value of connectedModeMobilityPrio in MO: EUtranFreqRelation is applied.";
      type erienmnrmlrat:ddt-Lrat_FreqPrioEUTRA_connectedModeMobilityPrio;
      default -1000;
    }
    leaf offloadAllowed {
      description "Indicates if the related EUTRAN frequency is allowed as a target frequency for offload only.\nThis parameters takes effect only when loadBalancingAllowed is set to false.";
      type boolean;
      default false;
    }
    leaf voicePrio {
      description "Prioritizes EUTRAN frequencies among all frequencies related to the cell for UEs in connected mode. Sets the priority to which frequency to perform mobility to for a voice session.\nThe value -1 means the frequency is excluded.\nThe value 0 means the lowest priority.\nWhen value is configured to -1000, the parameter is ignored and the value of voicePrio in MO: EUtranFreqRelation is applied.";
      type erienmnrmlrat:ddt-Lrat_FreqPrioEUTRA_voicePrio;
      default -1000;
    }
    leaf cellReselectionPriority {
      description "CellReselectionPriority concerns the absolute priority of the concerned carrier frequency, as transmitted to the UE in the IE idleModeMobilityControlInfo in the RRCConnectionRelease message, and used by the cell reselection procedure. Corresponds with parameter \"priority\" in TS 36.304\nValue 0 means: lowest priority. The UE behaviour for the case the field is absent, if applicable, is specified in TS 36.304.\nWhen value is configured to -1000, the frequency is not included in the idleModeMobilityControlInfo of the RRCConnectionRelease message.";
      type erienmnrmlrat:ddt-Lrat_FreqPrioEUTRA_cellReselectionPriority;
      default -1000;
    }
    leaf arfcnValueEUtranDl {
      description "Indicates the ARFCN applicable for a downlink E-UTRA carrier frequency, as defined in 3GPP TS 36.104 for specified E-UTRA bands. For TDD this also indicates the ARFCN for uplink. The values that can be used depends on national operator specific frequency allocation as well as from the supported frequency band(s) of the equipment in the eNodeB.\nWhen value is configured to -1000, the parameter is ignored.";
      type erienmnrmlrat:ddt-Lrat_FreqPrioEUTRA_arfcnValueEUtranDl;
      default -1000;
    }
    leaf loadBalancingAllowed {
      description "Indicates if the related EUTRAN frequency is allowed as a target frequency for load balancing and offloading features.\nIf set to false, the parameter offloadAllowed controls if the UE is allowed to be offloaded.";
      type boolean;
      default true;
    }
  } // end 'grouping struct-FreqPrioEUTRA'
  grouping struct-MobilityParams1xRtt {
    leaf fchFchInitSetupRc11 {
      description "FPC_FCH_INIT_SETUP_RC11 in 3GPP2 C.S0097.\n8dB, matches ECAM range/granularity of 8 bits/0.125dB.";
      type erienmnrmlrat:ddt-Lrat_MobilityParams1xRtt_fchFchInitSetupRc11;
      default 64;
    }
    leaf fchFchInitSetupRc12 {
      description "FPC_FCH_INIT_SETUP_RC12 in 3GPP2 C.S0097.\n8dB, matches ECAM range/granularity of 8 bits/0.125dB.";
      type erienmnrmlrat:ddt-Lrat_MobilityParams1xRtt_fchFchInitSetupRc12;
      default 64;
    }
    leaf gcsnaL2AckTimer {
      description "Length of time the mobile station or IWS waits after it sends GCSNA1xCircuitService message, in units of 80ms";
      type erienmnrmlrat:ddt-Lrat_MobilityParams1xRtt_gcsnaL2AckTimer;
      default 3;
    }
    leaf protocolRev {
      description "P_REV in 3GPP2 C.S0097\nThe protocol revision level of the BTS (e.g. 5=IS95B, 6=IS2000 Release 0, 7=IS2000 Release A)";
      type erienmnrmlrat:ddt-Lrat_MobilityParams1xRtt_protocolRev;
      default 0;
    }
    leaf authenticationEnabled {
      description "AUTH in 3GPP2 C.S0097.\nThis parameter indicates whether the authentication is enabled.";
      type boolean;
      default false;
    }
    leaf localTimeOffset {
      description "LTM_OFF in 3GPP2 C.S0097.\nThis parameter indicates the offset of local time in units of 0.5hr from system time (GPS).";
      type erienmnrmlrat:ddt-Lrat_MobilityParams1xRtt_localTimeOffset;
      default 0;
    }
    leaf mcc {
      description "Part of country code\nMCC of USA = 310\nMCC of Canada = 302\nMCC of Australia = 505";
      type erienmnrmlrat:ddt-Lrat_MobilityParams1xRtt_mcc;
      default 0;
    }
    leaf minProtocolRev {
      description "MIN_P_REV in 3GPP2 C.S0097\n(e.g. 1 for 1900 MHz,  3 for 800 MHz)";
      type erienmnrmlrat:ddt-Lrat_MobilityParams1xRtt_minProtocolRev;
      default 3;
    }
    leaf imsiTSupported {
      description "BTS IMSI-T supported indicator\nSet to True to enable IMSI-T support.";
      type boolean;
      default false;
    }
    leaf preferredMsidType {
      description "PREF_MSID_TYPE in 3GPP2 C.S0097.\nThe preferred identity used by mobile";
      yexte:dependencies "Depends on  IMSI_T_SUPPORTED. If IMSI_T_SUPPORTED is false, the value can not be set as \"IMSIS_ESN\"";
      type erienmnrmlrat:enum-CdmaMsIdType;
      default IMSI_ESN_OR_TMSI;
    }
    leaf maxNumAltServiceOption {
      description "MAX_NUM_ALT_SO in 3GPP2 C.S0097.\nSet the value to 1 Per CAB 128 only if not using PREV 7 BTS. Value 0 is also a flag to IVSN to query if mobile capability is not stored in VLR, even for P_REV > 5 mobiles (Ensure a QueryOpt for IVSN is selected in MTX Table NOISBSC).  Enable ORCM set TRUE will address CAB-128 concern and effectively negates reason for CAB-128.";
      type erienmnrmlrat:ddt-Lrat_MobilityParams1xRtt_maxNumAltServiceOption;
      default 0;
    }
    leaf pilotIncrement {
      description "PILOT_INC in 3GPP2 C.S0097\nThis parameter indicates the Pilot PN sequence offset index increment. The interval between pilots for base stations in a system.";
      type erienmnrmlrat:ddt-Lrat_MobilityParams1xRtt_pilotIncrement;
      default 4;
    }
    leaf fchFchInitSetupRc4 {
      description "FPC_FCH_INIT_SETUP_RC4 in 3GPP2 C.S0097.\n7dB, matches ECAM range/granularity of 8 bits/0.125dB.";
      type erienmnrmlrat:ddt-Lrat_MobilityParams1xRtt_fchFchInitSetupRc4;
      default 64;
    }
    leaf fchFchInitSetupRc5 {
      description "FPC_FCH_INIT_SETUP_RC5 in 3GPP2 C.S0097.\n7dB, matches ECAM range/granularity of 8 bits/0.125dB.";
      type erienmnrmlrat:ddt-Lrat_MobilityParams1xRtt_fchFchInitSetupRc5;
      default 56;
    }
    leaf imsiBit11and12 {
      description "IMSI_11_12 in 3GPP2 C.S0097.\nThe 11th and 12th digits of the IMSI.";
      type erienmnrmlrat:ddt-Lrat_MobilityParams1xRtt_imsiBit11and12;
      default 0;
    }
    leaf fchFchInitSetupRc3 {
      description "FPC_FCH_INIT_SETUP_RC3 in 3GPP2 C.S0097.\n7dB, matches ECAM range/granularity of 8 bits/0.125dB.";
      type erienmnrmlrat:ddt-Lrat_MobilityParams1xRtt_fchFchInitSetupRc3;
      default 56;
    }
    leaf gcsnaSequenceContextTimer {
      description "GCSNASequenceContextTimer value\nThe value of GCSNASequenceContextTimer is greater than the value of GCSNAL2AckTimer. This field is in units of 100 ms.";
      type erienmnrmlrat:ddt-Lrat_MobilityParams1xRtt_gcsnaSequenceContextTimer;
      default 5;
    }
    leaf dayLightSaving {
      description "DAYLT in 3GPP2 C.S0097.\nThis parameter indicates whether Daylight savings is on or off.";
      type boolean;
      default false;
    }
  } // end 'grouping struct-MobilityParams1xRtt'
  grouping struct-AcBarringPresence {
    leaf acBarringPriorityCsfb {
      description "Priority Level of CSFB Access Class used by Progressive Access Barring algorithm.";
      type erienmnrmlrat:enum-AcBarringPriorityLevel;
      default PRIORITY0;
    }
    leaf-list acBarringPrioMoSignalingSpecAc {
      min-elements 5;
      max-elements 5;
      description "Priority Levels of MO Signaling Special Access Classes used by Progressive Barring for Special Access Classes algorithm.";
      type erienmnrmlrat:enum-AcBarringPriorityLevel;
      default PRIORITY0;
      default PRIORITY0;
      default PRIORITY0;
      default PRIORITY0;
      default PRIORITY0;
    }
    leaf-list acBarringPrioMoDataSpecAc {
      min-elements 5;
      max-elements 5;
      description "Priority Levels of MO Data Special Access Classes used by Progressive Barring for Special Access Classes algorithm.";
      type erienmnrmlrat:enum-AcBarringPriorityLevel;
      default PRIORITY0;
      default PRIORITY0;
      default PRIORITY0;
      default PRIORITY0;
      default PRIORITY0;
    }
    leaf-list acBarringPrioCsfbSpecAc {
      min-elements 5;
      max-elements 5;
      description "Priority Levels of CSFB Special Access Classes used by Progressive Barring for Special Access Classes algorithm.";
      type erienmnrmlrat:enum-AcBarringPriorityLevel;
      default PRIORITY0;
      default PRIORITY0;
      default PRIORITY0;
      default PRIORITY0;
      default PRIORITY0;
    }
    leaf acBarringPrioEmergencySpecAc {
      description "Priority Level of Emergency Special Access Class used by Progressive Barring for Special Access Classes algorithm.";
      type erienmnrmlrat:enum-AcBarringPriorityLevel;
      default PRIORITY0;
    }
    leaf acBarringPriorityMmtelVideo {
      description "Priority Level of MMTEL Video Access Class used by Progressive Access Barring algorithm.";
      type erienmnrmlrat:enum-AcBarringPriorityLevel;
      default PRIORITY0;
    }
    leaf acBarringForEmergencySpecAcPres {
      description "Specifies presence of Emergency special Access Class configuration in SIB2.";
      type erienmnrmlrat:enum-AcBarringModeEm;
      default MANUAL;
    }
    leaf acBarringForMmtelVideoPresence {
      description "Presence of IE ssac-BarringForMMTEL-Video-r9 in SIB2.";
      type erienmnrmlrat:enum-AcBarringMode;
      default OFF;
    }
    leaf acBarringForMoDataPresence {
      description "Specifies presence of Information Element ac-BarringForMO-Data in SIB2.";
      type erienmnrmlrat:enum-AcBarringMode;
      default OFF;
    }
    leaf acBarringForCsfbPresence {
      description "Specifies presence of ac-BarringForCSFB in SIB2.";
      type erienmnrmlrat:enum-AcBarringMode;
      default OFF;
    }
    leaf-list acBarringPrioMmtelVoiceSpecAc {
      min-elements 5;
      max-elements 5;
      description "Priority Levels of MMTEL Voice Special Access Classes used by Progressive Barring for Special Access Classes algorithm.";
      type erienmnrmlrat:enum-AcBarringPriorityLevel;
      default PRIORITY0;
      default PRIORITY0;
      default PRIORITY0;
      default PRIORITY0;
      default PRIORITY0;
    }
    leaf acBarringForMoSignPresence {
      description "Specifies presence of Information Element ac-BarringForMO-Signalling in SIB2.";
      type erienmnrmlrat:enum-AcBarringMode;
      default OFF;
    }
    leaf acBarringPriorityMoSignaling {
      description "Priority Level of MO Signaling Access Class used by Progressive Access Barring algorithm.";
      type erienmnrmlrat:enum-AcBarringPriorityLevel;
      default PRIORITY0;
    }
    leaf acBarringPriorityMoData {
      description "Priority Level of MO Data Access Class used by Progressive Access Barring algorithm.";
      type erienmnrmlrat:enum-AcBarringPriorityLevel;
      default PRIORITY0;
    }
    leaf acBarringForMmtelVoicePresence {
      description "Presence of IE ssac-BarringForMMTEL-Voice-r9 in SIB2.";
      type erienmnrmlrat:enum-AcBarringMode;
      default OFF;
    }
    leaf-list acBarringPrioMmtelVideoSpecAc {
      min-elements 5;
      max-elements 5;
      description "Priority Levels of MMTEL Video Special Access Classes used by Progressive Barring for Special Access Classes algorithm.";
      type erienmnrmlrat:enum-AcBarringPriorityLevel;
      default PRIORITY0;
      default PRIORITY0;
      default PRIORITY0;
      default PRIORITY0;
      default PRIORITY0;
    }
    leaf acBarringPriorityMmtelVoice {
      description "Priority Level of MMTEL Voice Access Class used by Progressive Access Barring algorithm.";
      type erienmnrmlrat:enum-AcBarringPriorityLevel;
      default PRIORITY0;
    }
  } // end 'grouping struct-AcBarringPresence'
  grouping moc-PimCancellationConfig-keys {
    description "Key(s) for MOC PimCancellationConfig";
    leaf id {
      erienmyext:no-notification;
      description "The value component of the RDN.";
      mandatory true;
      yexte:ecim-name pimCancellationConfigId;
      type string;
    }
  } // end 'grouping moc-PimCancellationConfig-keys'
  grouping moc-PimCancellationConfig {
    description "PIM cancellation configuration data of SectorCarrier participating in PIM cancellation function.";
    leaf pimCancellationFunctionRef {
      description "Refers to PimCancellationFunction instance to indicate PIM cancellation function SectorCarrier is participating in.";
      yexte:dependencies "PimCancellationConfig MOs under the same SectorCarrier MOs are not allowed to refer to the same PimCancellationFunction MO.";
      erienmyext:enm-type MOREF;
      type string;
    }
    leaf dlPimCandidate {
      description "Include DL carriers for PIM calculation.";
      type boolean;
      default false;
    }
    leaf ulPimCancellationMode {
      description "PIM cancellation mode on UL carriers.";
      type erienmnrmlrat:enum-UlPimCancellationMode;
      default EXCLUDED;
    }
  } // end 'grouping moc-PimCancellationConfig'
  grouping moc-FlexibleQoSGroup-keys {
    description "Key(s) for MOC FlexibleQoSGroup";
    leaf id {
      erienmyext:no-notification;
      description "The value component of the RDN.";
      mandatory true;
      yexte:ecim-name flexibleQoSGroupId;
      type string;
    }
  } // end 'grouping moc-FlexibleQoSGroup-keys'
  grouping moc-FlexibleQoSGroup {
    description "Group of members to assign a bearer certain SCI profile. Multiple members in the same group must not be applicable to the same bearer.";
    leaf qciProfileRef {
      description "Reference to QCI profile MO, QciProfilePredefined or QciProfileOperatorDefined.";
      mandatory true;
      yexte:disturbances "Changing this attribute can affect traffic.";
      yexte:takes-effect "Cell lock/unlock";
      yexte:dependencies "Each qciProfileRef attribute in different FlexibleQoSGroup MOCs must be unique. Default QCI profiles cannot be used.";
      erienmyext:enm-type MOREF;
      type string;
    }
  } // end 'grouping moc-FlexibleQoSGroup'
  grouping moc-Rrc-keys {
    description "Key(s) for MOC Rrc";
    leaf id {
      erienmyext:no-notification;
      description "The value component of the RDN.\n";
      mandatory true;
      yexte:ecim-name rrcId;
      type string;
    }
  } // end 'grouping moc-Rrc-keys'
  grouping moc-Rrc {
    description "Models the manageable RRC protocol characteristics.\n\nThe RDN of this MO is Rrc=1.";
    leaf t304Br {
      description "CAT-M UE timer to supervise successful handover completion according to 3GPP TS 36.331.";
      yexte:disturbances "Lowering the value can stop outgoing HO.";
      yexte:takes-effect "New connection";
      type erienmnrmlrat:ddt-Lrat_Rrc_t304Br;
      default 1000;
    }
    leaf t301NbIot {
      status deprecated {
        yexte:status-information "Since 17.Q3. Planned to be removed.";
      }
      description "NbIot UE timer to supervise a response to RRC Connection Reestablishment Request (according to 3GPP TS 36.331), during a radio connection re-establishment procedure. The UE returns to Idle and optionally starts to reconnect over NAS when the timer expires. Provided in NB-SIB2.";
      yexte:disturbances "Lowering the value can increase drop rate.";
      yexte:takes-effect "Next cell unlock";
      type erienmnrmlrat:ddt-Lrat_Rrc_t301NbIot;
      default 10000;
    }
    leaf t301Br {
      description "UE timer to supervise a response to RRC Connection Reestablishment Request, according to 3GPP TS 36.331, during a radio connection re-establishment procedure. The UE returns to Idle and optionally starts to reconnect over NAS when the timer expires.\nProvided to the Bandwidth reduced UE by System Information.";
      yexte:disturbances "Lowering the value can increase drop rate.";
      type erienmnrmlrat:ddt-Lrat_Rrc_t301Br;
      default 0;
    }
    leaf t320 {
      description "Validity time for cell reselection priority information provided by dedicated signaling.\nUsed by the UE.";
      type erienmnrmlrat:ddt-Lrat_Rrc_t320;
      default 30;
    }
    leaf t300 {
      description "UE timer to supervise a response to RRC Connection Request (according to 3GPP TS 36.331).\nProvided to the UE by System Information.";
      yexte:disturbances "Lowering the value can decrease accessibility.";
      type erienmnrmlrat:ddt-Lrat_Rrc_t300;
      default 1000;
    }
    leaf t311 {
      description "UE timer triggered at radio link failure to supervise the period where the UE tries to re-establish the radio connection, either by performing RRC Connection Reestablishment (according to 3GPP TS 36.331), or by finding a suitable cell on another RAT. The UE returns to Idle and optionally starts to reconnect over NAS when the timer expires.\nProvided to the UE by System Information.";
      yexte:disturbances "Lowering the value can increase drop rate.";
      type erienmnrmlrat:ddt-Lrat_Rrc_t311;
      default 3000;
    }
    leaf t300NbIot {
      description "NbIot UE timer to supervise a response to RRC Connection Request (according to 3GPP TS 36.331). Provided in NB-SIB2.";
      yexte:disturbances "Lowering the value can decrease accessibility.";
      yexte:takes-effect "Next cell unlock";
      type erienmnrmlrat:ddt-Lrat_Rrc_t300NbIot;
      default 40000;
    }
    leaf tWaitForRrcConnReest {
      description "Waiting time for the RRC message RRC Connection Reestablishment Request upon detecting Radio Link Failure.\nUsed by the RBS.\n";
      yexte:takes-effect "New connection";
      type erienmnrmlrat:ddt-Lrat_Rrc_tWaitForRrcConnReest;
      default 6;
    }
    leaf t301 {
      description "UE timer to supervise a response to RRC Connection Reestablishment Request (according to 3GPP TS 36.331), during a radio connection re-establishment procedure. The UE returns to Idle and optionally starts to reconnect over NAS when the timer expires.\nProvided to the UE by System Information.";
      yexte:disturbances "Lowering the value can increase drop rate.";
      type erienmnrmlrat:ddt-Lrat_Rrc_t301;
      default 400;
    }
    leaf t304 {
      description "UE timer to supervise successful handover completion according to 3GPP TS 36.331.";
      yexte:disturbances "Lowering the value can stop outgoing HO.";
      type erienmnrmlrat:ddt-Lrat_Rrc_t304;
      default 1000;
    }
    leaf t300Br {
      description "UE timer to supervise a response to RRC Connection Request, according to 3GPP TS 36.331.\nProvided to the Bandwidth reduced UE by System Information.";
      yexte:disturbances "Lowering the value can decrease accessibility.";
      type erienmnrmlrat:ddt-Lrat_Rrc_t300Br;
      default 0;
    }
    leaf tRrcConnectionReconfiguration {
      description "Waiting time for the RRC message RRC Connection Reconfiguration Complete.\nUsed by the RBS.\n";
      yexte:takes-effect "New connection.";
      type erienmnrmlrat:ddt-Lrat_Rrc_tRrcConnectionReconfiguration;
      default 6;
    }
    leaf tRrcConnReest {
      description "Waiting time for the RRC message RRC Connection Reestablishment Complete.\nUsed by the RBS.\n";
      yexte:takes-effect "New connection";
      type erienmnrmlrat:ddt-Lrat_Rrc_tRrcConnReest;
      default 1;
    }
    leaf t311NbIot {
      status deprecated {
        yexte:status-information "Since 17.Q3. Planned to be removed.";
      }
      description "NbIot UE timer triggered at radio link failure to supervise the period where the UE tries to re-establish the radio connection, either by performing RRC Connection Reestablishment (according to 3GPP TS 36.331), or by finding a suitable cell on another RAT. The UE returns to Idle and optionally starts to reconnect over NAS when the timer expires. Provided in NB-SIB2.";
      yexte:disturbances "Lowering the value can increase drop rate.";
      yexte:takes-effect "Next cell unlock";
      type erienmnrmlrat:ddt-Lrat_Rrc_t311NbIot;
      default 5000;
    }
  } // end 'grouping moc-Rrc'
  grouping moc-UeMeasControl-keys {
    description "Key(s) for MOC UeMeasControl";
    leaf id {
      erienmyext:no-notification;
      description "The value component of the RDN.\n";
      mandatory true;
      yexte:ecim-name ueMeasControlId;
      type string;
    }
  } // end 'grouping moc-UeMeasControl-keys'
  grouping moc-UeMeasControl {
    description "Models the manageable characteristics for UE measurements.\n\nThe RDN of this MO is UeMeasControl=1.";
    leaf maxMeasUtraFdd {
      description "The number of measurements that can be concurrently performed by the UE on UTRA FDD measurement objects.";
      yexte:takes-effect "New connection";
      type erienmnrmlrat:ddt-Lrat_UeMeasControl_maxMeasUtraFdd;
      default 5;
    }
    leaf maxMeasCdma2000eHrpd {
      description "The number of measurements that can be concurrently performed by the UE on CDMA2000 eHRPD measurement objects.";
      yexte:takes-effect "New connection";
      type erienmnrmlrat:ddt-Lrat_UeMeasControl_maxMeasCdma2000eHrpd;
      default 5;
    }
    leaf csfbHoTargetSearchTimer {
      description "Length of time the eNodeB waits for reports from B1 and B2 measurements configured in the UE for CS Fallback reasons.";
      yexte:takes-effect "New connection";
      type erienmnrmlrat:ddt-Lrat_UeMeasControl_csfbHoTargetSearchTimer;
      default 500;
    }
    list prioOffsetPerQci {
      min-elements 0;
      max-elements 19;
      key auto-generated-struct-key;
      leaf auto-generated-struct-key {
        type uint16;
        description "This leaf has been injected to allow for struct instances in a sequence to be ordered.";
        mandatory true;
      }
      description "Parameters for service-specific priority offset for a certain QCI profile.";
      erienmyext:enm-type STRUCT;
      uses erienmnrmlrat:struct-PrioOffsetPerQci;
    } // end 'list prioOffsetPerQci'
    leaf bothB2RscpEcnoCheck {
      description "Enables checking the second value - RSCP or Ecno - in a B2 measurement report.";
      yexte:takes-effect "New connection";
      yexte:dependencies "Mobility Control at Poor Coverage must be active.";
      type boolean;
      default false;
    }
    leaf a5MobilityTimerBr {
      description "Length of time eNodeB waits for reports from A3/A5 measurements configured in CAT-M UE for mobility reasons.";
      yexte:takes-effect "New connection";
      type erienmnrmlrat:ddt-Lrat_UeMeasControl_a5MobilityTimerBr;
      default 0;
    }
    leaf measQuantityUtraFDD {
      description "Measurement quantity used for all types of UTRA FDD measurements.";
      yexte:takes-effect "New connection";
      type erienmnrmlrat:enum-ThresholdUtra;
      default RSCP;
    }
    leaf ueMeasurementsActiveIF {
      description "Activates or deactivates EUTRAN inter-frequency measurements for mobility and soft lock of cells purposes when feature Mobility Control at Poor Coverage is enabled.";
      yexte:disturbances "Changing this attribute to false can cause loss of traffic. Blocks measurement based IF mobility.";
      yexte:takes-effect "New connection";
      type boolean;
      default true;
    }
    leaf excludeInterFreqAtCritical {
      description "If set, E-UTRA Inter-frequencies must be excluded when eNodeB selects the highest priority frequency at A2Critical.";
      yexte:takes-effect "New connection";
      yexte:dependencies "Feature Mobility Control at Poor Coverage must be active.";
      type boolean;
      default false;
    }
    leaf maxUtranCellsToMeasure {
      description "Defines the maximal number of UTRAN cells to perform mobility measurements upon.";
      type erienmnrmlrat:ddt-Lrat_UeMeasControl_maxUtranCellsToMeasure;
      default 32;
    }
    leaf bothInterA3RsrpRsrqCheck {
      description "Enables checking the second value - RSRQ or RSRP - in an inter-frequency A3 measurement report.";
      yexte:takes-effect "New connection";
      yexte:dependencies "Mobility Control at Poor Coverage must be active.";
      type boolean;
      default false;
    }
    leaf filterCoefficientRscpUtra {
      description "Filtering coefficient for UTRAN using measured quantity Received Signal Code Power (RSCP). The coefficient filters measurements before event evaluation.";
      yexte:takes-effect "New connection";
      type erienmnrmlrat:ddt-Lrat_UeMeasControl_filterCoefficientRscpUtra;
      default 4;
    }
    leaf ueMeasurementsActive {
      description "Activates or deactivates A3/A5/B2 measurements on EUTRAN inter-frequencies and on GERAN, UTRAN, CDMA2000 HRPD and CDMA2000 1xRtt frequencies for mobility purposes. This attribute also activates or deactivates A4/B1 measurements on EUTRAN inter-frequencies, GERAN and UTRAN frequencies for soft lock of cell purposes.\nNote that this parameter has no effect when feature Mobility Control at Poor Coverage is enabled.";
      yexte:disturbances "Changing this attribute to false can cause loss of traffic. Blocks outgoing measurement-based IF and IRAT mobility.";
      yexte:takes-effect "New connection";
      type boolean;
      default false;
    }
    leaf targetA2UlSearchOffset {
      description "Offset value above a1a2UlSearchThreshold that UL SINR in target cell must reach for handover to be allowed. Used when feature Uplink-Triggered Inter-Frequency Mobility is enabled. Configured in target cell.";
      yexte:takes-effect "New connection";
      type erienmnrmlrat:ddt-Lrat_UeMeasControl_targetA2UlSearchOffset;
      default 20;
    }
    leaf maxMeasUtraTdd {
      description "The number of measurements that can be concurrently performed by the UE on UTRA TDD measurement objects.";
      yexte:takes-effect "New connection";
      type erienmnrmlrat:ddt-Lrat_UeMeasControl_maxMeasUtraTdd;
      default 5;
    }
    leaf lowPrioMeasThresh {
      description "Frequency priority threshold to specify the low priority measurement group from connectedModeMobilityPrio or voicePrio in search zone. Those less than this threshold are put in low priority measurement group and can be configured after event A2OuterSearch is triggered from UE.";
      yexte:takes-effect "New connection";
      yexte:dependencies "Feature Mobility Control at Poor Coverage must be active.";
      type erienmnrmlrat:ddt-Lrat_UeMeasControl_lowPrioMeasThresh;
      default 0;
    }
    leaf bothIntraA3RsrpRsrqCheck {
      description "Enables checking the second value - RSRQ or RSRP - in an intra-frequency A3 measurement report.";
      yexte:takes-effect "New connection";
      yexte:dependencies "Mobility Control at Poor Coverage must be active.";
      type boolean;
      default false;
    }
    leaf checkA2SearchLevel {
      description "Disables or enables functionality of Level Based Search Zone Transitions. If enabled, eNodeB checks reported RSRP or RSRQ level of A2 Search or A2 Outer Search measurement to trigger measurement and mobility action.";
      yexte:takes-effect "New connection";
      yexte:dependencies "Feature Mobility Control at Poor Coverage must be active.";
      type boolean;
      default true;
    }
    leaf servOrPrioIFHoTimer {
      description "The length of time the eNodeB waits for measurement reports from the UE in the feature Service or Priority-triggered inter-freq Handover.";
      yexte:takes-effect "New connection";
      type erienmnrmlrat:ddt-Lrat_UeMeasControl_servOrPrioIFHoTimer;
      default 0;
    }
    leaf inhibitB2RsrqConfig {
      description "Disables or enables configuration of B2-RSRQ if event A2Search-RSRQ is triggered when the UE enters the search zone.";
      yexte:takes-effect "New connection";
      yexte:dependencies "This attribute is only effective when feature Mobility Control at Poor Coverage is activated.";
      type boolean;
      default false;
    }
    leaf bothB1RscpEcnoCheck {
      description "Enables checking the second value - RSCP or Ecno - in a B1 measurement report.";
      yexte:takes-effect "New connection";
      yexte:dependencies "Mobility Control at Poor Coverage must be active.";
      type boolean;
      default false;
    }
    leaf filterCoefficientEUtraNI {
      description "Filtering coefficient for noise and interference value measure in eNodeB and used in calculation of uplink SINR. Coefficient filters noise and interference samples used to compare uplink quality in source and potential target cell. The filter coefficient assumes a sample period of 200ms.";
      type erienmnrmlrat:ddt-Lrat_UeMeasControl_filterCoefficientEUtraNI;
      default 9;
    }
    leaf ueMeasurementsActiveBr {
      description "Activates A3/A5 measurements on E-UTRAN inter-frequencies for mobility purposes about CAT-M UE.";
      yexte:takes-effect "New connection";
      type boolean;
      default false;
    }
    leaf searchEffortTime {
      description "Time used in feature Mobility Control at Poor Coverage to determine if measured frequencies must be excluded for mobility action at critical threshold.\nSpecial value: 0 means infinity.\nIf ULTRIG is enabled, timer is also applicable for UL-triggered measurements.";
      type erienmnrmlrat:ddt-Lrat_UeMeasControl_searchEffortTime;
      default 40;
    }
    leaf maxNoMeasReportsInact {
      description "Maximal value of reports that any UE must provide any system functions, based on periodical measurements, that are used to measure on EUtran, Utran and Geran neighbors.\nSpecial Value: 0 means infinity.";
      yexte:disturbances "Changing this attribute can affect UE battery consumption and user throughput.";
      type erienmnrmlrat:ddt-Lrat_UeMeasControl_maxNoMeasReportsInact;
      default 1;
    }
    leaf filterCoefficientEUtraRsrp {
      description "The filtering coefficient for E-UTRA using the measured quantity Reference Signal Received Power (RSRP). The coefficient filters measurements before event evaluation.";
      yexte:takes-effect "New connection.";
      type erienmnrmlrat:ddt-Lrat_UeMeasControl_filterCoefficientEUtraRsrp;
      default 4;
    }
    leaf maxMeasEUtraOther {
      description "The number of measurements that can be concurrently performed by the UE on E-UTRA frequencies of a type (FDD - TDD) other than the serving cell frequency.";
      yexte:takes-effect "New connection";
      type erienmnrmlrat:ddt-Lrat_UeMeasControl_maxMeasEUtraOther;
      default 5;
    }
    leaf maxMeasGeran {
      description "The number of measurements that can be concurrently performed by the UE on GERAN measurement objects.";
      yexte:takes-effect "New connection";
      type erienmnrmlrat:ddt-Lrat_UeMeasControl_maxMeasGeran;
      default 5;
    }
    leaf sMeasure {
      description "Primary cell (PCell) quality threshold controlling whether or not the UE is required to perform measurements of intra-frequency, inter-frequency and inter-RAT neighboring cells.\nValue \"0\" indicates to disable s-Measure.\nCorresponds to s-Measure in TS 36.331.";
      yexte:disturbances "High values can stop outgoing HO.";
      yexte:takes-effect "New connection.";
      type erienmnrmlrat:ddt-Lrat_UeMeasControl_sMeasure;
      default 0;
    }
    leaf filterCoefficientEUtraRsrq {
      description "The filtering coefficient for E-UTRA using the measured quantity Reference Signal Received Quality (RSRQ). The coefficient filters measurements before event evaluation.";
      yexte:takes-effect "New connection.";
      type erienmnrmlrat:ddt-Lrat_UeMeasControl_filterCoefficientEUtraRsrq;
      default 11;
    }
    leaf ueMeasurementsActiveCDMA20001xRtt {
      description "Activates or deactivates CDMA 1xRtt measurements for mobility purposes when Mobility Control at Poor Coverage feature is enabled.";
      yexte:disturbances "Changing this attribute to false can cause loss of traffic. Blocks measurement based mobility to CDMA 1xRtt.";
      yexte:takes-effect "New connection";
      type boolean;
      default true;
    }
    leaf filterCoefficientEUtraUlSinrMax {
      description "Filtering coefficient for the UE UL-normalized Signal-to-Noise-Max measurements in eNodeB. The coefficient filters measurements before event evaluation.";
      type erienmnrmlrat:ddt-Lrat_UeMeasControl_filterCoefficientEUtraUlSinrMax;
      default 11;
    }
    leaf ueMeasurementsActiveGERAN {
      description "Activates or deactivates GERAN measurements for mobility and soft lock of cells purposes when feature Mobility Control at Poor Coverage is enabled.";
      yexte:disturbances "Changing this attribute to false can cause loss of traffic. Blocks measurement based mobility to GERAN.";
      yexte:takes-effect "New connection";
      type boolean;
      default true;
    }
    leaf ueMeasurementsActiveCDMA2000 {
      description "Activates or deactivates CDMA2000 measurements for mobility purposes when Mobility Control at Poor Coverage feature is enabled.";
      yexte:disturbances "Changing this attribute to false can cause loss of traffic. Blocks measurement based mobility to CDMA2000.";
      yexte:takes-effect "New connection";
      type boolean;
      default true;
    }
    leaf a3SuspendCsgTimer {
      description "The length of time the eNodeB discards A3 measurement report for CSG or Hybrid CSG cells from UE. If 0, timer is not started.";
      yexte:takes-effect "New connection";
      type erienmnrmlrat:ddt-Lrat_UeMeasControl_a3SuspendCsgTimer;
      default 0;
    }
    leaf a5B2MobilityTimer {
      description "Length of time the eNodeB waits for reports from A3/A5/B2 measurements configured in UE for mobility reasons.\nIf 0, timer is not started.\nIf ULTRIG is enabled, timer is also applicable for UL-triggered measurements.";
      yexte:takes-effect "New connection";
      type erienmnrmlrat:ddt-Lrat_UeMeasControl_a5B2MobilityTimer;
      default 0;
    }
    leaf maxMeasInterFreqEUtra {
      description "The number of measurements that can be concurrently performed by the UE on E-UTRA frequencies other than the serving cell frequency.";
      yexte:takes-effect "New connection";
      type erienmnrmlrat:ddt-Lrat_UeMeasControl_maxMeasInterFreqEUtra;
      default 7;
    }
    leaf allowReleaseQci1 {
      description "This attribute specifies whether or not blind and measurement-based Release of a User Equipment (UE) with a QCI1 bearer is allowed.";
      type boolean;
      default false;
    }
    leaf filterCoefficientEcnoUtra {
      description "Filtering coefficient for UTRAN using measured quantity ratio of energy per modulation bit to noise spectral density (Ecno). The coefficient filters measurements before event evaluation.";
      yexte:takes-effect "New connection";
      type erienmnrmlrat:ddt-Lrat_UeMeasControl_filterCoefficientEcnoUtra;
      default 4;
    }
    leaf maxMeasCdma20001xRtt {
      description "Number of measurements that can be concurrently performed by the UE on CDMA2000 1xRTT measurement objects";
      yexte:takes-effect "New connection";
      type erienmnrmlrat:ddt-Lrat_UeMeasControl_maxMeasCdma20001xRtt;
      default 3;
    }
    leaf ulSinrOffset {
      description "Offset value above UL SINR in source cell that estimated UL SINR in target cell must reach for handover to be allowed. Used when feature UL-Triggered Inter-Frequency Mobility is enabled. Configured in source cell.";
      yexte:takes-effect "New connection";
      type erienmnrmlrat:ddt-Lrat_UeMeasControl_ulSinrOffset;
      default 30;
    }
    leaf bothA5RsrpRsrqCheck {
      description "This attribute is used to turn on/off the functionality for checking the second value - RSRP or RSRQ - in an A5 Target Good Enough measurement report triggered by RSRQ or RSRP respectively.";
      yexte:takes-effect "New connection";
      yexte:dependencies "Feature Mobility Control at Poor Coverage must be active.";
      type boolean;
      default false;
    }
    leaf a3MobilityTimerBr {
      description "Length of time eNodeB waits for reports from A3 measurements configured in CAT-M UE for intra frequency mobility. If 0, timer is not started.";
      yexte:takes-effect "New connection";
      type erienmnrmlrat:ddt-Lrat_UeMeasControl_a3MobilityTimerBr;
      default 0;
    }
    leaf ueMeasurementsActiveUTRAN {
      description "Activates or deactivates UTRAN measurements for mobility and soft lock of cells purposes when feature Mobility Control at Poor Coverage is enabled.";
      yexte:disturbances "Changing this attribute to false can cause loss of traffic. Blocks measurement based mobility to UTRAN.";
      yexte:takes-effect "New connection";
      type boolean;
      default true;
    }
    leaf intraFreqMeasModeBr {
      description "Intra-frequency measurement configuration mode for CAT-M UE which requires measurement gaps for intra-frequency measurement.";
      yexte:takes-effect "New connection";
      type erienmnrmlrat:enum-MeasureModeBr;
      default PUSCH_SINR_BASED;
    }
  } // end 'grouping moc-UeMeasControl'
  grouping moc-UlCompGroup-keys {
    description "Key(s) for MOC UlCompGroup";
    leaf id {
      erienmyext:no-notification;
      description "The value component of the Relative Distinguished Name (RDN).";
      mandatory true;
      yexte:ecim-name ulCompGroupId;
      type string;
    }
  } // end 'grouping moc-UlCompGroup-keys'
  grouping moc-UlCompGroup {
    description "Defines a set of sectorCarriers. Uplink Coordinated multi-point reception of antenna signals is possible only between antenna signals from sectorCarriers within the same set of sectorCarriers.";
    leaf administrativeState {
      description "The administrative state.\nNote: If this attribute is set to SHUTTING_DOWN, it will immediately go into the state LOCKED.";
      yexte:disturbances "Changing this attribute to LOCKED or SHUTTINGDOWN disables UL CoMP.";
      type erienmnrmlrat:enum-AdmState;
      default LOCKED;
    }
    leaf-list availabilityStatus {
      min-elements 0;
      config false;
      description "The availability status. It contains details about operationalState. This attribute is set by the application in the RBS.";
      notife:notifiable-state-data true;
      type erienmnrmlrat:enum-AvailStatus;
    }
    leaf operationalState {
      config false;
      description "The operational state. This attribute is set by the application in the RBS.";
      notife:notifiable-state-data true;
      type erienmnrmlrat:enum-OperState;
    }
    leaf-list sectorCarrierRef {
      min-elements 1;
      max-elements 600;
      description "Defines a set of sectorCarriers. Uplink Coordinated multi-point reception of antenna signals is possible only between antenna signals from sectorCarriers within the same set of sectorCarriers. There shall be at least one sectorCarrier per UlCompGroup.";
      yexte:takes-effect "Object enabled";
      erienmyext:enm-type MOREF;
      type string;
    }
  } // end 'grouping moc-UlCompGroup'
  grouping moc-PtmResOpUseConfig-keys {
    description "Key(s) for MOC PtmResOpUseConfig";
    leaf id {
      erienmyext:no-notification;
      description "The value component of the RDN.";
      mandatory true;
      yexte:ecim-name ptmResOpUseConfigId;
      type string;
    }
  } // end 'grouping moc-PtmResOpUseConfig-keys'
  grouping moc-PtmResOpUseConfig {
    description "Contains PTM specific parameters affecting Cell Reserved For Operator Use functionality.\n\nThe RDN of this MO is PtmResOpUseConfig=1.";
    leaf unresMsrUsageThreshold {
      description "If Monitored System Resources use is below threshold and subscription ratio is below unresSRatioThreshold, it has the following effects:\n- PLMN IDs specified in ptmSubscriberGroupRef are broadcast as Unreserved.\n- Incoming HOs of users with SPIDs specified in ptmSubscriberGroupRef are allowed.\nNo effect when PtmCellProfile::cellType is set to NON_PRIORITY.";
      yexte:disturbances "Changing this attribute can affect traffic.";
      yexte:dependencies resMsrUsageThreshold>=unresMsrUsageThreshold;
      type erienmnrmlrat:ddt-Lrat_PtmResOpUseConfig_unresMsrUsageThreshold;
      default 40;
    }
    leaf-list ptmSubscriberGroupRef {
      min-elements 0;
      max-elements 12;
      description "Reference to an instance of PtmSubscriberGroup MO Class.\nPTM Subscriber Groups affected by Cell Reserved For Operator Use.\nIf empty, functionality is disabled.\nNo effect when PtmCellProfile::cellType is set to NON_PRIORITY.";
      yexte:disturbances "Changing this attribute can affect traffic.";
      erienmyext:enm-type MOREF;
      type string;
    }
    leaf resMsrUsageThreshold {
      description "If Monitored System Resources exceed threshold on a cell, it has the following effects:\n- PLMN IDs specified in ptmSubscriberGroupRef are broadcast as Reserved for Operator Use.\n- Incoming HOs of users with SPIDs specified in ptmSubscriberGroupRef are blocked.\nNo effect when PtmCellProfile::cellType is set to NON_PRIORITY.";
      yexte:disturbances "Changing this attribute can affect traffic.";
      yexte:dependencies resMsrUsageThreshold>=unresMsrUsageThreshold;
      type erienmnrmlrat:ddt-Lrat_PtmResOpUseConfig_resMsrUsageThreshold;
      default 70;
    }
    leaf unresSRatioThreshold {
      description "If subscription ratio is below threshold, and usage of all Monitored System Resources is below unresMsrUsageThreshold, it has the following effects:\n- PLMN IDs specified in ptmSubscriberGroupRef are broadcast as Unreserved.\n- Incoming HOs of users with SPIDs specified in ptmSubscriberGroupRef are allowed.\nNo effect when PtmCellProfile::cellType is set to NON_PRIORITY.";
      yexte:disturbances "Changing this attribute can affect traffic.";
      yexte:dependencies resSRatioThreshold>=unresSRatioThreshold;
      type erienmnrmlrat:ddt-Lrat_PtmResOpUseConfig_unresSRatioThreshold;
      default 55;
    }
    leaf resSRatioThreshold {
      description "If subscription ratio on a cell exceeds threshold, it has following effects:\n- PLMN IDs specified in ptmSubscriberGroupRef are broadcast as Reserved for Operator Use.\n- Incoming HOs of users with SPIDs specified in ptmSubscriberGroupRef are blocked.\nNo effect when PtmCellProfile::cellType is set to NON_PRIORITY.";
      yexte:disturbances "Changing this attribute can affect traffic.";
      yexte:dependencies resSRatioThreshold>=unresSRatioThreshold;
      type erienmnrmlrat:ddt-Lrat_PtmResOpUseConfig_resSRatioThreshold;
      default 70;
    }
  } // end 'grouping moc-PtmResOpUseConfig'
  grouping moc-ReportConfigEUtraIFA3UlTrig-keys {
    description "Key(s) for MOC ReportConfigEUtraIFA3UlTrig";
    leaf id {
      erienmyext:no-notification;
      description "The value component of the RDN.";
      mandatory true;
      yexte:ecim-name reportConfigEUtraIFA3UlTrigId;
      type string;
    }
  } // end 'grouping moc-ReportConfigEUtraIFA3UlTrig-keys'
  grouping moc-ReportConfigEUtraIFA3UlTrig {
    description "Contains report configuration settings for the A3 event for inter-frequency LTE measurements initiated by Uplink-Triggered Inter-Frequency Mobility.\n\nThe RDN of this MO is ReportConfigEUtraIFA3UlTrig=1.";
    leaf a3Offset {
      description "The offset value for event A3.";
      yexte:takes-effect "New connection";
      type erienmnrmlrat:ddt-Lrat_ReportConfigEUtraIFA3UlTrig_a3Offset;
      default 0;
    }
    leaf hysteresisA3 {
      description "The hysteresis value for event A3.";
      yexte:takes-effect "New connection";
      type erienmnrmlrat:ddt-Lrat_ReportConfigEUtraIFA3UlTrig_hysteresisA3;
      default 10;
    }
    leaf reportIntervalA3 {
      description "The interval for event triggered periodical reporting.";
      yexte:takes-effect "New connection";
      type erienmnrmlrat:enum-ReportInterval;
      default MS_2048;
    }
    leaf timeToTriggerA3 {
      description "Time-to-trigger value for event A3.";
      yexte:takes-effect "New connection";
      type erienmnrmlrat:ddt-Lrat_ReportConfigEUtraIFA3UlTrig_timeToTriggerA3;
      default 40;
    }
  } // end 'grouping moc-ReportConfigEUtraIFA3UlTrig'
  grouping moc-PmUeMeasControl-keys {
    description "Key(s) for MOC PmUeMeasControl";
    leaf id {
      erienmyext:no-notification;
      description "The value component of the Relative Distinguished Name (RDN).\n";
      mandatory true;
      yexte:ecim-name pmUeMeasControlId;
      type string;
    }
  } // end 'grouping moc-PmUeMeasControl-keys'
  grouping moc-PmUeMeasControl {
    description "This managed object contains the settings for PM Initiated UE Measurements.\n";
    container ueMeasInterRat2 {
      description "Specification of UE measurement initiated when PM event UE_MEAS_GERAN2 or UE_MEAS_UTRAN2 is activated in cell trace or UE trace scanner.";
      erienmyext:enm-type STRUCT;
      uses erienmnrmlrat:struct-PmUeMeasInterRat;
    } // end 'container ueMeasInterRat2'
    container ueMeasInterFreq2 {
      description "Specification of UE measurement initiated when PM event UE_MEAS_INTERFREQ2 is activated in cell trace or UE trace scanner.";
      erienmyext:enm-type STRUCT;
      uses erienmnrmlrat:struct-PmUeMeasInterFreq;
    } // end 'container ueMeasInterFreq2'
    container ueMeasInterRat1 {
      description "Specification of UE measurement initiated when PM event UE_MEAS_GERAN1 or UE_MEAS_UTRAN1 is activated in cell trace scanner.";
      erienmyext:enm-type STRUCT;
      uses erienmnrmlrat:struct-PmUeMeasInterRat;
    } // end 'container ueMeasInterRat1'
    leaf measQuantityUtraFDDPm {
      status deprecated {
        yexte:status-information "Since L17A. Has no functional behavior. Planned to be removed.";
      }
      description "Measurement quantity used for all types of UTRA FDD measurements.";
      yexte:takes-effect "New connection";
      type erienmnrmlrat:enum-ThresholdUtra;
      default RSCP;
    }
    container ueMeasIntraFreq1 {
      description "The specification of the UE measurement initiated by activating the PM event UE_MEAS_INTRAFREQ1 in a Cell Trace scanner.\n";
      erienmyext:enm-type STRUCT;
      uses erienmnrmlrat:struct-PmUeMeasIntraFreq;
    } // end 'container ueMeasIntraFreq1'
    container ueMeasIntraFreq2 {
      description "The specification of the UE measurement initiated by activating the PM event UE_MEAS_INTRAFREQ2 in a Cell Trace or UE Trace scanner.\n";
      erienmyext:enm-type STRUCT;
      uses erienmnrmlrat:struct-PmUeMeasIntraFreq;
    } // end 'container ueMeasIntraFreq2'
    container ueMeasInterFreq1 {
      description "Specification of UE measurement initiated when PM event UE_MEAS_INTERFREQ1 is activated in cell trace scanner.";
      erienmyext:enm-type STRUCT;
      uses erienmnrmlrat:struct-PmUeMeasInterFreq;
    } // end 'container ueMeasInterFreq1'
    leaf measGapAllowedPm {
      description "Whether or not measurement gap configuration is allowed for EUTRAN inter-frequency and IRAT measurements.";
      yexte:takes-effect "New connection";
      type boolean;
      default false;
    }
  } // end 'grouping moc-PmUeMeasControl'
  grouping moc-AnrFunctionGeran-keys {
    description "Key(s) for MOC AnrFunctionGeran";
    leaf id {
      erienmyext:no-notification;
      description "The value component of the Relative Distinguished Name (RDN).";
      mandatory true;
      yexte:ecim-name anrFunctionGeranId;
      type string;
    }
  } // end 'grouping moc-AnrFunctionGeran-keys'
  grouping moc-AnrFunctionGeran {
    description "Parameters and constraints for GERAN ANR functions.\n\nThe RDN of this MO is AnrFunctionGeran=1.";
    leaf anrGeranMeasReportRacIncr {
      description "Defines the increase in the target number of measurement reports for each GeranFreqGroupRelation each time a PCI measurement report is received with known cell but the corresponding RAC missing.\nPlease note that the unit is decMeasurementReport. Thus, the given number of measurement reports will be divided by 10.";
      type erienmnrmlrat:ddt-Lrat_AnrFunctionGeran_anrGeranMeasReportRacIncr;
      default 20;
    }
    leaf rimIntegrationEnabled {
      description "This parameter indicates if ANR should be able to modify RIM associations to GERAN cells";
      type boolean;
      default true;
    }
    leaf anrGeranMeasReportIncr {
      description "Defines the increase in the target number of measurement reports per GeranFrequencyGroupRelation each time an Automated Neighbor Relations (ANR) GERAN measurement report is received with unknown neighbor GERAN cells or an unknown cell found in GERAN mobility report.\nPlease note that the unit is decMeasurementReport. Thus, the given number of measurement reports will be divided by 10.";
      type erienmnrmlrat:ddt-Lrat_AnrFunctionGeran_anrGeranMeasReportIncr;
      default 10;
    }
    leaf anrGeranMeasReportDecr {
      description "The decrease in the target number of measurement reports per GeranFrequencyGroupRelation each time an Automated Neighbor Relations (ANR) GERAN measurement report is received with only known neighbor cells.\nPlease note that the unit is decMeasurementReport. Thus, the given number of measurement reports will be divided by 10.";
      type erienmnrmlrat:ddt-Lrat_AnrFunctionGeran_anrGeranMeasReportDecr;
      default 1;
    }
    leaf anrGeranMeasReportMin {
      description "The minimum target number of measurement reports per hour for each GeranFrequencyGroupRelation. The number of measurement reports may deviate from the target.\nPlease note that the unit is decMeasurementReport. Thus, the given number of measurement reports will be divided by 10.";
      type erienmnrmlrat:ddt-Lrat_AnrFunctionGeran_anrGeranMeasReportMin;
      default 5;
    }
    leaf anrStateGsm {
      description "Activates or deactivates the Automated Neighbor Relations (ANR) function support for GSM for one RBS. The value of the attribute is irrelevant when no valid license key is installed for the ANR feature.";
      type erienmnrmlrat:enum-ActivationVals;
      default DEACTIVATED;
    }
    leaf anrGeranMeasReportMax {
      description "The maximum target number of measurement reports per hour for each GeranFrequencyGroupRelation. The number of measurement reports may deviate from the target.\nPlease note that the unit is decMeasurementReport. Thus, the given number of measurement reports will be divided by 10.";
      type erienmnrmlrat:ddt-Lrat_AnrFunctionGeran_anrGeranMeasReportMax;
      default 100;
    }
    leaf anrGeranRacMeasOn {
      description "Indicates whether more CGI measurements shall be initiated to find RAC for cells that were previously added by ANR with missing RAC.\n";
      type boolean;
      default true;
    }
  } // end 'grouping moc-AnrFunctionGeran'
  grouping moc-ExternalUtranCellFDD-keys {
    description "Key(s) for MOC ExternalUtranCellFDD";
    leaf id {
      erienmyext:no-notification;
      description "The value component of the Relative Distinguished Name (RDN).";
      mandatory true;
      yexte:ecim-name externalUtranCellFDDId;
      type string;
    }
  } // end 'grouping moc-ExternalUtranCellFDD-keys'
  grouping moc-ExternalUtranCellFDD {
    description "This Managed Object contains a UTRAN cell for Frequency Division Duplex (FDD).";
    leaf userLabel {
      description "Label for free use.";
      type erienmnrmlrat:ddt-Lrat_ExternalUtranCellFDD_userLabel;
    }
    leaf rimAssociationStatus {
      config false;
      description "This parameter indicates the current status of the RIM association to this external cell.";
      notife:notifiable-state-data true;
      type erienmnrmlrat:enum-RIMAssociationStatus;
    }
    leaf timeOfCreation {
      erienmyext:no-notification;
      config false;
      description "Indicates the time and date when the MO was created by the Automated Neighbor Relations (ANR) function or operator. Format: YYYY-MM-DD HH:MM:SS";
      type erienmnrmlrat:ddt-Lrat_ExternalUtranCellFDD_timeOfCreation;
    }
    leaf masterUtranCellId {
      description "The identity of the UtranCell represented by this MO, particularly for automatically created ExternalUtranCell managed objects. The masterUtranCellId is set to the Full Distinguished Name (FDN).";
      type erienmnrmlrat:ddt-Lrat_ExternalUtranCellFDD_masterUtranCellId;
      default "";
    }
    container cellIdentity {
      description "UTRAN Cell Identity.\nUsed to identity the cell uniquely within UTRAN Iu mode.";
      erienmyext:enm-type STRUCT;
      uses erienmnrmlrat:struct-CellIdentityUtra;
    } // end 'container cellIdentity'
    leaf physicalCellIdentity {
      description "Indicates the physical layer identity of the cell, that is, the primary scrambling code.";
      mandatory true;
      yexte:takes-effect "New connection";
      type erienmnrmlrat:ddt-Lrat_ExternalUtranCellFDD_physicalCellIdentity;
    }
    leaf timeOfLastModification {
      config false;
      description "The date and time when the MO was last modified by the Automated Neighbor Relations (ANR) function or operator. Format: YYYY-MM-DD HH:MM:SS";
      notife:notifiable-state-data true;
      type erienmnrmlrat:ddt-Lrat_ExternalUtranCellFDD_timeOfLastModification;
    }
    leaf lac {
      description "The Location Area Code of the external UTRAN cell. A fixed-length code identifying the location area within a PLMN. Refer to 3GPP TS 23.003.\nThe value 0 of the attribute is used to mark invalid/unusable lac information for the cell. For example, handover to an external UTRAN cell (that is part of a Utran cell relation) can be considered only if the value of the lac attribute is NOT 0.";
      yexte:disturbances "Changes may affect traffic";
      type erienmnrmlrat:ddt-Lrat_ExternalUtranCellFDD_lac;
      default 0;
    }
    leaf lbUtranCellOffloadCapacity {
      description "Offload subscription capacity associated with the UTRAN target cell\nThe value is used to moderate the offload rate to the UTRAN target cell.";
      yexte:disturbances "Changing this attribute can cause loss of traffic.";
      type erienmnrmlrat:ddt-Lrat_ExternalUtranCellFDD_lbUtranCellOffloadCapacity;
      default 1000;
    }
    leaf rimCapable {
      description "This parameter indicates if the external UTRAN cell is RIM capable. If the value is RIMIncapable, no attempt will be made to create a RIM association to the external UTRAN cell, other values will result in a attempt to create a RIM association.";
      yexte:disturbances "If the value is other than RIMIncapable the eNB will try to set up a RIM association to the external cell";
      type erienmnrmlrat:enum-RIMCapability;
      default RIM_CAPABLE;
    }
    leaf createdBy {
      erienmyext:no-notification;
      config false;
      description "Indicates whether the MO has been created by the Automated Neighbor Relations (ANR) function or operator.";
      type erienmnrmlrat:enum-CreatedByIrat;
    }
    leaf rac {
      description "The Routing Area Code of a routing area.\nThe value -1 of the attribute is used to mark that the optional RAC IE should NOT be sent in the Target ID IE of the HANDOVER REQUIRED S1 message. Refer to 3GPP TS 36.413.";
      yexte:disturbances "Changes may affect traffic";
      type erienmnrmlrat:ddt-Lrat_ExternalUtranCellFDD_rac;
      default -1;
    }
    leaf isRemoveAllowed {
      description "Indicates if the Automated Neighbor Relations (ANR) function is allowed to remove this object. It does not restrict operator removal of the object. Objects created by ANR have this parameter set to true initially.";
      type boolean;
      default false;
    }
    leaf srvccCapability {
      description "Describes the SRVCC capability of the external cell.";
      type erienmnrmlrat:enum-SrvccCapability;
      default NOT_SUPPORTED;
    }
    container plmnIdentity {
      description "PLMN ID supported by the cell.\n";
      erienmyext:enm-type STRUCT;
      uses erienmnrmlrat:struct-PlmnIdentity;
    } // end 'container plmnIdentity'
    leaf-list reservedBy {
      min-elements 0;
      config false;
      description "Contains a list of MO instances that reserve this MO instance.";
      notife:notifiable-state-data true;
      erienmyext:enm-type MOREF;
      type string;
    }
    leaf lastModification {
      config false;
      description "Indicates whether the MO has been last modified by the Automated Neighbor Relations (ANR) function or operator.";
      notife:notifiable-state-data true;
      type erienmnrmlrat:enum-LastModificationUtran;
    }
    action changeFrequency {
      description "Changes the frequency of the external cell. This MO action includes the following steps:\n- Create the UtranFrequency MO (with the specified arfcnValueUtranDl) if it does not already exist.\n- Create the UtranFreqRelation MO (with the same attribute values as the existing UtranFreqRelation MO) if it does not already exist.\n- Create a new ExternalUtranCellFDD MO (with the same attribute values as the existing ExternalUtranCellFDD MO) under the specified UtranFrequency MO.\n- For each UtranCellRelation to the old ExternalUtranCellFDD, create a new UtranCellRelation MO (with the same attribute values as the existing UtranCellRelation MO) referring to the new ExternalUtranCellFDD MO. The old UtranCellRelation MOs are then removed.\n- Remove the old ExternalUtranCellFDD MO. This will be performed after successful execution of this MO action. ";
      input {
        leaf arfcnValueUtranDl {
          mandatory true;
          description "The new DL frequency for this cell.";
          type erienmnrmlrat:ddt-ExternalUtranCellFDD_changeFrequency_arfcnValueUtranDl;
        }
      }
    }
  } // end 'grouping moc-ExternalUtranCellFDD'
  grouping moc-LogicalChannelGroup-keys {
    description "Key(s) for MOC LogicalChannelGroup";
    leaf id {
      erienmyext:no-notification;
      description "The value component of the Relative Distinguished Name (RDN). Valid values for this MO type are: 0, 1, 2, or 3. The values correspond to logical channel group IDs in 3GPP TS 36.321.";
      mandatory true;
      yexte:ecim-name logicalChannelGroupId;
      type string;
    }
  } // end 'grouping moc-LogicalChannelGroup-keys'
  grouping moc-LogicalChannelGroup {
    description "Represents QoS configuration related to a Logical Channel group.\n\nThe RDNs of these MOs are LogicalChannelGroup=0 to LogicalChannelGroup=3.";
    leaf userLabel {
      description "Label for free use.\n";
      type erienmnrmlrat:ddt-Lrat_LogicalChannelGroup_userLabel;
    }
    leaf-list reservedBy {
      min-elements 0;
      config false;
      description "Contains a list of QciProfile instances that reserve this MO instance.\n";
      yexte:takes-effect "New connection.";
      notife:notifiable-state-data true;
      erienmyext:enm-type MOREF;
      type string;
    }
  } // end 'grouping moc-LogicalChannelGroup'
  grouping moc-Cdma20001xRttFreqRelation-keys {
    description "Key(s) for MOC Cdma20001xRttFreqRelation";
    leaf id {
      erienmyext:no-notification;
      description "Value component of the RDN";
      mandatory true;
      yexte:ecim-name cdma20001xRttFreqRelationId;
      type string;
    }
  } // end 'grouping moc-Cdma20001xRttFreqRelation-keys'
  grouping moc-Cdma20001xRttFreqRelation {
    description "The MO represents a mobility relation between an EUtranCellFDD or an EUtranCellTDD and a Cdma20001xRTTFreq. It contains parameters that are specific for this relation.";
    leaf b2Thr2Cdma20001xFreqOffset {
      description "The frequency-relation specific offset for the absolute threshold b2Threshold2Cdma20001xRtt, Signal quality in the thresholdCDMA2000 for event B2, used for Multi-Layer Service-Triggered Mobility.";
      yexte:takes-effect "Ongoing connection";
      type erienmnrmlrat:ddt-Lrat_Cdma20001xRttFreqRelation_b2Thr2Cdma20001xFreqOffset;
      default 0;
    }
    leaf userLabel {
      description "Label for free use";
      type erienmnrmlrat:ddt-Lrat_Cdma20001xRttFreqRelation_userLabel;
    }
    leaf b2Thr1RsrqCdma20001xFreqOffset {
      description "The frequency-relation specific offset for the absolute threshold b2Threshold1Rsrq, RSRQ threshold1 for event B2, used for Multi-Layer Service-Triggered Mobility.";
      yexte:takes-effect "Ongoing connection";
      type erienmnrmlrat:ddt-Lrat_Cdma20001xRttFreqRelation_b2Thr1RsrqCdma20001xFreqOffset;
      default 0;
    }
    leaf csFallbackPrio {
      description "CDMA2000 1xRTT CSFB frequency priority.\nThis attribute prioritizes CDMA2000 1xRTT frequencies among all frequencies related to the cell for UEs in connected mode.\nSets the priority to which frequency/frequency group to make CS Fallback.\nThe value 0 means the lowest priority.\nThe value 7 means the highest priority.";
      yexte:takes-effect "New connection";
      type erienmnrmlrat:ddt-Lrat_Cdma20001xRttFreqRelation_csFallbackPrio;
      default 0;
    }
    leaf b2Thr1RsrpCdma20001xFreqOffset {
      description "The frequency-relation specific offset for the absolute threshold b2Threshold1Rsrp, RSRP threshold1 for event B2, used for Multi-Layer Service-Triggered Mobility.";
      yexte:takes-effect "Ongoing connection";
      type erienmnrmlrat:ddt-Lrat_Cdma20001xRttFreqRelation_b2Thr1RsrpCdma20001xFreqOffset;
      default 0;
    }
    leaf voicePrio {
      description "This attribute prioritizes CDMA 1xRtt frequencies among all frequencies related to the cell for User Equipments (UEs) in connected mode. It sets the priority value for the frequency to which the mobility action for a voice session is performed.\nThe value -1 means the frequency is excluded.\nThe value 0 means the lowest priority.\nThe value 7 means the highest priority.";
      yexte:takes-effect "New connection";
      type erienmnrmlrat:ddt-Lrat_Cdma20001xRttFreqRelation_voicePrio;
      default 0;
    }
    leaf cdma2000FreqRef {
      yexte:restricted;
      description "Reference to the Cdma2000Freq MO";
      mandatory true;
      yexte:takes-effect "New connection";
      erienmyext:enm-type MOREF;
      type string;
    }
    leaf csFallbackPrioEC {
      description "CDMA2000 1xRTT frequency priority for emergency calls\nThis attribute prioritizes CDMA2000 1xRTT frequencies for emergency calls among all frequencies/frequency groups related to the cell for UEs in connected mode.\nSets the priority to which frequency to make emergency call CS Fallback.\nThe value 0 means the lowest priority.\nThe value 7 means the highest priority.";
      yexte:takes-effect "New connection";
      type erienmnrmlrat:ddt-Lrat_Cdma20001xRttFreqRelation_csFallbackPrioEC;
      default 0;
    }
    leaf qOffsetFreq {
      description "Frequency-specific offset to apply when evaluating triggering conditions for measurement reporting";
      yexte:takes-effect "New connection";
      type erienmnrmlrat:ddt-Lrat_Cdma20001xRttFreqRelation_qOffsetFreq;
      default 0;
    }
  } // end 'grouping moc-Cdma20001xRttFreqRelation'
  grouping moc-Cdma20001xRttCellRelation-keys {
    description "Key(s) for MOC Cdma20001xRttCellRelation";
    leaf id {
      erienmyext:no-notification;
      description "Value component of the RDN";
      mandatory true;
      yexte:ecim-name cdma20001xRttCellRelationId;
      type string;
    }
  } // end 'grouping moc-Cdma20001xRttCellRelation-keys'
  grouping moc-Cdma20001xRttCellRelation {
    description "The MO represents a mobility relation between an EUtranCellFDD or an EUtranCellTDD and a Cdma20001xRTTCell. It contains parameters that are specific for this relation.";
    leaf externalCdma20001xRttCellRef {
      yexte:restricted;
      description "Reference to an ExternalCdma20001xRttCell";
      mandatory true;
      yexte:takes-effect "New connection";
      erienmyext:enm-type MOREF;
      type string;
    }
    leaf includeInSystemInformation {
      description "CDMA2000 cell inclusion in system information.\nThis attribute indicates whether the CDMA2000 cell is included in System Information.\nWhen the value is set to false, the CDMA2000 cell is not included in SIB8.\nA maximum of 16 CDMA2000 cells can be included per frequency.\nA maximum of 32 CDMA2000 cells can be included in SIB8.";
      yexte:dependencies "Restriction: The referred cell shall only set one of the attributes (includeInSystemInformation or includeInSystemInformationRel9) to true.";
      type boolean;
      default true;
    }
    leaf userLabel {
      description "Label for free use";
      type erienmnrmlrat:ddt-Lrat_Cdma20001xRttCellRelation_userLabel;
    }
    leaf includeInSystemInformationRel9 {
      description "CDMA2000 cell inclusion in Release 9 part of system information.\nThis attribute indicates whether the CDMA2000 cell is included in the Release 9 part of System Information.\nWhen the value is set to false, the CDMA2000 cell is not included in the Release 9 part of SIB8.\nA release 8 relation of the same frequency is required for the CDMA2000 cell to be included in the Release 9 part of SIB8.\nA total maximum of 40 1xRTT CDMA2000 cells (release 8 and 9 combined) can be included in SIB8.";
      yexte:dependencies "Restriction: The referred cell shall only set one of the attributes (includeInSystemInformation or includeInSystemInformationRel9) to true.\nDependencies: In 3GPP rel9, the possibility to add 16 additional CDMA2000 cells on the same frequency, was added. The additional CDMA2000 cells are controlled by the parameter includeInSystemInformationRel9.";
      type boolean;
      default false;
    }
  } // end 'grouping moc-Cdma20001xRttCellRelation'
  grouping moc-PtmIfoConfig-keys {
    description "Key(s) for MOC PtmIfoConfig";
    leaf id {
      erienmyext:no-notification;
      description "The value component of the RDN.";
      mandatory true;
      yexte:ecim-name ptmIfoConfigId;
      type string;
    }
  } // end 'grouping moc-PtmIfoConfig-keys'
  grouping moc-PtmIfoConfig {
    description "Contains PTM specific parameters affecting Inter-Frequency Offload feature.\n\nThe RDN of this MO is PtmIfoConfig=1.";
    leaf-list ptmSubscriberGroupRef {
      min-elements 0;
      max-elements 12;
      description "Reference to an instance of PtmSubscriberGroup MO Class.\nOrder of PTM Subscriber Group offload from cell, using IFO feature.\nUEs not assigned to any group are offloaded in first group.\nIf list is empty, functionality is disabled.\nNo effect when PtmCellProfile::cellType is set to NON_PRIORITY.";
      yexte:disturbances "Changing this attribute can affect traffic.";
      erienmyext:enm-type MOREF;
      type string;
    }
  } // end 'grouping moc-PtmIfoConfig'
  grouping moc-ResourcePartition-keys {
    description "Key(s) for MOC ResourcePartition";
    leaf id {
      erienmyext:no-notification;
      description "The value component of the RDN.";
      mandatory true;
      yexte:ecim-name resourcePartitionId;
      type string;
    }
  } // end 'grouping moc-ResourcePartition-keys'
  grouping moc-ResourcePartition {
    description "A combination of attributes which specify the resource partition a given UE should be included in.";
    leaf partitionName {
      status deprecated {
        yexte:status-information "Since L17A. Has no functional behavior. Planned to be removed.";
      }
      description "The name of the resource partition.";
      yexte:takes-effect "Cell lock/unlock";
      type string;
      default "";
    }
    leaf-list spidList {
      min-elements 0;
      max-elements 20;
      description "Specifies which SPID values shall be included in the resource partition. A partition with a spidList containing the value 0 will include UEs with no defined SPID value. A partition configured with an empty spidList will include all UE's with a spid value not appearing in any other partition in the ResourcePartitionGroup.";
      yexte:disturbances "Changing this attribute can affect traffic.";
      yexte:takes-effect "Cell lock/unlock";
      yexte:dependencies "Can only be configured if plmnList is empty.";
      type erienmnrmlrat:ddt-Lrat_ResourcePartition_spidList;
    }
    leaf partitionId {
      description "Resource partition ID.";
      yexte:takes-effect "Next cell unlock";
      yexte:dependencies "Unique id among all ResourcePartition MOs.";
      type erienmnrmlrat:ddt-Lrat_ResourcePartition_partitionId;
      default 0;
    }
    leaf-list reservedBy {
      min-elements 0;
      config false;
      description "Contains a list of MO instances that reserve this MO instance.";
      yexte:dependencies "The MO may not be deleted if it is reserved.";
      notife:notifiable-state-data true;
      erienmyext:enm-type MOREF;
      type string;
    }
    list plmnList {
      min-elements 0;
      max-elements 6;
      key auto-generated-struct-key;
      leaf auto-generated-struct-key {
        type uint16;
        description "This leaf has been injected to allow for struct instances in a sequence to be ordered.";
        mandatory true;
      }
      description "Specifies which PLMNs shall be included in the resource partition.";
      erienmyext:enm-type STRUCT;
      uses erienmnrmlrat:struct-PlmnIdentity;
    } // end 'list plmnList'
  } // end 'grouping moc-ResourcePartition'
  grouping moc-SciProfile-keys {
    description "Key(s) for MOC SciProfile";
    leaf id {
      erienmyext:no-notification;
      description "The value component of the RDN.";
      mandatory true;
      yexte:ecim-name sciProfileId;
      type string;
    }
  } // end 'grouping moc-SciProfile-keys'
  grouping moc-SciProfile {
    description "Contains bearer-level eNB specific QoS configuration used for feature FlexibleQoS. SCI profile can be used only when FlexibleQoS is activated.\n\nThe RDNs of these MOs are SciProfile=sci1 to SciProfile=sci18, SciProfile=default.";
    leaf priority {
      description "SCI-related bearer priority. Refer to priority defined in 3GPP TS 23.203.";
      yexte:disturbances "Changing this attribute can cause loss of traffic.";
      yexte:takes-effect "New connection";
      yexte:dependencies "Only relevant if the license for Flexible QoS is present and active.";
      type erienmnrmlrat:ddt-Lrat_SciProfile_priority;
      default 9;
    }
    leaf dlResourceAllocationStrategy {
      description "Defines downlink resource allocation strategy of SCI.";
      yexte:takes-effect "New connection";
      yexte:dependencies "Parameter changes take effect only if the licenses are present and active for the following: Flexible QoS, Downlink Frequency Selective Scheduling and QoS Aware Scheduler.";
      type erienmnrmlrat:enum-ResourceAllocationStrategy;
      default RESOURCE_FAIR;
    }
    leaf pdb {
      description "Contribution from eNodeB to PDB for SCI. Packet delays outside eNodeB are excluded, for example in the transport network. For more information about PDB refer to TS23.203.";
      yexte:takes-effect "New connection";
      yexte:dependencies "Only relevant if the licenses for Flexible QoS and QoS Aware Scheduler are present and active.";
      type erienmnrmlrat:ddt-Lrat_SciProfile_pdb;
      default 0;
    }
    leaf srsAllocationStrategy {
      description "If parameter srsAllocationStrategy in QoS configuration for UE DRB is ACTIVATED, then an attempt is made to allocate UE sounding. Algorithm uses priority parameter in QoS configuration to resolve which QoS configuration defines sounding, if several DRBs are setup to UE with different QoS configurations.";
      yexte:takes-effect "New connection";
      yexte:dependencies "Only relevant if the licenses are present and active for: Flexible QoS, QoS Aware Scheduler and frequency selective scheduling.";
      type erienmnrmlrat:enum-SrsAllocationStrategy;
      default DEACTIVATED;
    }
    leaf ulMaxWaitingTime {
      description "Scheduler attempts to achieve ulMaxWaitingTime for UL bearers before giving any UL bearer a higher priority. Value 0 means that the higher priority is never applied. Must be set to similar or slightly shorter value than PDB. If value set too low, higher priority services can be affected. For more information about PDB refer to TS23.203.";
      yexte:disturbances "Changing this attribute can affect performance of all data bearers.\n A value that is set too low can affect other services with higher priority. A value that is set too high can cause Dynamic UE Admission Control to fail in keeping the cell stable at overload.";
      yexte:takes-effect "New connection";
      yexte:dependencies "Only used for Resource Fair Scheduling algorithm. Only relevant if licenses for Flexible QoS and Advanced Differentiation for Resource Fair Scheduler are present and active.";
      type erienmnrmlrat:ddt-Lrat_SciProfile_ulMaxWaitingTime;
      default 0;
    }
    leaf ulMinBitRate {
      description "Scheduler attempts to achieve minbitrate for all bearers before giving any user a higher rate. Value 0 means that minRate scheduler is not used.";
      yexte:disturbances "Changing this attribute can cause loss of traffic.";
      yexte:takes-effect "New connection";
      yexte:dependencies "Parameter is used only if one of the following Proportional Fair scheduling algorithms is selected: \"maximum_C_over_I\", \"proportional_fair_low\", \"proportional_fair_medium\", \"proportional_fair_high\" or \"equal_rate\". Only relevant if licenses for Flexible QoS and QoS Aware Scheduler are present and active.";
      type erienmnrmlrat:ddt-Lrat_SciProfile_ulMinBitRate;
      default 0;
    }
    leaf schedulingAlgorithm {
      description "Scheduling algorithm used for certain SCI.";
      yexte:disturbances "Changing this attribute can cause loss of traffic.";
      yexte:takes-effect "New connection";
      yexte:dependencies "Only relevant if the licenses for Flexible QoS and QoS Aware Scheduler are present and active. Value DELAY_BASED can only be used if attribute serviceType for a bearer has value VOIP.";
      type erienmnrmlrat:enum-SchedulingAlgorithm;
      default RESOURCE_FAIR;
    }
    leaf dlMaxWaitingTime {
      description "Scheduler attempts to achieve dlMaxWaitingTime for DL bearers before giving any DL bearer a higher priority. Value 0 means that the higher priority is never applied. Must be set to similar or slightly shorter value than PDB. If value set too low, higher priority services can be affected. For more information about PDB refer to TS23.203.";
      yexte:disturbances "Changing this attribute can affect performance of all data bearers.\nA value that is set too low can affect other services with higher priority. A value that is set too high can cause Dynamic UE Admission Control to fail in keeping the cell stable at overload.";
      yexte:takes-effect "New connection";
      yexte:dependencies "Only used for Resource Fair Scheduling algorithm. Only relevant if licenses for Flexible QoS and Advanced Differentiation for Resource Fair Scheduling are present and active.";
      type erienmnrmlrat:ddt-Lrat_SciProfile_dlMaxWaitingTime;
      default 0;
    }
    leaf dlRelativePriority {
      description "The relative priority for DL associated with an SCI.";
      yexte:takes-effect "New connection";
      yexte:dependencies "Changes to this parameter take effect only if the licenses are present and active for: Flexible QoS, QoS Aware Scheduler, Proportional Fair Scheduler, and the Rps.";
      type erienmnrmlrat:ddt-Lrat_SciProfile_dlRelativePriority;
      default 1;
    }
    leaf absPrioOverride {
      description "Indicates if the data radio bearer is subject to Absolute Priority Override.";
      yexte:disturbances "Changing this attribute can cause loss of traffic.";
      yexte:takes-effect "New connection";
      yexte:dependencies "Only relevant if the licenses for Flexible QoS and QoS Aware Scheduler are present and active.";
      type erienmnrmlrat:enum-AbsPrioOverride;
      default NO_OVERRIDE;
    }
    leaf dlMinBitRate {
      description "Scheduler attempts to achieve minbitrate for all bearers before giving any user a higher rate. Value 0 means that minRate scheduler is not used.";
      yexte:disturbances "Changing this attribute can cause loss of traffic.";
      yexte:takes-effect "New connection";
      yexte:dependencies "Parameter is used only if one of the following Proportional Fair scheduling algorithms is selected: \"maximum_C_over_I\", \"proportional_fair_low\", \"proportional_fair_medium\", \"proportional_fair_high\" or \"equal_rate\". Only relevant if the licenses for Flexible QoS and QoS Aware Scheduler are present and active.";
      type erienmnrmlrat:ddt-Lrat_SciProfile_dlMinBitRate;
      default 0;
    }
    leaf sci {
      yexte:restricted;
      description "SCI specifies eNodeB configuration that controls packet-forwarding treatment for bearers. Each MO instance has unique SCI value.\nSpecial value: 0 activates default SCI profile. Used for specific bearer with no defined profile.";
      mandatory true;
      yexte:takes-effect "Object unlocked";
      yexte:dependencies "Each SCI must be unique.";
      type erienmnrmlrat:ddt-Lrat_SciProfile_sci;
    }
    leaf-list reservedBy {
      min-elements 0;
      config false;
      description "List of MO instances that reserve this MO instance.";
      yexte:dependencies "MO can not be deleted if it is reserved.";
      notife:notifiable-state-data true;
      erienmyext:enm-type MOREF;
      type string;
    }
    leaf ulRelativePriority {
      description "The relative priority for UL associated with an SCI.";
      yexte:takes-effect "New connection";
      yexte:dependencies "Parameter changes take effect only if the licenses are present and active for: Flexible QoS, QoS Aware Scheduler, Proportional Fair Scheduler, and RPS.";
      type erienmnrmlrat:ddt-Lrat_SciProfile_ulRelativePriority;
      default 1;
    }
    leaf logicalChannelGroupRef {
      description "Refers to an instance of LCG. Assigns LCG to SCI.";
      mandatory true;
      yexte:takes-effect "New connection";
      yexte:dependencies "Only relevant if the license for Flexible QoS is present and active.";
      erienmyext:enm-type MOREF;
      type string;
    }
    leaf lessMaxDelayThreshold {
      description "Time delay that scheduling stays on-hold for Low Energy Scheduler Solution.\nIf 0, Low Energy Scheduler Solution is disabled.";
      yexte:takes-effect "New connection";
      type erienmnrmlrat:ddt-Lrat_SciProfile_lessMaxDelayThreshold;
      default 0;
    }
    leaf ulResourceAllocationStrategy {
      description "Defines uplink resource allocation strategy of SCI.";
      yexte:takes-effect "New connection";
      yexte:dependencies "Only relevant if the licenses are present and active for: Flexible QoS, Uplink Frequency Selective Scheduling and QoS Aware Scheduler.";
      type erienmnrmlrat:enum-ResourceAllocationStrategy;
      default RESOURCE_FAIR;
    }
  } // end 'grouping moc-SciProfile'
  grouping moc-ReportConfigCsfbGeran-keys {
    description "Key(s) for MOC ReportConfigCsfbGeran";
    leaf id {
      erienmyext:no-notification;
      description "The value component of the RDN.";
      mandatory true;
      yexte:ecim-name reportConfigCsfbGeranId;
      type string;
    }
  } // end 'grouping moc-ReportConfigCsfbGeran-keys'
  grouping moc-ReportConfigCsfbGeran {
    description "Contains report configuration settings for the B1 or B2 event for GERAN measurements, used when searching for a suitable target cell when CS Fallback is triggered for the UE.\n\nThe RDN of this MO is ReportConfigCsfbGeran=1.";
    leaf timeToTrigger {
      description "The time to trigger value for the event B1 or B2 measurement.";
      yexte:takes-effect "New connection";
      type erienmnrmlrat:ddt-Lrat_ReportConfigCsfbGeran_timeToTrigger;
      default 40;
    }
    leaf thresholdGeran {
      description "The Signal Quality in the ThresholdGERAN, threshold value for event B1 or B2.";
      yexte:takes-effect "New connection";
      type erienmnrmlrat:ddt-Lrat_ReportConfigCsfbGeran_thresholdGeran;
      default -110;
    }
    leaf hysteresis {
      description "The hysteresis value for the event B1 and event B2, threshold2, measurement.";
      yexte:takes-effect "New connection";
      type erienmnrmlrat:ddt-Lrat_ReportConfigCsfbGeran_hysteresis;
      default 10;
    }
  } // end 'grouping moc-ReportConfigCsfbGeran'
  grouping moc-ReportConfigB2CdmaUlTrig-keys {
    description "Key(s) for MOC ReportConfigB2CdmaUlTrig";
    leaf id {
      status deprecated {
        yexte:status-information "Since 17.Q4. Has no functional behavior. Planned to be removed.";
      }
      erienmyext:no-notification;
      description "The value component of the RDN.";
      mandatory true;
      yexte:ecim-name reportConfigB2CdmaUlTrigId;
      type string;
    }
  } // end 'grouping moc-ReportConfigB2CdmaUlTrig-keys'
  grouping moc-ReportConfigB2CdmaUlTrig {
    description "Contains report configuration settings for the B2 event for CDMA2000 measurements initiated by Uplink-Triggered Inter-Frequency Mobility. The actual threshold values used can be adjusted by frequency relation or QCI related offsets if the feature Multi-Layer Service-Triggered Mobility (MLSTM) is enabled.\n\nThe RDN of this MO is ReportConfigB2CdmaUlTrig=1.";
    leaf b2Threshold2Cdma2000 {
      status deprecated {
        yexte:status-information "Since 17.Q4. Has no functional behavior. Planned to be removed.";
      }
      description "The Signal Quality in the thresholdCDMA2000, threshold2 value for eventB2.";
      yexte:takes-effect "New connection";
      type erienmnrmlrat:ddt-Lrat_ReportConfigB2CdmaUlTrig_b2Threshold2Cdma2000;
      default -75;
    }
    leaf hysteresisB2 {
      status deprecated {
        yexte:status-information "Since 17.Q4. Has no functional behavior. Planned to be removed.";
      }
      description "The hysteresis value for the event B2.";
      yexte:takes-effect "New connection";
      type erienmnrmlrat:ddt-Lrat_ReportConfigB2CdmaUlTrig_hysteresisB2;
      default 10;
    }
    leaf timeToTriggerB2 {
      status deprecated {
        yexte:status-information "Since 17.Q4. Has no functional behavior. Planned to be removed.";
      }
      description "Time-to-trigger value for event B2.";
      yexte:takes-effect "New connection";
      type erienmnrmlrat:ddt-Lrat_ReportConfigB2CdmaUlTrig_timeToTriggerB2;
      default 640;
    }
    leaf reportIntervalB2 {
      status deprecated {
        yexte:status-information "Since 17.Q4. Has no functional behavior. Planned to be removed.";
      }
      description "The interval for event triggered periodical reporting for B2 event.";
      yexte:takes-effect "New connection";
      type erienmnrmlrat:enum-ReportInterval;
      default MS_2048;
    }
  } // end 'grouping moc-ReportConfigB2CdmaUlTrig'
  grouping moc-GUtraNetwork-keys {
    description "Key(s) for MOC GUtraNetwork";
    leaf id {
      erienmyext:no-notification;
      description "The value component of the RDN.";
      mandatory true;
      yexte:ecim-name gUtraNetworkId;
      type string;
    }
  } // end 'grouping moc-GUtraNetwork-keys'
  grouping moc-GUtraNetwork {
    description "This managed object is a container for Managed Objects related to GUTRA networks.";
    leaf userLabel {
      description "User-defined alphanumeric label, maximum 128 characters including spaces.";
      type erienmnrmlrat:ddt-Lrat_GUtraNetwork_userLabel;
    }
  } // end 'grouping moc-GUtraNetwork'
  grouping moc-ReportConfigEUtraBestCell-keys {
    description "Key(s) for MOC ReportConfigEUtraBestCell";
    leaf id {
      erienmyext:no-notification;
      description "The value component of the Relative Distinguished Name (RDN).\n";
      mandatory true;
      yexte:ecim-name reportConfigEUtraBestCellId;
      type string;
    }
  } // end 'grouping moc-ReportConfigEUtraBestCell-keys'
  grouping moc-ReportConfigEUtraBestCell {
    description "This managed object contains the Report Configuration settings for best cell UE measurements.\n\nThe RDN of this MO is ReportConfigEUtraBestCell=1.";
    leaf a3offset {
      description "The offset value for eventA3.\n";
      yexte:takes-effect "New connection";
      type erienmnrmlrat:ddt-Lrat_ReportConfigEUtraBestCell_a3offset;
      default 30;
    }
    leaf triggerQuantityA3 {
      description "The quantity that triggers the event.\n";
      yexte:takes-effect "New connection";
      type erienmnrmlrat:enum-TriggerQuantity;
      default RSRP;
    }
    leaf hysteresisA3 {
      description "The hysteresis value for eventA3.\n";
      yexte:takes-effect "New connection";
      type erienmnrmlrat:ddt-Lrat_ReportConfigEUtraBestCell_hysteresisA3;
      default 10;
    }
    leaf timeToTriggerA3 {
      description "The time-to-trigger value for eventA3.";
      yexte:takes-effect "New connection";
      type erienmnrmlrat:ddt-Lrat_ReportConfigEUtraBestCell_timeToTriggerA3;
      default 40;
    }
    leaf timeToTriggerA3Rsrq {
      status deprecated {
        yexte:status-information "Since L16B. Has no functional behavior. Planned to be removed.";
      }
      description "Time-to-trigger value for event A3 with trigger quantity RSRQ. If set to -1, this attribute is not used for report configuration.";
      yexte:takes-effect "New connection";
      yexte:dependencies "Feature Mobility Control at Poor Coverage must be active.";
      type erienmnrmlrat:ddt-Lrat_ReportConfigEUtraBestCell_timeToTriggerA3Rsrq;
      default -1;
    }
  } // end 'grouping moc-ReportConfigEUtraBestCell'
  grouping moc-DiffAdmCtrlFilteringProfile-keys {
    description "Key(s) for MOC DiffAdmCtrlFilteringProfile";
    leaf id {
      erienmyext:no-notification;
      description "The value component of the RDN.";
      mandatory true;
      yexte:ecim-name diffAdmCtrlFilteringProfileId;
      type string;
    }
  } // end 'grouping moc-DiffAdmCtrlFilteringProfile-keys'
  grouping moc-DiffAdmCtrlFilteringProfile {
    description "Filtering profile for additional level of Differentiated Admission Control.\nAttributes take effect only when AdmissionControl::diffAdmCtrlFilteringEnabled is true.";
    leaf-list firstPreEmptionSpidSet {
      min-elements 0;
      max-elements 6;
      description "First SPID values for pre-emption.\nUEs (or their E-RABs) matching these SPID values are first choice for pre-emption.\nValue -1 denotes UEs without defined SPID value.";
      yexte:disturbances "Changing this attribute can cause loss of traffic.";
      type erienmnrmlrat:ddt-Lrat_DiffAdmCtrlFilteringProfile_firstPreEmptionSpidSet;
    }
    leaf-list reservedBy {
      min-elements 0;
      config false;
      description "Contains a list of MO instances that reserve this MO instance.";
      notife:notifiable-state-data true;
      erienmyext:enm-type MOREF;
      type string;
    }
  } // end 'grouping moc-DiffAdmCtrlFilteringProfile'
  grouping moc-CellPerformance-keys {
    description "Key(s) for MOC CellPerformance";
    leaf id {
      erienmyext:no-notification;
      description "The value component of the RDN.";
      mandatory true;
      yexte:ecim-name cellPerformanceId;
      type string;
    }
  } // end 'grouping moc-CellPerformance-keys'
  grouping moc-CellPerformance {
    description "Contains parameters related to cell level performance improvement.\n\nThe RDN of this MO is CellPerformance=1.";
  } // end 'grouping moc-CellPerformance'
  grouping moc-MeasCellGroup-keys {
    description "Key(s) for MOC MeasCellGroup";
    leaf id {
      erienmyext:no-notification;
      description "The value component of the RDN.";
      mandatory true;
      yexte:ecim-name measCellGroupId;
      type string;
    }
  } // end 'grouping moc-MeasCellGroup-keys'
  grouping moc-MeasCellGroup {
    description "Set of measurement group defined for use in the node.";
    leaf-list spidList {
      min-elements 0;
      max-elements 20;
      description "SPID values to be included in this measurement group. A measurement group with a spidList containing the value 0 includes UEs with no defined SPID value. Only valid when this MO instance is referenced from EUtranCellFDD::measCellGroupUeRef or EUtranCellTDD::measCellGroupUeRef.";
      yexte:takes-effect "New connection";
      yexte:dependencies "Can only be configured if plmnList is empty.";
      type erienmnrmlrat:ddt-Lrat_MeasCellGroup_spidList;
    }
    leaf groupId {
      description "Measurement group ID.";
      yexte:dependencies "Unique id among all MeasCellGroup MOs.";
      type erienmnrmlrat:ddt-Lrat_MeasCellGroup_groupId;
      default 0;
    }
    leaf-list reservedBy {
      min-elements 0;
      config false;
      description "Contains a list of MO instances that reserve this MO instance.";
      notife:notifiable-state-data true;
      erienmyext:enm-type MOREF;
      type string;
    }
    list plmnList {
      min-elements 0;
      max-elements 6;
      key auto-generated-struct-key;
      leaf auto-generated-struct-key {
        type uint16;
        description "This leaf has been injected to allow for struct instances in a sequence to be ordered.";
        mandatory true;
      }
      description "PLMNs to be included in this measurement group. Only valid when this MO instance is referenced from EUtranCellFDD::measCellGroupUeRef or EUtranCellTDD::measCellGroupUeRef.";
      erienmyext:enm-type STRUCT;
      uses erienmnrmlrat:struct-PlmnIdentity;
    } // end 'list plmnList'
    leaf groupPrbUnit {
      description "PRB utilization PDF bin step size for measurement group.";
      type erienmnrmlrat:ddt-Lrat_MeasCellGroup_groupPrbUnit;
      default 5;
    }
  } // end 'grouping moc-MeasCellGroup'
  grouping moc-ReportConfigA1Prim-keys {
    description "Key(s) for MOC ReportConfigA1Prim";
    leaf id {
      erienmyext:no-notification;
      description "The value component of the Relative Distinguished Name (RDN).";
      mandatory true;
      yexte:ecim-name reportConfigA1PrimId;
      type string;
    }
  } // end 'grouping moc-ReportConfigA1Prim-keys'
  grouping moc-ReportConfigA1Prim {
    description "This managed object contains report configuration settings for the primary A1 event measurements. The A1 event is used to detect the Bad Coverage Cease condition.\nPrimary and secondary reporting configuration MOs refer to the option to use different settings for two simultaneous measurements for the event A1.\n\nThe RDN of this MO is ReportConfigA1Prim=1.";
    leaf a1ThrRsrpPrimOffsetCeABr {
      description "CAT-M UE in CE mode A Good coverage Offset for the absolute threshold a1ThresholdRsrpPrim.";
      yexte:takes-effect "New connection";
      type erienmnrmlrat:ddt-Lrat_ReportConfigA1Prim_a1ThrRsrpPrimOffsetCeABr;
      default 0;
    }
    leaf hysteresisA1Prim {
      description "The hysteresis value for the primary eventA1 measurement.";
      yexte:takes-effect "New connection";
      type erienmnrmlrat:ddt-Lrat_ReportConfigA1Prim_hysteresisA1Prim;
      default 10;
    }
    leaf timeToTriggerA1Prim {
      description "The time-to-trigger value for the primary eventA1 measurement.";
      yexte:takes-effect "New connection";
      type erienmnrmlrat:ddt-Lrat_ReportConfigA1Prim_timeToTriggerA1Prim;
      default 640;
    }
    leaf a1ThresholdRsrqPrim {
      description "The Reference Signal Received Quality (RSRQ) threshold value for the primary eventA1.";
      yexte:takes-effect "New connection";
      yexte:dependencies "Only used if triggerQuantityA2Prim is set to RSRQ.";
      type erienmnrmlrat:ddt-Lrat_ReportConfigA1Prim_a1ThresholdRsrqPrim;
      default -195;
    }
    leaf a1ThresholdRsrpPrim {
      description "The Reference Signal Received Power (RSRP) threshold value for the primary eventA1.";
      yexte:takes-effect "New connection";
      yexte:dependencies "Only used if triggerQuantityA2Prim is set to RSRP.";
      type erienmnrmlrat:ddt-Lrat_ReportConfigA1Prim_a1ThresholdRsrpPrim;
      default -136;
    }
  } // end 'grouping moc-ReportConfigA1Prim'
  grouping moc-PwsCmas-keys {
    description "Key(s) for MOC PwsCmas";
    leaf id {
      erienmyext:no-notification;
      description "The value component of the RDN.";
      mandatory true;
      yexte:ecim-name pwsCmasId;
      type string;
    }
  } // end 'grouping moc-PwsCmas-keys'
  grouping moc-PwsCmas {
    description "This MO class stores warning information to be broadcast in SIB12.\n\nThe RDNs of these MOs are PwsCmas=1 to PwsCmas=64.";
  } // end 'grouping moc-PwsCmas'
  grouping moc-ReportConfigB2CdmaRttUlTrig-keys {
    description "Key(s) for MOC ReportConfigB2CdmaRttUlTrig";
    leaf id {
      status deprecated {
        yexte:status-information "Since 17.Q4. Has no functional behavior. Planned to be removed.";
      }
      erienmyext:no-notification;
      description "The value component of the RDN.";
      mandatory true;
      yexte:ecim-name reportConfigB2CdmaRttUlTrigId;
      type string;
    }
  } // end 'grouping moc-ReportConfigB2CdmaRttUlTrig-keys'
  grouping moc-ReportConfigB2CdmaRttUlTrig {
    description "Contains report configuration settings for the B2 event for CDMA2000 1xRTT measurements initiated by Uplink-Triggered Inter-Frequency Mobility. The actual threshold values used can be adjusted by frequency relation or QCI related offsets if the feature Multi-Layer Service-Triggered Mobility (MLSTM) is enabled.\n\nThe RDN of this MO is ReportConfigB2CdmaRttUlTrig=1.";
    leaf hysteresisB2 {
      status deprecated {
        yexte:status-information "Since 17.Q4. Has no functional behavior. Planned to be removed.";
      }
      description "The hysteresis value for the event B2.";
      yexte:takes-effect "New connection";
      type erienmnrmlrat:ddt-Lrat_ReportConfigB2CdmaRttUlTrig_hysteresisB2;
      default 10;
    }
    leaf b2Threshold2Cdma20001xRtt {
      status deprecated {
        yexte:status-information "Since 17.Q4. Has no functional behavior. Planned to be removed.";
      }
      description "The Signal Quality in the thresholdCDMA2000, threshold2 value for eventB2.";
      yexte:takes-effect "New connection";
      type erienmnrmlrat:ddt-Lrat_ReportConfigB2CdmaRttUlTrig_b2Threshold2Cdma20001xRtt;
      default -75;
    }
    leaf timeToTriggerB2 {
      status deprecated {
        yexte:status-information "Since 17.Q4. Has no functional behavior. Planned to be removed.";
      }
      description "Time-to-trigger value for event B2.";
      yexte:takes-effect "New connection";
      type erienmnrmlrat:ddt-Lrat_ReportConfigB2CdmaRttUlTrig_timeToTriggerB2;
      default 640;
    }
    leaf reportIntervalB2 {
      status deprecated {
        yexte:status-information "Since 17.Q4. Has no functional behavior. Planned to be removed.";
      }
      description "The interval for event triggered periodical reporting for B2 event.";
      yexte:takes-effect "New connection";
      type erienmnrmlrat:enum-ReportInterval;
      default MS_2048;
    }
  } // end 'grouping moc-ReportConfigB2CdmaRttUlTrig'
  grouping moc-InstantUplinkAccess-keys {
    description "Key(s) for MOC InstantUplinkAccess";
    leaf id {
      erienmyext:no-notification;
      description "The value component of the RDN.";
      mandatory true;
      yexte:ecim-name instantUplinkAccessId;
      type string;
    }
  } // end 'grouping moc-InstantUplinkAccess-keys'
  grouping moc-InstantUplinkAccess {
    description "Parameters for Instant Uplink Access feature for EUtranCellFDD/TDD.\n\nThe RDN of this MO is InstantUplinkAccess=1.";
    leaf iuaTargetBufferEmptyTime {
      description "Time to empty iuaTargetBufferSize with IUA-SPS grant. If not emptied during this time, IUA is deactivated for that UE.";
      type erienmnrmlrat:ddt-Lrat_InstantUplinkAccess_iuaTargetBufferEmptyTime;
      default 4;
    }
    leaf iuaDuration {
      description "Duration after which IUA active UE is considered for deactivation. IUA active UE can be deactivated earlier, depending on SINR and load conditions.";
      type erienmnrmlrat:ddt-Lrat_InstantUplinkAccess_iuaDuration;
      default 1050;
    }
    leaf iuaInactivityTimer {
      description "Time since last UL transmission timer. IUA is deactivated due to inactivity when both iuaDuration and iuaInactivityTimer expire.";
      type erienmnrmlrat:ddt-Lrat_InstantUplinkAccess_iuaInactivityTimer;
      default 100;
    }
    leaf iuaTargetBufferSize {
      description "IUA target buffer size in IUA active mode. Transport block size of IUA-SPS grant depends on SINR of UE and iuaUePrbLimit.";
      type erienmnrmlrat:ddt-Lrat_InstantUplinkAccess_iuaTargetBufferSize;
      default 86;
    }
    leaf iuaEnabled {
      description "Enables IUA for cell.";
      type boolean;
      default false;
    }
    leaf iuaCellResourceLimit {
      description "Maximum percentage of available PUSCH PRBs and SEs for each TTI for each cell that IUA can use at cell level. Sum of resources for each cell is less than or equal to iuaBbmResourceLimit. Minimum value of 1 means 1 PUSCH PRB and 1 UL SE. Ceiling function is applied while calculating other values. For example if available PUSCH PRBs are 90 and SEs for each TTI for each cell are 18 with iuaCellResourceLimit set to 20, maximum resources for each cell that IUA can use are (20% of 90) = 18 PUSCH PRBs and (20% of 18) = 4 SEs.";
      type erienmnrmlrat:ddt-Lrat_InstantUplinkAccess_iuaCellResourceLimit;
      default 20;
    }
    leaf iuaLoadThreshold {
      description "Filtered load threshold. Below the threshold, IUA is activated in cell. Measured by MSR in UL as done for Dynamic UE Admission Control.";
      type erienmnrmlrat:ddt-Lrat_InstantUplinkAccess_iuaLoadThreshold;
      default 80;
    }
    leaf iuaSinrThreshold {
      description "UE filtered SINR threshold. Above the threshold, IUA is activated.";
      type erienmnrmlrat:ddt-Lrat_InstantUplinkAccess_iuaSinrThreshold;
      default 5;
    }
    leaf iuaUePrbLimit {
      description "Upper limit on number of PUSCH PRBs an IUA active UE can use. Maximum value is restricted to available PUSCH PRBs for IUA.";
      type erienmnrmlrat:ddt-Lrat_InstantUplinkAccess_iuaUePrbLimit;
      default 3;
    }
    leaf iuaInterval {
      description "Time interval between UL short-SPS instances. Value 0 means load based selection of IUA interval. Load is measured by MSR in UL as done for Dynamic UE Admission Control feature.";
      yexte:dependencies "In EUtranCellFDD, INTERVAL_5MS is not allowed.\nIn EUtranCellTDD, INTERVAL_2MS and INTERVAL_4MS are not allowed.";
      type erienmnrmlrat:enum-IuaIntervalSelection;
      default INTERVAL_1MS;
    }
    leaf iuaDeactTimer {
      description "Time since last UL transmission timer. At high load, IUA is deactivated when iuaDeactTimer expires. High load is determined when resources needed for UEs with real data in buffer are unavailable due to being taken by IUA UEs.";
      type erienmnrmlrat:ddt-Lrat_InstantUplinkAccess_iuaDeactTimer;
      default 10;
    }
    leaf iuaSinrDeactHyst {
      description "UE filtered SINR hysteresis. IUA is deactivated when filtered SINR is less than iuaSinrThreshold by iuaSinrDeactHyst.";
      type erienmnrmlrat:ddt-Lrat_InstantUplinkAccess_iuaSinrDeactHyst;
      default 20;
    }
  } // end 'grouping moc-InstantUplinkAccess'
  grouping moc-PreschedProfile-keys {
    description "Key(s) for MOC PreschedProfile";
    leaf id {
      erienmyext:no-notification;
      description "The value component of the RDN.";
      mandatory true;
      yexte:ecim-name preschedProfileId;
      type string;
    }
  } // end 'grouping moc-PreschedProfile-keys'
  grouping moc-PreschedProfile {
    description "Prescheduling profiles and parameters to map towards different advanced subscriber groups.\n\nThe RDNs of these MOs are PreschedProfile=0 to PreschedProfile=4.";
    leaf preschedulingDuration {
      description "Prescheduling is stopped if there are no UL transmissions during this time.";
      type erienmnrmlrat:ddt-Lrat_PreschedProfile_preschedulingDuration;
      default 200;
    }
    leaf-list reservedBy {
      min-elements 0;
      config false;
      description "Contains a list of MO instances that reserve this MO instance.";
      yexte:dependencies "The MO may not be deleted if it is reserved.";
      notife:notifiable-state-data true;
      erienmyext:enm-type MOREF;
      type string;
    }
    leaf preschedulingDataSize {
      description "Granted data size during prescheduling period.";
      type erienmnrmlrat:ddt-Lrat_PreschedProfile_preschedulingDataSize;
      default 86;
    }
    leaf preschedulingPeriod {
      description "Period in ms lapsed between granted prescheduling instances.";
      type erienmnrmlrat:ddt-Lrat_PreschedProfile_preschedulingPeriod;
      default 5;
    }
  } // end 'grouping moc-PreschedProfile'
  grouping moc-ReportConfigEUtraBadCovSec-keys {
    description "Key(s) for MOC ReportConfigEUtraBadCovSec";
    leaf id {
      erienmyext:no-notification;
      description "The value component of the Relative Distinguished Name (RDN).\n";
      mandatory true;
      yexte:ecim-name reportConfigEUtraBadCovSecId;
      type string;
    }
  } // end 'grouping moc-ReportConfigEUtraBadCovSec-keys'
  grouping moc-ReportConfigEUtraBadCovSec {
    description "This managed object contains the Report Configuration settings for secondary bad coverage UE measurements.\n\nThe RDN of this MO is ReportConfigEUtraBadCovSec=1.";
    leaf a2ThresholdRsrqSec {
      description "The secondary Reference Signal Received Quality (RSRQ) threshold value for eventA2. Only used if triggerQuantityA2Sec is set to RSRQ.\nPrimary and secondary measurement parameters refer to the option to use different settings for two simultaneous measurements for eventA2.\n";
      yexte:takes-effect "New connection";
      type erienmnrmlrat:ddt-Lrat_ReportConfigEUtraBadCovSec_a2ThresholdRsrqSec;
      default -195;
    }
    leaf timeToTriggerA2Sec {
      description "The time to trigger value for the secondary eventA2 measurement. Primary and secondary measurement parameters refer to the option to use different settings for two simultaneous measurements for eventA2.\n";
      yexte:takes-effect "New connection";
      type erienmnrmlrat:ddt-Lrat_ReportConfigEUtraBadCovSec_timeToTriggerA2Sec;
      default 640;
    }
    leaf hysteresisA2Sec {
      description "The hysteresis value for the secondary eventA2 measurement. Primary and secondary measurement parameters refer to the option to use different settings for two simultaneous measurements for eventA2.\n";
      yexte:takes-effect "New connection";
      type erienmnrmlrat:ddt-Lrat_ReportConfigEUtraBadCovSec_hysteresisA2Sec;
      default 10;
    }
    leaf triggerQuantityA2Sec {
      description "The quantity that triggers the eventA2 and eventA1 for the secondary eventA2 and eventA1 measurement. Primary and secondary measurement parameters refer to the option to use different settings for two simultaneous measurements for eventA2 and eventA1.";
      yexte:takes-effect "New connection";
      type erienmnrmlrat:enum-TriggerQuantity;
      default RSRQ;
    }
    leaf a2ThresholdRsrpSec {
      description "The secondary Reference Signal Received Power (RSRP) threshold value for eventA2. Only used if triggerQuantityA2Sec is set to RSRP.\nPrimary and secondary measurement parameters refer to the option to use different settings for two simultaneous measurements for eventA2.\n";
      yexte:takes-effect "New connection";
      type erienmnrmlrat:ddt-Lrat_ReportConfigEUtraBadCovSec_a2ThresholdRsrpSec;
      default -140;
    }
    leaf a2ThrRsrpSecOffsetCeABr {
      description "CAT-M UE in CE mode A Bad coverage Offset for the absolute threshold a2ThresholdRsrpSec.";
      yexte:takes-effect "New connection";
      type erienmnrmlrat:ddt-Lrat_ReportConfigEUtraBadCovSec_a2ThrRsrpSecOffsetCeABr;
      default 0;
    }
  } // end 'grouping moc-ReportConfigEUtraBadCovSec'
  grouping moc-MbsfnArea-keys {
    description "Key(s) for MOC MbsfnArea";
    leaf id {
      erienmyext:no-notification;
      description "The value component of the Relative Distinguished Name (RDN).";
      mandatory true;
      yexte:ecim-name mbsfnAreaId;
      type string;
    }
  } // end 'grouping moc-MbsfnArea-keys'
  grouping moc-MbsfnArea {
    description "This MO represents a MBMS Single Frequence Network (MBSFN) area and contains MBSFN area related parameters.";
    leaf userLabel {
      description "Label for free use.";
      type erienmnrmlrat:ddt-Lrat_MbsfnArea_userLabel;
    }
    container notificationConfiguration {
      description "Notification configuration\nNote: If several MbsfnArea are activated for a cell, the notificationConfiguration of highest notificationConfigurationPriority will be used.";
      status deprecated {
        yexte:status-information "Since L16B. Planned to be removed.";
      }
      erienmyext:enm-type STRUCT;
      uses erienmnrmlrat:struct-NotificationConfig;
    } // end 'container notificationConfiguration'
    leaf commonSFAllocPeriod {
      description "Specifies the period during which resources corresponding with field commonSFAlloc are divided between the (P)MCH that are configured for this MBSFN area. The subframe allocation patterns, as defined by commonSFAlloc, repeat continuously during this period. Value 4 corresponds to 4 radio frames, 8 corresponds to 8 radio frames and so on.";
      yexte:takes-effect "Object unlocked";
      yexte:precondition "Attribute administrativeState must be set to LOCKED before modifying this attribute.";
      yexte:dependencies "The mchSchedulingPeriod in the MO class PmchMch must be\na multiple of commonSFAllocPeriod.";
      type erienmnrmlrat:ddt-Lrat_MbsfnArea_commonSFAllocPeriod;
      default 32;
    }
    leaf notificationIndicator {
      status deprecated {
        yexte:status-information "Since L16B. Planned to be removed.";
      }
      description "Specifies which PDCCH bit is used to notify the UE about change of the MCCH applicable for this MBSFN area. Value 0 corresponds with the least significant bit as defined in TS 36.212 and so on.";
      yexte:takes-effect "Object unlocked";
      yexte:precondition "Attribute administrativeState must be set to LOCKED before modifying this attribute.";
      type erienmnrmlrat:ddt-Lrat_MbsfnArea_notificationIndicator;
      default 0;
    }
    leaf sfAllocInfo {
      status deprecated {
        yexte:status-information "Since L16A. Planned to be removed.";
      }
      description "Indicates the subframes of the radio frames indicated by the mcch-RepetitionPeriod and the mcch-Offset, that may carry MCCH. Value \"1\" indicates that the corresponding subframe is allocated. Value \"0\" indicates that the corresponding subframe is not allocated. The following mapping applies:\nFDD: The first/ leftmost bit defines the allocation for subframe #1 of the radio frame indicated by mcch-RepetitionPeriod and mcch-Offset, the second bit for #2, the third bit for #3 , the fourth bit for #6, the fifth bit for #7 and the sixth bit for #8.\nTDD: The first/leftmost bit defines the allocation for subframe #3 of the radio frame indicated by mcch-RepetitionPeriod and mcch-Offset, the second bit for #4, third bit for #7, fourth bit for #8, fifth bit for #9. Uplink subframes are not allocated. The last bit is not used.";
      yexte:takes-effect "Object unlocked";
      yexte:precondition "Attribute administrativeState must be set to LOCKED before modifying this attribute.";
      type erienmnrmlrat:ddt-Lrat_MbsfnArea_sfAllocInfo;
      default 000000;
    }
    leaf mbsfnAreaIdentity {
      description "Specifies the MBSFN area identity.";
      mandatory true;
      yexte:takes-effect "Object unlocked";
      yexte:precondition "Attribute administrativeState must be set to LOCKED before modifying this attribute.";
      type erienmnrmlrat:ddt-Lrat_MbsfnArea_mbsfnAreaIdentity;
    }
    container commonSFAlloc {
      description "Specifies the subframes that are reserved for MBSFN in downlink.";
      status deprecated {
        yexte:status-information "Since L16B. Replaced by attribute commonSFAllocList. Planned to be removed.";
      }
      erienmyext:enm-type STRUCT;
      uses erienmnrmlrat:struct-SubFrameConfig;
    } // end 'container commonSFAlloc'
    leaf mcchRepetitionPeriod {
      description "Specifies the interval between transmissions of MCCH information, in radio frames, Value 32 corresponds to 32 radio frames, 64 corresponds to 64 radio frames and so on.";
      yexte:takes-effect "Object unlocked";
      yexte:precondition "Attribute administrativeState must be set to LOCKED before modifying this attribute.";
      yexte:dependencies "Attribute must be greater than mchSchedulingPeriod in MO class PmchMch.";
      type erienmnrmlrat:ddt-Lrat_MbsfnArea_mcchRepetitionPeriod;
      default 32;
    }
    leaf nonMbsfnRegionLength {
      description "Specifies how many symbols from the beginning of the subframe constitute the non-MBSFN region. This value applies in all subframes of the MBSFN area used for PMCH transmission. The values 1 and 2 correspond to 1 and 2 symbols, respectively.";
      yexte:takes-effect "Object unlocked";
      yexte:precondition "Attribute administrativeState must be set to LOCKED before modifying this attribute.";
      type erienmnrmlrat:ddt-Lrat_MbsfnArea_nonMbsfnRegionLength;
      default 2;
    }
    leaf administrativeState {
      description "The administrative state.\nNote: If this attribute is set to SHUTTING_DOWN, it will immediately go into the state LOCKED.";
      yexte:takes-effect "Object unlocked";
      type erienmnrmlrat:enum-AdmState;
      default LOCKED;
    }
    leaf mcchModificationPeriod {
      description "Specifies periodically appearing boundaries, i.e. radio frames for which SFN mod mcch-ModificationPeriod = 0, The contents of different transmissions of MCCH information can only be different if there is at least one such boundary in-between them.";
      yexte:takes-effect "Object unlocked";
      yexte:precondition "Attribute administrativeState must be set to LOCKED before modifying this attribute.";
      yexte:dependencies "The mchSchedulingPeriod in the MO class PmchMch must be\nsmaller than or equal to mcchModificationPeriod.";
      type erienmnrmlrat:ddt-Lrat_MbsfnArea_mcchModificationPeriod;
      default 512;
    }
    list commonSFAllocList {
      min-elements 0;
      max-elements 8;
      key auto-generated-struct-key;
      leaf auto-generated-struct-key {
        type uint16;
        description "This leaf has been injected to allow for struct instances in a sequence to be ordered.";
        mandatory true;
      }
      description "Subframes that are reserved for MBSFN in DL.";
      erienmyext:enm-type STRUCT;
      uses erienmnrmlrat:struct-SubFrameConfig;
    } // end 'list commonSFAllocList'
    leaf mcchOffset {
      status deprecated {
        yexte:status-information "Since L16A. Planned to be removed.";
      }
      description "Specifies, together with the mcchRepetitionPeriod, the radio frames in which MCCH is scheduled i.e. MCCH is scheduled in radio frames for which: SFN mod mcchRepetitionPeriod = mcch-Offset.";
      yexte:takes-effect "Object unlocked";
      yexte:precondition "Attribute administrativeState must be set to LOCKED before modifying this attribute.";
      type erienmnrmlrat:ddt-Lrat_MbsfnArea_mcchOffset;
      default 0;
    }
    leaf signallingMCS {
      description "Indicates the Modulation and Coding Scheme (MCS) applicable for the subframes indicated by the field sf-AllocInfo and for the first subframe of each MCH scheduling period (which may contain the MCH scheduling information provided by MAC). Value 2 corresponds with the value 2 for parameter I-MCS in TS 36.213, Table 7.1.7.1-1], and so on.";
      mandatory true;
      yexte:takes-effect "Object unlocked";
      yexte:precondition "Attribute administrativeState must be set to LOCKED before modifying this attribute.";
      type erienmnrmlrat:ddt-Lrat_MbsfnArea_signallingMCS;
    }
    leaf-list serviceAreaId {
      min-elements 0;
      max-elements 64;
      description "MBMS Service Area identities that are covered by the MBSFN area.";
      yexte:takes-effect "Next MO unlock";
      yexte:dependencies "One defined serviceAreaId must be configured in eNodeB to ENABLE TermPointToMmeM3.\nMust not be changed when MbsfnArea is unlocked.\nMust not be changed if system-created MO instance MbmsService exists under any PmchMch MO instance under the MbsfnArea.\nQCI and serviceAreaId combination can be set for at most two PmchMch under different MbsfnAreas.";
      type erienmnrmlrat:ddt-Lrat_MbsfnArea_serviceAreaId;
    }
  } // end 'grouping moc-MbsfnArea'
  grouping moc-AirIfLoadProfile-keys {
    description "Key(s) for MOC AirIfLoadProfile";
    leaf id {
      erienmyext:no-notification;
      description "The value component of the (Relative Distinguished Name) RDN";
      mandatory true;
      yexte:ecim-name airIfLoadProfileId;
      type string;
    }
  } // end 'grouping moc-AirIfLoadProfile-keys'
  grouping moc-AirIfLoadProfile {
    description "Contains parameters and constraints for Air Interface Load Generator needed to start the function in a Cell.";
    leaf userLabel {
      description "Label for free use";
      type erienmnrmlrat:ddt-Lrat_AirIfLoadProfile_userLabel;
    }
    leaf ailgLowPrioModType {
      description "Supported modulation type for lower priority artificial load.";
      yexte:takes-effect "Feature start";
      type erienmnrmlrat:enum-DataModSchemes;
      default QPSK_MOD_SCH;
    }
    leaf ailgChangePeriod {
      description "The pattern for generated artificial load changes periodically after each  ailgChangePeriod. The period applies to both PDSCH and PDCCH artificial load.\nWithin each period the same load pattern in terms of positions of PDSCH PRBs and/or PDCCH CCEs within the available bandwidth is used.";
      yexte:takes-effect "Feature start";
      type erienmnrmlrat:ddt-Lrat_AirIfLoadProfile_ailgChangePeriod;
      default 1;
    }
    leaf dlPrbLoadLevel {
      description "Minimal load level associated with downlink Physical Resource Block (PRB) use.\nIf the sum of higher priority artificial load defined according to ailgHighPrio and real UE is below this level, lower priority artificial load is generated to reach the minimal load level.\n0 means that no minimal load level is defined";
      yexte:takes-effect "Feature start";
      type erienmnrmlrat:ddt-Lrat_AirIfLoadProfile_dlPrbLoadLevel;
      default 0;
    }
    container trafficModelPrb {
      description "Contains the attributes required to configure a traffic model pattern to  use for filling the Physical Resource Blocks (PRBs).";
      erienmyext:enm-type STRUCT;
      uses erienmnrmlrat:struct-TrafficModelPrb;
    } // end 'container trafficModelPrb'
    leaf minLoadLevelPdcch {
      description "Minimum load level for PDCCH in terms of utilization of the available Control Channel Elements (CCE). If the PDCCH load from real UE is below this level, lower priority artificial load is generated to reach this minimum load level.\nThe value \"0\" means that no minimum load level is defined.";
      yexte:takes-effect "Feature start";
      type erienmnrmlrat:ddt-Lrat_AirIfLoadProfile_minLoadLevelPdcch;
      default 0;
    }
    leaf noOfOcngPrbSeries {
      description "The number of series (where each series is defined in ocngPrbSerie) to be allocated for the OFDMA Channel Noise Generator (OCNG) pattern, as defined in 3GPP TS 36.133.";
      yexte:takes-effect "Feature start";
      yexte:dependencies "Valid if ailgHighPrio = OCNG";
      type erienmnrmlrat:ddt-Lrat_AirIfLoadProfile_noOfOcngPrbSeries;
      default 1;
    }
    list ocngPrbSerie {
      min-elements 0;
      max-elements 10;
      key auto-generated-struct-key;
      leaf auto-generated-struct-key {
        type uint16;
        description "This leaf has been injected to allow for struct instances in a sequence to be ordered.";
        mandatory true;
      }
      description "Contains the attributes required to configure the OFDMA Channel Noise Generator (OCNG) Frequency Division Duplex (FDD) pattern to use for filling the Physical Resource Blocks (PRBs), according to 3GPP TS 36.133.";
      erienmyext:enm-type STRUCT;
      uses erienmnrmlrat:struct-OcngPrbSerie;
    } // end 'list ocngPrbSerie'
    leaf-list reservedBy {
      min-elements 0;
      config false;
      description "Contains a list of managed object instances that reserves this managed object instance. ";
      yexte:dependencies "The MO may not be deleted if it is reserved.";
      notife:notifiable-state-data true;
      erienmyext:enm-type MOREF;
      type string;
    }
    leaf ailgHighPrio {
      description "The method used to generate high priority artificial load.";
      yexte:takes-effect "Feature start";
      type erienmnrmlrat:enum-PrbPatternModel;
      default NO_HIGH_PRIO_LOAD;
    }
    leaf ailgLoadType {
      description "Decides the type of load to be generated by means of different combinations of PDSCH load, Beam Forming (BF) and PDCCH load.";
      yexte:takes-effect "Feature start";
      type erienmnrmlrat:enum-AilgLoadType;
      default PDSCH_NO_BF;
    }
  } // end 'grouping moc-AirIfLoadProfile'
  grouping moc-GeranFreqGroupRelation-keys {
    description "Key(s) for MOC GeranFreqGroupRelation";
    leaf id {
      erienmyext:no-notification;
      description "The value component of the Relative Distinguished Name (RDN).\n";
      mandatory true;
      yexte:ecim-name geranFreqGroupRelationId;
      type string;
    }
  } // end 'grouping moc-GeranFreqGroupRelation-keys'
  grouping moc-GeranFreqGroupRelation {
    description "This Managed Object represents a mobility relation between an EUtranCellFDD or an EUtranCellTDD and a GeranFreqGroup. It contains parameters that are specific for this relation.\n\nDeleting this MO while the parent EUtranCellFDD/EUtranCellTDD has operationalState set to ENABLED is not recommended as it may affect traffic.";
    leaf userLabel {
      description "Label for free use.\n";
      type erienmnrmlrat:ddt-Lrat_GeranFreqGroupRelation_userLabel;
    }
    leaf nccPermitted {
      description "Field encoded as a bit map.\nBit N is set to 0 if a BCCH carrier with NCC = N-1 is not permitted for monitoring.\nBit N is set to 1 if the BCCH carrier with NCC = N-1 is permitted for monitoring.\nBit N = 1 to 8; bit 1 of the bitmap is the leading bit of the bit string.\n";
      type erienmnrmlrat:ddt-Lrat_GeranFreqGroupRelation_nccPermitted;
      default 11111111;
    }
    leaf b2Thr1RsrqGeranFreqOffset {
      description "The frequency group relation specific offset for the absolute threshold b2Threshold1Rsrq, RSRQ threshold1 value for event B2, used for Multi-Layer Service-Triggered Mobility.";
      yexte:takes-effect "Ongoing connection";
      type erienmnrmlrat:ddt-Lrat_GeranFreqGroupRelation_b2Thr1RsrqGeranFreqOffset;
      default 0;
    }
    list b2GeranOffsetPerPC {
      min-elements 0;
      max-elements 2;
      key auto-generated-struct-key;
      leaf auto-generated-struct-key {
        type uint16;
        description "This leaf has been injected to allow for struct instances in a sequence to be ordered.";
        mandatory true;
      }
      description "The frequency group relation specific offset for the absolute threshold, RSRP/RSRQ threshold1 value for event B2, used for Multi-Layer Service-Triggered Mobility and High Power UE.";
      erienmyext:enm-type STRUCT;
      uses erienmnrmlrat:struct-B2GeranPCOffsetMCPC;
    } // end 'list b2GeranOffsetPerPC'
    leaf altCsfbTargetPrioEc {
      description "Prioritizes the GERAN frequency group  for emergency calls among all frequencies related to the cell for UEs in connected mode.\nSets the priority to the alternative target frequency/frequency group to which to make release with redirect to, when measurement or handover to selected target fails for emergency calls.\nValue -1 means the frequency is excluded.\nValue 0 means the lowest priority.\nValue 7 means the highest priority.";
      yexte:takes-effect "New connection";
      type erienmnrmlrat:ddt-Lrat_GeranFreqGroupRelation_altCsfbTargetPrioEc;
      default 0;
    }
    leaf pMaxGeran {
      description "Calculates the parameter Pcompensation (defined in 3GPP TS 36.304) at cell reselection to a GERAN cell.\nValue 1000 means the parameter is not included in system information.";
      type erienmnrmlrat:ddt-Lrat_GeranFreqGroupRelation_pMaxGeran;
      default 1000;
    }
    leaf mobilityAction {
      description "The preferred way to transfer a UE in connected mode to a GERAN frequency group in case of coverage triggered mobility.";
      yexte:takes-effect "New connection";
      type erienmnrmlrat:enum-MobilityActionGeran;
      default RELEASE_WITH_REDIRECT;
    }
    leaf altCsfbTargetPrio {
      description "Prioritizes the GERAN frequency group among all frequencies related to the cell for UEs in connected mode.\nSets the priority to the alternative target frequency/frequency group to which to make release with redirect, when measurement or handover to selected target fails.\nValue -1 means the frequency is excluded.\nValue 0 means the lowest priority.\nValue 7 means the highest priority.";
      yexte:takes-effect "New connection";
      type erienmnrmlrat:ddt-Lrat_GeranFreqGroupRelation_altCsfbTargetPrio;
      default 0;
    }
    leaf b2Thr1RsrpGeranFreqOffset {
      description "The frequency group relation specific offset for the absolute threshold b2Threshold1Rsrp, RSRP threshold1 value for event B2, used for Multi-Layer Service-Triggered Mobility.";
      yexte:takes-effect "Ongoing connection";
      type erienmnrmlrat:ddt-Lrat_GeranFreqGroupRelation_b2Thr1RsrpGeranFreqOffset;
      default 0;
    }
    list allowedPlmnList {
      min-elements 0;
      max-elements 15;
      key auto-generated-struct-key;
      leaf auto-generated-struct-key {
        type uint16;
        description "This leaf has been injected to allow for struct instances in a sequence to be ordered.";
        mandatory true;
      }
      description "Lists all Public Land Mobile Network (PLMN) IDs allowed for this frequency relation.\n\nA UE that does not support one of the IDs included in allowedPlmnList does not measure on this frequency, according to the UE Handover Restriction List.\n\nNo values in the list imply that the frequency has no restrictions for PLMN.\n\nThe PLMN identity contains the following parts:\n1. MobileCountryCode, MCC, 3 digits\n2. MobileNetworkCode, MNC, 2 or 3 digits (the correct number of digits is set in the mncLength member of this Struct)\n\nFor example, if MCC=125 and MNC=46, then plmnId=12546.";
      erienmyext:enm-type STRUCT;
      uses erienmnrmlrat:struct-PlmnIdentity;
    } // end 'list allowedPlmnList'
    leaf threshXLow {
      description "The threshold used by UE when reselecting towards a lower priority frequency from the current serving frequency. Corresponds to parameter Thresx,low in 3GPP TS 36.304.";
      type erienmnrmlrat:ddt-Lrat_GeranFreqGroupRelation_threshXLow;
      default 0;
    }
    leaf anrMeasOn {
      description "ANR performs measurement on the referenced frequency if this parameter is set to true. Otherwise, ANR does not perform any measurements on this frequency.";
      yexte:takes-effect "New connection";
      type boolean;
      default true;
    }
    leaf qRxLevMin {
      description "The required minimum received Rx level in the GERAN frequency used in cell reselection. Corresponds to parameter Qrxlevmin in 3GPP TS 36.304.";
      type erienmnrmlrat:ddt-Lrat_GeranFreqGroupRelation_qRxLevMin;
      default -115;
    }
    leaf cellReselectionPriority {
      description "Absolute priority of the radio access technology. 0 means lowest priority. Corresponds to parameter priority in 3GPP TS 36.304.";
      yexte:dependencies "The value must be unique and not already used by other RAT, i.e. equal priorities between RATs are not supported.";
      type erienmnrmlrat:ddt-Lrat_GeranFreqGroupRelation_cellReselectionPriority;
      default 5;
    }
    leaf geranFreqGroupRef {
      yexte:restricted;
      description "Reference to the GERAN frequency group MO, GeranFreqGroup.\n";
      mandatory true;
      erienmyext:enm-type MOREF;
      type string;
    }
    leaf qOffsetFreq {
      description "Indicates a frequency-specific offset to apply when evaluating triggering conditions for measurement reporting.";
      yexte:takes-effect "New connection";
      type erienmnrmlrat:ddt-Lrat_GeranFreqGroupRelation_qOffsetFreq;
      default 0;
    }
    leaf csFallbackPrioEC {
      description "Prioritizes GERAN Frequency group among all frequencies/frequency groups for emergency calls related to the cell for UEs in connected mode.\nSets the priority to which frequency group to make emergency call CS Fallback to.\nThe value -1 means the frequency is excluded.\nThe value 0 means the lowest priority.\nThe value 7 means the highest priority.";
      yexte:takes-effect "New connection";
      type erienmnrmlrat:ddt-Lrat_GeranFreqGroupRelation_csFallbackPrioEC;
      default 0;
    }
    leaf csFallbackPrio {
      description "Prioritizes GERAN Frequency group among all frequencies related to the cell for UEs in connected mode.\nSets the priority to which frequency/frequency group to make CS Fallback to.\nThe value -1 means the frequency is excluded.\nThe value 0 means the lowest priority.\nThe value 7 means the highest priority.";
      yexte:takes-effect "New connection";
      type erienmnrmlrat:ddt-Lrat_GeranFreqGroupRelation_csFallbackPrio;
      default 0;
    }
    leaf connectedModeMobilityPrio {
      description "Prioritizes GERAN frequencies among all frequencies related to the cell for UEs in connected mode.\n(0 means the lowest priority. -1 means the frequency is excluded.)";
      yexte:takes-effect "New connection";
      type erienmnrmlrat:ddt-Lrat_GeranFreqGroupRelation_connectedModeMobilityPrio;
      default 5;
    }
    leaf mobilityActionCsfb {
      description "The preferred way to transfer a UE in connected mode to a GERAN frequency group in case of CS Fallback.";
      yexte:takes-effect "New connection";
      type erienmnrmlrat:enum-MobilityActionCsfbGeran;
      default RELEASE_WITH_REDIRECT;
    }
    list qciB2ThrOffsets {
      min-elements 0;
      max-elements 19;
      key auto-generated-struct-key;
      leaf auto-generated-struct-key {
        type uint16;
        description "This leaf has been injected to allow for struct instances in a sequence to be ordered.";
        mandatory true;
      }
      description "Parameters for adding QCI profile and frequency relation specific offsets to B2 threshold values used for mobility decisions. Applicable if Multi-Layer Service-Triggered Mobility (MLSTM) is active.";
      erienmyext:enm-type STRUCT;
      uses erienmnrmlrat:struct-GeranFreqRelQciB2ThrOffsets;
    } // end 'list qciB2ThrOffsets'
    leaf b2Thr2GeranFreqOffset {
      description "The frequency group relation specific offset for the absolute threshold b2Threshold2Geran, Signal quality in the ThresholdGERAN for event B2, used for Multi-Layer Service-Triggered Mobility.";
      yexte:takes-effect "Ongoing connection";
      type erienmnrmlrat:ddt-Lrat_GeranFreqGroupRelation_b2Thr2GeranFreqOffset;
      default 0;
    }
    leaf threshXHigh {
      description "The threshold used by the UE when reselecting towards a higher priority frequency from the current serving frequency. Each frequency of GERAN may have a specific threshold. Corresponds to parameter Thresx,high in 3GPP TS 36.304.";
      type erienmnrmlrat:ddt-Lrat_GeranFreqGroupRelation_threshXHigh;
      default 4;
    }
    leaf voicePrio {
      description "This attribute prioritizes GERAN frequencies among all frequencies related to the cell for User Equipments (UEs) in connected mode. It sets the priority for which frequency to perform mobility to for a voice session.\nThe value -1 means the frequency is excluded.\nThe value 0 means the lowest priority.\nThe value 7 means the highest priority.";
      yexte:takes-effect "New connection";
      type erienmnrmlrat:ddt-Lrat_GeranFreqGroupRelation_voicePrio;
      default 0;
    }
  } // end 'grouping moc-GeranFreqGroupRelation'
  grouping moc-MimoSleepFunction-keys {
    description "Key(s) for MOC MimoSleepFunction";
    leaf id {
      erienmyext:no-notification;
      description "The value component of the RDN.";
      mandatory true;
      yexte:ecim-name mimoSleepFunctionId;
      type string;
    }
  } // end 'grouping moc-MimoSleepFunction-keys'
  grouping moc-MimoSleepFunction {
    description "Contains all MIMO sleep mode function configuration parameters of the in the cell.\n\nThe RDN of this MO is MimoSleepFunction=1.";
    leaf sleepMode {
      description "MIMO sleep mode status for the cell.\nValue \"OFF\" disables both detection and switching support.\nValue \"DETECTION\" enables detection-only mode. No switching is triggered.\nValues \"SOFT_SWITCH\", \"SWITCH\", \"ADVANCED_SWITCH\" enable detection and automatic switching.";
      yexte:disturbances "Activating sleep mode can impact traffic depending on how associated thresholds are configured.";
      yexte:dependencies "ADVANCED_SWITCH cannot be set if sleepPowerControl is set to USE_MAX_POWER.";
      type erienmnrmlrat:enum-MimoSleepStatus;
      default OFF;
    }
    leaf sleepEndTime {
      description "RBS daily end time (UTC time) to stop antenna muting detection or switching.\nFormat in ASCII-code: hh:mm hh = 00-23 mm = 00-59";
      type erienmnrmlrat:ddt-Lrat_MimoSleepFunction_sleepEndTime;
      default 05:00;
    }
    leaf switchDownRrcConnThreshold {
      description "Maximum number of user connections allowed during MIMO sleep detection period to enter MIMO sleep state.";
      yexte:disturbances "Changing this attribute can cause loss of traffic.";
      type erienmnrmlrat:ddt-Lrat_MimoSleepFunction_switchDownRrcConnThreshold;
      default 5;
    }
    leaf switchDownPrbThreshold {
      description "Maximum percentage of DL PRB usage allowed during MIMO sleep detection period to enter MIMO sleep state.";
      yexte:disturbances "Changing this attribute can cause loss of traffic.";
      type erienmnrmlrat:ddt-Lrat_MimoSleepFunction_switchDownPrbThreshold;
      default 10;
    }
    leaf sleepState {
      config false;
      description "If MIMO sleep mode takes effect and is activated. Energy saving mode starts.";
      notife:notifiable-state-data true;
      type erienmnrmlrat:enum-ActivationVals;
    }
    leaf switchUpMonitorDurTimer {
      description "MIMO sleep detection duration period to exit MIMO sleep state.";
      type erienmnrmlrat:ddt-Lrat_MimoSleepFunction_switchUpMonitorDurTimer;
      default 5;
    }
    leaf switchDownMonitorDurTimer {
      description "MIMO sleep detection duration period to enter MIMO sleep state.";
      type erienmnrmlrat:ddt-Lrat_MimoSleepFunction_switchDownMonitorDurTimer;
      default 30;
    }
    leaf sleepStartTime {
      description "RBS daily start time (UTC time) to perform antenna muting detection or switching.\nFormat in ASCII-code: hh:mm hh = 00-23 mm = 00-59";
      type erienmnrmlrat:ddt-Lrat_MimoSleepFunction_sleepStartTime;
      default 02:00;
    }
    leaf sleepPowerControl {
      description "Power allocation method on the transmit branches during MIMO sleep.";
      yexte:disturbances "Changing this attribute can cause loss of traffic.";
      yexte:dependencies "USE_MAX_POWER cannot be set if sleepMode is set to ADVANCED_SWITCH.";
      type erienmnrmlrat:enum-SleepPowerControlType;
      default RETAIN_SAME_POWER;
    }
    leaf switchUpPrbThreshold {
      description "Minimum percentage of DL PRB usage required during MIMO sleep detection period to exit MIMO sleep state.";
      yexte:disturbances "Changing this attribute can cause loss of traffic.";
      yexte:dependencies "switchUpPrbThreshold >= switchDownPrbThreshold";
      type erienmnrmlrat:ddt-Lrat_MimoSleepFunction_switchUpPrbThreshold;
      default 30;
    }
    leaf switchUpRrcConnThreshold {
      description "Minimum number of user connections required during MIMO sleep detection period to exit MIMO sleep state.";
      yexte:disturbances "Changing this attribute can cause loss of traffic.";
      type erienmnrmlrat:ddt-Lrat_MimoSleepFunction_switchUpRrcConnThreshold;
      default 50;
    }
  } // end 'grouping moc-MimoSleepFunction'
  grouping moc-ReportConfigEUtraIFBestCell-keys {
    description "Key(s) for MOC ReportConfigEUtraIFBestCell";
    leaf id {
      erienmyext:no-notification;
      description "The value component of the Relative Distinguished Name (RDN).";
      mandatory true;
      yexte:ecim-name reportConfigEUtraIFBestCellId;
      type string;
    }
  } // end 'grouping moc-ReportConfigEUtraIFBestCell-keys'
  grouping moc-ReportConfigEUtraIFBestCell {
    description "This managed object contains the report configuration settings for best cell measurements on other LTE frequencies.\n\nThe RDN of this MO is ReportConfigEUtraIFBestCell=1.";
    leaf a3RsrqOffset {
      description "Offset to obtain the A3Offset for inter-frequency A3 measurement for trigger quantity RSRQ. a3OffsetRsrq = a3offset + a3RsrqOffset";
      yexte:takes-effect "New connection";
      yexte:dependencies "Feature Mobility Control at Poor Coverage must be active.";
      type erienmnrmlrat:ddt-Lrat_ReportConfigEUtraIFBestCell_a3RsrqOffset;
      default 0;
    }
    leaf hysteresisA3RsrqOffset {
      description "Offset to obtain the Hysteresis for inter-frequency A3 measurement for trigger quantity RSRQ. hysteresisA3Rsrq = hysteresisA3 + hysteresisA3RsrqOffset";
      yexte:takes-effect "New connection";
      yexte:dependencies "Feature Mobility Control at Poor Coverage must be active.";
      type erienmnrmlrat:ddt-Lrat_ReportConfigEUtraIFBestCell_hysteresisA3RsrqOffset;
      default 0;
    }
    leaf a3offset {
      description "The offset value for eventA3.";
      yexte:takes-effect "New connection";
      type erienmnrmlrat:ddt-Lrat_ReportConfigEUtraIFBestCell_a3offset;
      default 30;
    }
    leaf triggerQuantityA3 {
      description "The quantity that triggers the event.";
      yexte:takes-effect "New connection";
      type erienmnrmlrat:enum-TriggerQuantity;
      default RSRP;
    }
    leaf hysteresisA3 {
      description "The hysteresis value for eventA3.";
      yexte:takes-effect "New connection";
      type erienmnrmlrat:ddt-Lrat_ReportConfigEUtraIFBestCell_hysteresisA3;
      default 10;
    }
    leaf timeToTriggerA3 {
      description "Time-to-trigger value for event A3. If timeToTriggerA3Rsrq is -1, this attribute is used for both RSRP and RSRQ. But if not set to -1, this attribute is used only for RSRP.";
      yexte:takes-effect "New connection";
      type erienmnrmlrat:ddt-Lrat_ReportConfigEUtraIFBestCell_timeToTriggerA3;
      default 40;
    }
    leaf timeToTriggerA3Rsrq {
      description "Time-to-trigger value for event A3 with trigger quantity RSRQ. If set to -1, this attribute is not used for report configuration.";
      yexte:takes-effect "New connection";
      yexte:dependencies "Feature Mobility Control at Poor Coverage must be active.";
      type erienmnrmlrat:ddt-Lrat_ReportConfigEUtraIFBestCell_timeToTriggerA3Rsrq;
      default -1;
    }
  } // end 'grouping moc-ReportConfigEUtraIFBestCell'
  grouping moc-UnlicensedBandProfile-keys {
    description "Key(s) for MOC UnlicensedBandProfile";
    leaf id {
      erienmyext:no-notification;
      description "The value component of the RDN.";
      mandatory true;
      yexte:ecim-name unlicensedBandProfileId;
      type string;
    }
  } // end 'grouping moc-UnlicensedBandProfile-keys'
  grouping moc-UnlicensedBandProfile {
    description "Structure for regulatory requirements for unlicensed bands.";
    leaf-list reservedBy {
      min-elements 0;
      config false;
      description "List of MO instances that reserve this MO instance.";
      yexte:dependencies "MO can not be deleted if it is reserved.";
      notife:notifiable-state-data true;
      erienmyext:enm-type MOREF;
      type string;
    }
    list unlicensedBandProfileList {
      min-elements 0;
      max-elements 36;
      key auto-generated-struct-key;
      leaf auto-generated-struct-key {
        type uint16;
        description "This leaf has been injected to allow for struct instances in a sequence to be ordered.";
        mandatory true;
      }
      description "Details of regulatory requirements for unlicensed bands.";
      erienmyext:enm-type STRUCT;
      uses erienmnrmlrat:struct-UnlicensedFrequencyProperties;
    } // end 'list unlicensedBandProfileList'
  } // end 'grouping moc-UnlicensedBandProfile'
  grouping moc-ImeisvTable-keys {
    description "Key(s) for MOC ImeisvTable";
    leaf id {
      erienmyext:no-notification;
      description "Value component of the RDN";
      mandatory true;
      yexte:ecim-name imeisvTableId;
      type string;
    }
  } // end 'grouping moc-ImeisvTable-keys'
  grouping moc-ImeisvTable {
    description "Contains eNB specific configuration used for feature Differentiated UE Handling.\n\nThe RDN of this MO is ImeisvTable=1.\n";
    leaf-list listOfFeaturesDefaultOn {
      min-elements 0;
      max-elements 10;
      description "List of features that are considered as \"Default ON\" in the eNB. Features in the list are possible to turn OFF per IMEISV.\nIf the feature Differentiated UE Handling is OPERABLE, a feature present in the list is OFF for UEs for which:\n- the UE's IMEISV is present in some ImeisvProfile AND\n- the feature is explicitly configured for this ImeisvProfile in attribute listOfFeaturesToTurnOff\nFor all other UEs the feature is ON.";
      yexte:disturbances "Changing this attribute can affect traffic.";
      yexte:takes-effect "New connection";
      yexte:dependencies "listOfFeaturesDefaultOff and listOfFeaturesDefaultOn must be disjoint sets";
      type erienmnrmlrat:enum-FeatureName;
    }
    leaf-list listOfFeaturesDefaultOff {
      min-elements 0;
      max-elements 10;
      description "List of features that are considered as \"Default OFF\" in the eNB. Features in the list are possible to turn ON per IMEISV.\nA feature present in the list is ON for all UEs if the feature Differentiated UE Handling is INOPERABLE.\nIf the feature Differentiated UE Handling is OPERABLE, a feature present in the list is ON for UEs for which:\n- the UE's IMEISV is present in some ImeisvProfile AND\n- the feature is explicitly configured for this ImeisvProfile in attribute listOfFeaturesToTurnOn\nFor all other UEs the feature is OFF.";
      yexte:disturbances "Changing this attribute can affect traffic.";
      yexte:takes-effect "New connection";
      yexte:dependencies "listOfFeaturesDefaultOff and listOfFeaturesDefaultOn must be disjoint sets";
      type erienmnrmlrat:enum-FeatureName;
    }
  } // end 'grouping moc-ImeisvTable'
  grouping moc-ExternalENodeBFunction-keys {
    description "Key(s) for MOC ExternalENodeBFunction";
    leaf id {
      erienmyext:no-notification;
      description "The value component of the Relative Distinguished Name (RDN).\n";
      mandatory true;
      yexte:ecim-name externalENodeBFunctionId;
      type string;
    }
  } // end 'grouping moc-ExternalENodeBFunction-keys'
  grouping moc-ExternalENodeBFunction {
    description "This managed object represents another ENodeB.\n";
    container eNodeBPlmnId {
      description "The Public Land Mobile Network (PLMN) ID of the node. The PLMN ID consists of:\n\n1. MobileCountryCode, MCC, 3 digits\n2. MobileNetworkCode, MNC, 2 or 3 digits (the correct number of digits is set in the mncLength member of this Struct).\n\nExample: If MCC=125 and MNC=46, then plmnId=12546.\nNote: The value (MCC=001, MNC=01) indicates that the PLMN is not initiated. The value can not be used as a valid PLMN Identity.\n";
      erienmyext:enm-type STRUCT;
      uses erienmnrmlrat:struct-PlmnIdentity;
    } // end 'container eNodeBPlmnId'
    leaf userLabel {
      description "User-defined alphanumeric label, maximum 128 characters including spaces.\n";
      type erienmnrmlrat:ddt-Lrat_ExternalENodeBFunction_userLabel;
    }
    leaf eranUlCompVlanPortRef {
      description "VlanPort instance that can be used to set up EranInterMeLinks and BbLinks under this ExternalENodeBFunction for Elastic RAN UL CoMP. If not set, ENodeBFunction::eranUlCompVlanPortRef is used as default.";
      yexte:takes-effect "Next MO unlock";
      erienmyext:enm-type MOREF;
      type string;
    }
    leaf eNBId {
      description "The ID of an RBS within a Public Land Mobile Network (PLMN).";
      mandatory true;
      type erienmnrmlrat:ddt-Lrat_ExternalENodeBFunction_eNBId;
    }
    leaf timeOfCreation {
      erienmyext:no-notification;
      config false;
      description "Indicates the time and date when the MO was created.\nFormat: YYYY-MM-DD HH:MM:SS";
      type erienmnrmlrat:ddt-Lrat_ExternalENodeBFunction_timeOfCreation;
    }
    leaf ulTrigHoSupport {
      description "Configures whether uplink triggered handover is allowed to this external eNodeB or not. This parameter has only effect if no X2 interface is configured or the external node does not support the ULTRIG feature.";
      type erienmnrmlrat:enum-ExternalUlTrigHoSupport;
      default NO_ULTRIG_HO;
    }
    leaf timeOfLastModification {
      config false;
      description "Indicates the time and date when the MO was last modified.\nFormat: YYYY-MM-DD HH:MM:SS";
      notife:notifiable-state-data true;
      type erienmnrmlrat:ddt-Lrat_ExternalENodeBFunction_timeOfLastModification;
    }
    leaf interENodeBCAInteractionMode {
      description "Used to set whether applications shall use eRAN or X2 for CA together with the external eNodeB.";
      yexte:disturbances "Changing this attribute can affect traffic. A TermPointToENB lock/unlock for this external eNodeB is required.";
      yexte:takes-effect "Next MO unlock";
      type erienmnrmlrat:enum-InterENodeBCAInteractionMode;
      default IENBCA;
    }
    leaf eranVlanPortRef {
      description "VlanPort instance that can be used to set up EranInterMeLinks and BbLinks under this ExternalENodeBFunction. If not set, ENodeBFunction::eranVlanPortRef is used as default.";
      yexte:disturbances "Changing this attribute can affect traffic. A TermPointToENB lock/unlock for this external eNodeB is required.";
      yexte:takes-effect "Next MO unlock";
      erienmyext:enm-type MOREF;
      type string;
    }
    leaf mfbiSupport {
      description "Specifies whether the feature Multiple Frequency Band Indicators is enabled or disabled in the external eNB. Specifies whether it is allowed to perform mobility actions for secondary frequency bands to that eNB or not.";
      type boolean;
      default false;
    }
    leaf ulTrigSupport {
      erienmyext:no-notification;
      config false;
      description "Specifies whether the feature Uplink-Triggered Inter-Frequency Mobility is installed in the external eNodeB.\nSet to true by the system when license for Uplink-Triggered Inter-Frequency Mobility is installed and a X2 connection exists.";
      type boolean;
    }
    leaf createdBy {
      config false;
      description "Indicates whether the MO has been created by the Automated Neighbor Relations (ANR) function or operator or X2";
      notife:notifiable-state-data true;
      type erienmnrmlrat:enum-CreatedByEutran;
    }
    list gUGroupIdList {
      min-elements 0;
      max-elements 16;
      key auto-generated-struct-key;
      leaf auto-generated-struct-key {
        type uint16;
        description "This leaf has been injected to allow for struct instances in a sequence to be ordered.";
        mandatory true;
      }
      description "A list of all globally unique group IDs to which a neighboring RBS belongs. A globally unique ID refers to a pool area.\nThe attribute is set during the RBS at X2 SETUP procedure.";
      erienmyext:enm-type STRUCT;
      uses erienmnrmlrat:struct-GUGroupIdRO;
    } // end 'list gUGroupIdList'
    leaf lastModification {
      config false;
      description "Indicates whether the MO was last modified by the Automated Neighbor Relations (ANR) function or operator or X2 and if the MO is to be deleted who triggered the deletion";
      notife:notifiable-state-data true;
      type erienmnrmlrat:enum-LastModificationEutran;
    }
    leaf masterEnbFunctionId {
      description "The ID of the eNodeBFunction that this MO represents, in particular for automatically-created ExternalENbFunctionId managed objects.";
      type erienmnrmlrat:ddt-Lrat_ExternalENodeBFunction_masterEnbFunctionId;
      default "";
    }
    leaf eSCellCapacityScaling {
      description "Scaling factor for SCell subscription capacity. Used to decrease CA attraction of cells belonging to indicated eNodeB if cell is used as external SCell for CA.";
      type erienmnrmlrat:ddt-Lrat_ExternalENodeBFunction_eSCellCapacityScaling;
      default 100;
    }
  } // end 'grouping moc-ExternalENodeBFunction'
  grouping moc-PmEventService-keys {
    description "Key(s) for MOC PmEventService";
    leaf id {
      erienmyext:no-notification;
      description "The value component of the RDN.\n";
      mandatory true;
      yexte:ecim-name pmEventServiceId;
      type string;
    }
  } // end 'grouping moc-PmEventService-keys'
  grouping moc-PmEventService {
    description "Contains the parameters for PM event handling functions.\n\nThe RDN of this MO is PmEventService=1.";
    leaf ueTraceFileSize {
      description "ueTraceFileSize is calculated basing on compression factor equal to 8. In some outstanding conditions it is possible that the maximum size could exceed definition in MOM attribute, depending of content of ROP file.\nIf ueTraceFileSize is reached during ROP, UE trace recording stops until next ROP.";
      yexte:takes-effect "At the next ROP.";
      yexte:dependencies "ueTraceFileSize <= totalUeTraceStorageSize";
      type erienmnrmlrat:ddt-Lrat_PmEventService_ueTraceFileSize;
      default 1000;
    }
    leaf totalCellTraceStorageSize {
      description "Total available storage for the cell trace recording files. The actual limit may be slightly offset from this value due to the fact that the compressed file size is approximated by the system.";
      yexte:takes-effect "At the next ROP.";
      yexte:dependencies "totalCellTraceStorageSize >= cellTraceFileSize AND totalCellTraceStorageSize <= totalEventStorageSize";
      type erienmnrmlrat:ddt-Lrat_PmEventService_totalCellTraceStorageSize;
      default 80000;
    }
    leaf cellTraceHighPrioReserve {
      description "The percentage of total cell trace storage (totalCellTraceStorageSize) reserved for high-priority scanners.\nThis means that no events from low-priority scanners are stored in the file when the storage limit is reached for the sum of the low-priority scanners:\ntotalCellTraceStorageSize - (cellTraceHighPrioReserv / 100) * totalCellTraceStorageSize.\nHigh-priority scanner files are not limited to the reserved area for high priority scanners. These files can also be stored in the non-reserved area together with the low-priority scanner files. When the default value of zero is set, the high- and low-priority share the totalCellTraceStorageSize for storing cell trace events.";
      yexte:takes-effect "At the next ROP.";
      type erienmnrmlrat:ddt-Lrat_PmEventService_cellTraceHighPrioReserve;
      default 0;
    }
    leaf cellTraceFileSize {
      description "cellTraceFileSize is calculated basing on compression factor equal to 8. In some outstanding conditions it is possible that the maximum size could exceed definition in MOM attribute, depending of content of ROP file.\nIf the cellTraceFileSize is reached within a specific Reporting Output Period (ROP), cell trace recording stops until the next ROP begins.";
      yexte:takes-effect "At the next ROP.";
      yexte:dependencies "cellTraceFileSize <= totalCellTraceStorageSize";
      type erienmnrmlrat:ddt-Lrat_PmEventService_cellTraceFileSize;
      default 1000;
    }
    list streamStatusPmCellTrace {
      min-elements 0;
      max-elements 6;
      key auto-generated-struct-key;
      leaf auto-generated-struct-key {
        type uint16;
        description "This leaf has been injected to allow for struct instances in a sequence to be ordered.";
        mandatory true;
      }
      description "List of status on PM Cell Trace streams and file writing\n";
      erienmyext:enm-type STRUCT;
      uses erienmnrmlrat:struct-TraceStreamStructRO;
    } // end 'list streamStatusPmCellTrace'
    leaf-list eventsExcludedFromUeTrace {
      min-elements 0;
      max-elements 2;
      description "List of vendor specific events that are excluded from UE trace ROP files.\nUser can add and delete events to/from this list. This frees UE trace capacity for included events.\nAn empty list causes no events to be excluded.";
      yexte:takes-effect "New connection";
      type erienmnrmlrat:enum-PmEventGroup;
      default S1_PAGING;
    }
    leaf totalEventStorageSize {
      description "The total storage that the observability mechanisms can use to store information about the collected event data.\nThis means that the total size of the cell trace and UE trace files stored should be less than the value of this attribute. The actual limit may be slightly offset from this value due to the fact that the compressed file size is approximated by the system.";
      yexte:takes-effect "At the next ROP.";
      yexte:dependencies "totalEventStorageSize >= totalCellTraceStorageSize + totalUeTraceStorageSize";
      type erienmnrmlrat:ddt-Lrat_PmEventService_totalEventStorageSize;
      default 100000;
    }
    leaf totalUeTraceStorageSize {
      description "Total available storage for UE trace recording files. Actual limit can differ slightly from value because system approximates compressed file size.";
      yexte:takes-effect "At the next ROP.";
      yexte:dependencies "totalUeTraceStorageSize >= ueTraceFileSize AND totalUeTraceStorageSize <= totalEventStorageSize.";
      type erienmnrmlrat:ddt-Lrat_PmEventService_totalUeTraceStorageSize;
      default 16000;
    }
    leaf streamPortPmUeTrace {
      description "Port on target for UE trace streaming over the user datagram protocol port.";
      yexte:takes-effect "New connection";
      type erienmnrmlrat:ddt-Lrat_PmEventService_streamPortPmUeTrace;
      default 51543;
    }
    leaf cellTracePeriodicReport {
      description "Controls Periodic Measurement Reporting functionality.";
      yexte:disturbances "Changing this attribute can affect traffic. More data is generated for the cell traces.";
      type boolean;
      default false;
    }
    leaf thpFilterThresholdDl {
      status deprecated {
        yexte:status-information "Since 18.Q3. Has no functional behavior. Planned to be removed.";
      }
      description "Threshold for DL UE throughput measurements. Only bursts with transmitted volume larger than or equal to the threshold are included in the throughput measurement. The counters pmMacUeThpVolDl, pmMacUeThpTimeDl, pmMacUeThpDlDistr, pmMacDrbThpTimeDlQci and pmPdcpVolDlDrbFiltQci are based on filtered throughput measurements.";
      type erienmnrmlrat:enum-ThpFilterDlVolume;
      default FILTER_THRESH_70000;
    }
    leaf streamStatusNotification {
      description "Turns on or off stream status notifications.";
      type boolean;
      default true;
    }
    list streamStatusPmUeTrace {
      min-elements 0;
      max-elements 16;
      key auto-generated-struct-key;
      leaf auto-generated-struct-key {
        type uint16;
        description "This leaf has been injected to allow for struct instances in a sequence to be ordered.";
        mandatory true;
      }
      description "List of status on PM UE Trace streams and file writing.";
      erienmyext:enm-type STRUCT;
      uses erienmnrmlrat:struct-TraceStreamStructRO;
    } // end 'list streamStatusPmUeTrace'
    leaf ueTrExcludeNonRacUeRefEvents {
      description "If true, events with unavailable RacUeRef are excluded from UE trace log.";
      yexte:takes-effect "New connection";
      type boolean;
      default false;
    }
  } // end 'grouping moc-PmEventService'
  grouping moc-IdleModePrioAtRelease-keys {
    description "Key(s) for MOC IdleModePrioAtRelease";
    leaf id {
      erienmyext:no-notification;
      description "The value component of the RDN.";
      mandatory true;
      yexte:ecim-name idleModePrioAtReleaseId;
      type string;
    }
  } // end 'grouping moc-IdleModePrioAtRelease-keys'
  grouping moc-IdleModePrioAtRelease {
    description "Contains distribution model data for the Pre-Distribution At Release feature that controls the priority of the frequencies in IdleModeMobilityControlInfo in the RRC Connection Release message.";
    container lowLoadDistributionInfo {
      description "Contains the distribution models used at low load level in a cell.";
      erienmyext:enm-type STRUCT;
      uses erienmnrmlrat:struct-DistributionInfo;
    } // end 'container lowLoadDistributionInfo'
    container catmFreqDistributionInfo {
      description "CAT-M UE distribution model.";
      erienmyext:enm-type STRUCT;
      uses erienmnrmlrat:struct-DistributionInfo;
    } // end 'container catmFreqDistributionInfo'
    leaf mediumLoadThreshold {
      description "Threshold value for when the distribution model at medium load is used.";
      yexte:disturbances "Changing this attribute can affect traffic.";
      type erienmnrmlrat:ddt-Lrat_IdleModePrioAtRelease_mediumLoadThreshold;
      default 400;
    }
    leaf lowLoadThreshold {
      description "Threshold value for when the distribution model at low load is used.";
      yexte:disturbances "Changing this attribute can affect traffic.";
      type erienmnrmlrat:ddt-Lrat_IdleModePrioAtRelease_lowLoadThreshold;
      default 0;
    }
    container lowMediumLoadDistributionInfo {
      description "Contains the distribution models used at low-medium load level in a cell.";
      erienmyext:enm-type STRUCT;
      uses erienmnrmlrat:struct-DistributionInfo;
    } // end 'container lowMediumLoadDistributionInfo'
    container highLoadDistributionInfo {
      description "Contains the distribution models used at high load level in a cell.";
      erienmyext:enm-type STRUCT;
      uses erienmnrmlrat:struct-DistributionInfo;
    } // end 'container highLoadDistributionInfo'
    leaf highLoadThreshold {
      description "Threshold value for when the distribution model at high load is used.";
      yexte:disturbances "Changing this attribute can affect traffic.";
      type erienmnrmlrat:ddt-Lrat_IdleModePrioAtRelease_highLoadThreshold;
      default 800;
    }
    container mediumHighLoadDistributionInfo {
      description "Contains the distribution models used at medium-high load level in a cell.";
      erienmyext:enm-type STRUCT;
      uses erienmnrmlrat:struct-DistributionInfo;
    } // end 'container mediumHighLoadDistributionInfo'
    leaf-list reservedBy {
      min-elements 0;
      erienmyext:no-notification;
      config false;
      description "Contains a list of MO instances that reserve this MO instance.";
      erienmyext:enm-type MOREF;
      type string;
    }
    leaf mediumHighLoadThreshold {
      description "Threshold value for when the distribution model at medium-high load is used.";
      yexte:disturbances "Changing this attribute can affect traffic.";
      type erienmnrmlrat:ddt-Lrat_IdleModePrioAtRelease_mediumHighLoadThreshold;
      default 600;
    }
    container mediumLoadDistributionInfo {
      description "Contains the distribution models used at medium load level in a cell.";
      erienmyext:enm-type STRUCT;
      uses erienmnrmlrat:struct-DistributionInfo;
    } // end 'container mediumLoadDistributionInfo'
    leaf lowMediumLoadThreshold {
      description "Threshold value for when the distribution model at low-medium load is used.";
      yexte:disturbances "Changing this attribute can affect traffic.";
      type erienmnrmlrat:ddt-Lrat_IdleModePrioAtRelease_lowMediumLoadThreshold;
      default 200;
    }
  } // end 'grouping moc-IdleModePrioAtRelease'
  grouping moc-ReportConfigInterRatPm-keys {
    description "Key(s) for MOC ReportConfigInterRatPm";
    leaf id {
      erienmyext:no-notification;
      description "The value component of the RDN.";
      mandatory true;
      yexte:ecim-name reportConfigInterRatPmId;
      type string;
    }
  } // end 'grouping moc-ReportConfigInterRatPm-keys'
  grouping moc-ReportConfigInterRatPm {
    description "Contains Report Configuration settings for UE measurements on inter-Rat (GERAN or UTRAN) frequencies initiated by PM.";
    leaf timeToTriggerPm {
      description "Time during which specific event criteria must be met to trigger a measurement report.";
      yexte:takes-effect "New connection";
      yexte:dependencies "Used only when measSelectionInterRatPm is set to EVENT_B1 or EVENT_B2.";
      type erienmnrmlrat:ddt-Lrat_ReportConfigInterRatPm_timeToTriggerPm;
      default 640;
    }
    leaf triggerQuantityPm {
      description "Quantity that triggers PM-initiated IRAT measurements.";
      yexte:takes-effect "New connection";
      type erienmnrmlrat:enum-TriggerQuantity;
      default RSRP;
    }
    leaf reportAmountPm {
      description "Number of periodical reports.\nValue 0, reports are sent as long as event is fulfilled.";
      yexte:takes-effect "New connection";
      type erienmnrmlrat:ddt-Lrat_ReportConfigInterRatPm_reportAmountPm;
      default 0;
    }
    leaf b1ThresholdRscpUtraPm {
      description "UTRAN RSCP threshold value for eventB1.";
      yexte:takes-effect "New connection";
      yexte:dependencies "Used only when UeMeasControl::measQuantityUtraFDD is set to RSCP, ratSelectionPm is set to UTRAN and measSelectionInterRatPm is set to EVENT_B1.";
      type erienmnrmlrat:ddt-Lrat_ReportConfigInterRatPm_b1ThresholdRscpUtraPm;
      default -115;
    }
    leaf b2Threshold2RscpUtraPm {
      description "UTRAN RSCP threshold2 value for eventB2.";
      yexte:takes-effect "New connection";
      yexte:dependencies "Used only when UeMeasControl::measQuantityUtraFDD is set to RSCP, ratSelectionPm is set to UTRAN and measSelectionInterRatPm is set to EVENT_B2.";
      type erienmnrmlrat:ddt-Lrat_ReportConfigInterRatPm_b2Threshold2RscpUtraPm;
      default -115;
    }
    leaf ratSelectionPm {
      description "Whether selected inter-Rat is GERAN or UTRAN.";
      yexte:takes-effect "New connection";
      type erienmnrmlrat:enum-Rat;
      default UTRAN;
    }
    leaf reportIntervalPm {
      description "Interval for event-triggered periodical reporting.";
      yexte:takes-effect "New connection";
      type erienmnrmlrat:enum-ReportInterval;
      default MIN_1;
    }
    leaf b2Threshold2GeranPm {
      description "GERAN threshold2 value for eventB2.";
      yexte:takes-effect "New connection";
      yexte:dependencies "Used only when ratSelectionPm is set to GERAN and measSelectionInterRatPm is set to EVENT_B2.";
      type erienmnrmlrat:ddt-Lrat_ReportConfigInterRatPm_b2Threshold2GeranPm;
      default -110;
    }
    leaf b2Threshold1RsrpPm {
      description "RSRP threshold1 value for eventB2.";
      yexte:takes-effect "New connection";
      yexte:dependencies "Used only when triggerQuantityPm is set to RSRP and measSelectionInterRatPm is set to EVENT_B2.";
      type erienmnrmlrat:ddt-Lrat_ReportConfigInterRatPm_b2Threshold1RsrpPm;
      default -140;
    }
    leaf hysteresisPm {
      description "Hysteresis value for trigger condition for measurement report.";
      yexte:takes-effect "New connection";
      yexte:dependencies "Used only when measSelectionInterRatPm is set to EVENT_B1 or EVENT_B2.";
      type erienmnrmlrat:ddt-Lrat_ReportConfigInterRatPm_hysteresisPm;
      default 10;
    }
    leaf b2Threshold1RsrqPm {
      description "RSRQ threshold1 value for eventB2.";
      yexte:takes-effect "New connection";
      yexte:dependencies "Used only when triggerQuantityPm is set to RSRQ and measSelectionInterRatPm is set to EVENT_B2.";
      type erienmnrmlrat:ddt-Lrat_ReportConfigInterRatPm_b2Threshold1RsrqPm;
      default -195;
    }
    leaf measSelectionInterRatPm {
      description "MO measurement type. Options B1-B2 represent respective thresholds that trigger these events.\nIf PERIODICAL, periodical measurements occur with no specific trigger. Periodical measurements limits reporting to strongest cells.";
      yexte:takes-effect "New connection";
      type erienmnrmlrat:enum-MeasSelectionIrat;
      default PERIODICAL;
    }
    leaf-list reservedBy {
      min-elements 0;
      config false;
      description "Contains a list of MO instances that reserve this MO instance.";
      yexte:dependencies "The managed object cannot be deleted if it is reserved.";
      notife:notifiable-state-data true;
      erienmyext:enm-type MOREF;
      type string;
    }
    leaf b1ThresholdGeranPm {
      description "GERAN threshold value for eventB1.";
      yexte:takes-effect "New connection";
      yexte:dependencies "Used only when ratSelectionPm is set to GERAN and measSelectionInterRatPm is set to EVENT_B1.";
      type erienmnrmlrat:ddt-Lrat_ReportConfigInterRatPm_b1ThresholdGeranPm;
      default -110;
    }
    leaf b1ThresholdEcNoUtraPm {
      description "UTRAN Ec/No threshold value for eventB1.";
      yexte:takes-effect "New connection";
      yexte:dependencies "Used only when UeMeasControl::measQuantityUtraFDD is set to ECNO, ratSelectionPm is set to UTRAN and measSelectionInterRatPm is set to EVENT_B1. Not applicable for UTRA TDD.";
      type erienmnrmlrat:ddt-Lrat_ReportConfigInterRatPm_b1ThresholdEcNoUtraPm;
      default -240;
    }
    leaf maxReportCellsPm {
      description "Maximum number of cells included in measurement report for PM Initiated UE Measurements.";
      yexte:takes-effect "New connection";
      type erienmnrmlrat:ddt-Lrat_ReportConfigInterRatPm_maxReportCellsPm;
      default 4;
    }
    leaf b2Threshold2EcNoUtraPm {
      description "UTRAN Ec/No threshold2 value for eventB2.";
      yexte:takes-effect "New connection";
      yexte:dependencies "Used only when UeMeasControl::measQuantityUtraFDD is set to ECNO, ratSelectionPm is set to UTRAN and measSelectionInterRatPm is set to EVENT_B2. Not applicable for UTRA TDD.";
      type erienmnrmlrat:ddt-Lrat_ReportConfigInterRatPm_b2Threshold2EcNoUtraPm;
      default -240;
    }
  } // end 'grouping moc-ReportConfigInterRatPm'
  grouping moc-EUtranCellRelationUnlicensed-keys {
    description "Key(s) for MOC EUtranCellRelationUnlicensed";
    leaf id {
      erienmyext:no-notification;
      description "The value component of the RDN.";
      mandatory true;
      yexte:ecim-name eUtranCellRelationUnlicensedId;
      type string;
    }
  } // end 'grouping moc-EUtranCellRelationUnlicensed-keys'
  grouping moc-EUtranCellRelationUnlicensed {
    description "MO handles relationship between two neighboring, unlicensed EUTRAN cells.";
    leaf esCellCaConfigurationAvail {
      config false;
      description "Indicates if cell is able to serve as ESCell.\nExternalEUtranCellFDD/TDD::remoteCellState must be operState ENABLED.\nInter-eNodeB CA license must be active and baseband-to-baseband GTPU tunnel connection between ESCell and this eNodeB must be enabled, or elastic RAN license must be active and baseband-to-baseband connections must be enabled.\nIf not, no UEs are configured with this candidate. UEs already configured with this cell can retain the configuration.\nIf SCell is not external, this attribute is NOT_APPLICABLE.";
      yexte:dependencies "Depends on feature license and success of tunnels in TermPointToLbm (for the IeNB-CA feature only), TermPointToENB::interEnbSwCompatibilityState and on ExternalEUtranCellFDD/TDD::remoteCellState.";
      notife:notifiable-state-data true;
      type erienmnrmlrat:enum-EScellState;
    }
    leaf neighborCellRef {
      yexte:restricted;
      description "Reference to an instance of EUtranCellFDD, ExternalEUtranCellFDD, EUtranCellTDD or ExternalEUtranCellTDD managed object.";
      mandatory true;
      erienmyext:enm-type MOREF;
      type string;
    }
    leaf sCellPriority {
      description "Used to select SCell within frequency carrier. Highest priority SCell selected during initial blind SCell selection. 0 is lowest priority. -1 means cell is excluded from blind SCell selection.";
      yexte:takes-effect "New connection";
      yexte:dependencies "Only applicable when CarrierAggregationFunction::dynamicSCellSelectionMethod == PRIORITIZED.";
      type erienmnrmlrat:ddt-Lrat_EUtranCellRelationUnlicensed_sCellPriority;
      default 7;
    }
    leaf coverageIndicator {
      description "Indicates whether the coverage area of the cell indicated by the relation has approximately the same coverage area (overlap) as this cell, or whether it fully covers this cell, or if it is fully contained in this cell.";
      yexte:disturbances "Changes may affect traffic";
      type erienmnrmlrat:enum-SupportedCoverage;
      default NONE;
    }
    leaf earfcn {
      description "Unlicensed carrier EARFCN used.";
      yexte:disturbances "Changes may affect traffic. If the earfcn is changed the cell will be automatic locked/unlocked, if needed.";
      yexte:takes-effect "Next cell unlock";
      type erienmnrmlrat:ddt-Lrat_EUtranCellRelationUnlicensed_earfcn;
      default 0;
    }
  } // end 'grouping moc-EUtranCellRelationUnlicensed'
  grouping moc-GeranFrequency-keys {
    description "Key(s) for MOC GeranFrequency";
    leaf id {
      erienmyext:no-notification;
      description "The value component of the Relative Distinguished Name (RDN).\n";
      mandatory true;
      yexte:ecim-name geranFrequencyId;
      type string;
    }
  } // end 'grouping moc-GeranFrequency-keys'
  grouping moc-GeranFrequency {
    description "This Managed Object contains information of a specific Geran frequency.";
    leaf userLabel {
      description "Label for free use.\n";
      type erienmnrmlrat:ddt-Lrat_GeranFrequency_userLabel;
    }
    leaf bandIndicator {
      yexte:restricted;
      description "Indicates how to interpret an associated GERAN carrier ARFCN.\nThe parameter indicates the GERAN frequency band when the ARFCN value is either a DCS 1800 or a PCS 1900 carrier frequency. For ARFCN values not associated with one of these bands, the indicator has no meaning.";
      type erienmnrmlrat:enum-BandIndicator;
      default DCS_1800;
    }
    leaf-list reservedBy {
      min-elements 0;
      max-elements 16;
      config false;
      description "A list of references to instances of ExternalGeranCell.";
      notife:notifiable-state-data true;
      erienmyext:enm-type MOREF;
      type string;
    }
    leaf arfcnValueGeranDl {
      yexte:restricted;
      description "The GERAN BCCH carrier frequency.\nApplicable ARFCN for DL GERAN carrier frequency, as defined in 3GPP TS 45.005.";
      mandatory true;
      type erienmnrmlrat:ddt-Lrat_GeranFrequency_arfcnValueGeranDl;
    }
    leaf-list geranFreqGroupRef {
      min-elements 0;
      max-elements 192;
      description "A list of references to instances of GeranFreqGroup.";
      erienmyext:enm-type MOREF;
      type string;
    }
  } // end 'grouping moc-GeranFrequency'
  grouping moc-SignalingRadioBearer-keys {
    description "Key(s) for MOC SignalingRadioBearer";
    leaf id {
      erienmyext:no-notification;
      description "The value component of the RDN.";
      mandatory true;
      yexte:ecim-name signalingRadioBearerId;
      type string;
    }
  } // end 'grouping moc-SignalingRadioBearer-keys'
  grouping moc-SignalingRadioBearer {
    description "Signaling Radio Bearer configuration.\n\nThe RDN of this MO is SignalingRadioBearer=1.";
    leaf tReorderingUl {
      description "This timer is used by the receiving end of the Acknowledged Mode (AM) Radio Link Control (RLC) entity in eNB for SRB1 or SRB2, to detect loss of uplink RLC protocol data units at lower layers.";
      yexte:disturbances "Low values can cause high drop rate.";
      yexte:takes-effect "New connection.";
      type erienmnrmlrat:ddt-Lrat_SignalingRadioBearer_tReorderingUl;
      default 35;
    }
    leaf tReorderingDl {
      description "Time before sending STATUS report when a Sequence Number is outstanding.\n";
      yexte:takes-effect "New connection.";
      type erienmnrmlrat:ddt-Lrat_SignalingRadioBearer_tReorderingDl;
      default 35;
    }
    leaf tPollRetransmitUl {
      description "Time lapsed before request for new poll if no STATUS report arrives for the Sequence Number that is contained in the UL RLC Data PDU where the poll bit is set.";
      yexte:disturbances "High values can cause high drop rate.";
      yexte:takes-effect "New connection.";
      type erienmnrmlrat:ddt-Lrat_SignalingRadioBearer_tPollRetransmitUl;
      default 80;
    }
    leaf tPollRetransmitDl {
      description "Time lapsed before request for new poll if no STATUS report arrives for the Sequence Number that is contained in the DL RLC Data PDU where the poll bit is set.";
      yexte:takes-effect "Cell lock/unlock";
      type erienmnrmlrat:ddt-Lrat_SignalingRadioBearer_tPollRetransmitDl;
      default 80;
    }
    leaf dlMaxRetxThreshold {
      description "Maximum number RLC re-transmissions in DL before stopping and indicating to RRC that the RLC threshold is reached.";
      yexte:takes-effect "Cell lock/unlock";
      type erienmnrmlrat:ddt-Lrat_SignalingRadioBearer_dlMaxRetxThreshold;
      default 8;
    }
    leaf ulMaxRetxThreshold {
      description "Maximum number RLC re-transmissions in UL before stopping and indicating to RRC that the RLC threshold is reached.";
      yexte:disturbances "Low values can cause high drop rate.";
      yexte:takes-effect "New connection.";
      type erienmnrmlrat:ddt-Lrat_SignalingRadioBearer_ulMaxRetxThreshold;
      default 8;
    }
  } // end 'grouping moc-SignalingRadioBearer'
  grouping moc-NbIdleModeLoadDistr-keys {
    description "Key(s) for MOC NbIdleModeLoadDistr";
    leaf id {
      erienmyext:no-notification;
      description "The value component of the RDN.";
      mandatory true;
      yexte:ecim-name nbIdleModeLoadDistrId;
      type string;
    }
  } // end 'grouping moc-NbIdleModeLoadDistr-keys'
  grouping moc-NbIdleModeLoadDistr {
    description "Distribution model data for the Pre-Distribution At Release feature that controls the priority of the frequencies in redirectedCarrierInfo in the RRC Connection Release message.";
    leaf-list nbCarrierFreqList {
      min-elements 0;
      max-elements 8;
      description "UEs must be distributed between these frequencies. Position of the elements in list must correspond to position of elements in nbFreqDistributionList.\nUndefined value: 0";
      yexte:dependencies "Must have the same length as nbFreqDistributionList.";
      type erienmnrmlrat:ddt-Lrat_NbIdleModeLoadDistr_nbCarrierFreqList;
    }
    leaf-list nbFreqDistributionList {
      min-elements 0;
      max-elements 8;
      description "Percentage of UEs to be released to a certain frequency. Position of elements in list must correspond to position of elements in nbCarrierFreqList.\nUndefined value: 0";
      yexte:dependencies "Must have the same length as nbCarrierFreqList. Sum of percentages cannot exceed 100%.";
      type erienmnrmlrat:ddt-Lrat_NbIdleModeLoadDistr_nbFreqDistributionList;
    }
  } // end 'grouping moc-NbIdleModeLoadDistr'
  grouping moc-UtraNetwork-keys {
    description "Key(s) for MOC UtraNetwork";
    leaf id {
      erienmyext:no-notification;
      description "The value component of the Relative Distinguished Name (RDN).\n";
      mandatory true;
      yexte:ecim-name utraNetworkId;
      type string;
    }
  } // end 'grouping moc-UtraNetwork-keys'
  grouping moc-UtraNetwork {
    description "This managed object represents a Utra network.\n";
    leaf userLabel {
      description "Label for free use.\n";
      type erienmnrmlrat:ddt-Lrat_UtraNetwork_userLabel;
    }
  } // end 'grouping moc-UtraNetwork'
  grouping moc-ReportConfigEUtraInterFreqPm-keys {
    description "Key(s) for MOC ReportConfigEUtraInterFreqPm";
    leaf id {
      erienmyext:no-notification;
      description "The value component of the RDN.";
      mandatory true;
      yexte:ecim-name reportConfigEUtraInterFreqPmId;
      type string;
    }
  } // end 'grouping moc-ReportConfigEUtraInterFreqPm-keys'
  grouping moc-ReportConfigEUtraInterFreqPm {
    description "Contains Report Configuration settings for UE measurements on EUTRAN inter-frequencies initiated by PM.";
    leaf a5Threshold2RsrqPm {
      description "RSRQ threshold2 value for eventA5.";
      yexte:takes-effect "New connection";
      yexte:dependencies "Used only when triggerQuantityPm is set to RSRQ and measSelectionEUtraPm is set to EVENT_A5.";
      type erienmnrmlrat:ddt-Lrat_ReportConfigEUtraInterFreqPm_a5Threshold2RsrqPm;
      default -195;
    }
    leaf timeToTriggerPm {
      description "Time during which specific event criteria must be met to trigger a measurement report.";
      yexte:takes-effect "New connection";
      yexte:dependencies "Used only when measSelectionEUtraPm is set to EVENT_A1, EVENT_A2, EVENT_A3, EVENT_A4, EVENT_A5 or EVENT_A6.";
      type erienmnrmlrat:ddt-Lrat_ReportConfigEUtraInterFreqPm_timeToTriggerPm;
      default 640;
    }
    leaf triggerQuantityPm {
      description "Quantity that triggers PM-initiated EUtra measurements.";
      yexte:takes-effect "New connection";
      type erienmnrmlrat:enum-TriggerQuantity;
      default RSRP;
    }
    leaf a3OffsetPm {
      description "Offset value for eventA3.";
      yexte:takes-effect "New connection";
      yexte:dependencies "Used only when measSelectionEUtraPm is set to EVENT_A3.";
      type erienmnrmlrat:ddt-Lrat_ReportConfigEUtraInterFreqPm_a3OffsetPm;
      default 5;
    }
    leaf a3ReportOnLeavePm {
      description "If true, UE initiates measurement report procedure when cell meets leaving condition.";
      yexte:takes-effect "New connection";
      yexte:dependencies "Used only when measSelectionEUtraPm is set to EVENT_A3.";
      type boolean;
      default false;
    }
    leaf a1ThresholdRsrpPm {
      description "RSRP threshold value for eventA1.";
      yexte:takes-effect "New connection";
      yexte:dependencies "Used only when triggerQuantityPm is set to RSRP and measSelectionEUtraPm is set to EVENT_A1.";
      type erienmnrmlrat:ddt-Lrat_ReportConfigEUtraInterFreqPm_a1ThresholdRsrpPm;
      default -140;
    }
    leaf a5Threshold1RsrpPm {
      description "RSRP threshold1 value for eventA5.";
      yexte:takes-effect "New connection";
      yexte:dependencies "Used only when triggerQuantityPm is set to RSRP and measSelectionEUtraPm is set to EVENT_A5.";
      type erienmnrmlrat:ddt-Lrat_ReportConfigEUtraInterFreqPm_a5Threshold1RsrpPm;
      default -140;
    }
    leaf a5Threshold1RsrqPm {
      description "RSRQ threshold1 value for eventA5.";
      yexte:takes-effect "New connection";
      yexte:dependencies "Used only when triggerQuantityPm is set to RSRQ and measSelectionEUtraPm is set to EVENT_A5.";
      type erienmnrmlrat:ddt-Lrat_ReportConfigEUtraInterFreqPm_a5Threshold1RsrqPm;
      default -195;
    }
    leaf reportAmountPm {
      description "Number of periodical reports.\nValue 0, reports are sent as long as event is fulfilled.";
      yexte:takes-effect "New connection";
      type erienmnrmlrat:ddt-Lrat_ReportConfigEUtraInterFreqPm_reportAmountPm;
      default 0;
    }
    leaf measSelectionEUtraPm {
      description "MO measurement type. Options A1-A6 represent respective thresholds or offsets that trigger these events.\nIf PERIODICAL, periodical measurements occur with no specific trigger. Periodical measurements limits reporting to strongest cells.";
      yexte:takes-effect "New connection";
      type erienmnrmlrat:enum-MeasSelectionEUtra;
      default PERIODICAL;
    }
    leaf a6OffsetPm {
      description "Offset value for eventA6.";
      yexte:takes-effect "New connection";
      yexte:dependencies "Used only when measSelectionEUtraPm is set to EVENT_A6.";
      type erienmnrmlrat:ddt-Lrat_ReportConfigEUtraInterFreqPm_a6OffsetPm;
      default 30;
    }
    leaf a1ThresholdRsrqPm {
      description "RSRQ threshold value for eventA1.";
      yexte:takes-effect "New connection";
      yexte:dependencies "Used only when triggerQuantityPm is set to RSRQ and measSelectionEUtraPm is set to EVENT_A1.";
      type erienmnrmlrat:ddt-Lrat_ReportConfigEUtraInterFreqPm_a1ThresholdRsrqPm;
      default -195;
    }
    leaf a5Threshold2RsrpPm {
      description "RSRP threshold2 value for eventA5.";
      yexte:takes-effect "New connection";
      yexte:dependencies "Used only when triggerQuantityPm is set to RSRP and measSelectionEUtraPm is set to EVENT_A5.";
      type erienmnrmlrat:ddt-Lrat_ReportConfigEUtraInterFreqPm_a5Threshold2RsrpPm;
      default -140;
    }
    leaf a2ThresholdRsrpPm {
      description "RSRP threshold value for eventA2.";
      yexte:takes-effect "New connection";
      yexte:dependencies "Used only when triggerQuantityPm is set to RSRP and measSelectionEUtraPm is set to EVENT_A2.";
      type erienmnrmlrat:ddt-Lrat_ReportConfigEUtraInterFreqPm_a2ThresholdRsrpPm;
      default -140;
    }
    leaf reportIntervalPm {
      description "Interval for event-triggered periodical reporting.";
      yexte:takes-effect "New connection";
      type erienmnrmlrat:enum-ReportInterval;
      default MIN_1;
    }
    leaf a2ThresholdRsrqPm {
      description "RSRQ threshold value for eventA2.";
      yexte:takes-effect "New connection";
      yexte:dependencies "Used only when triggerQuantityPm is set to RSRQ and measSelectionEUtraPm is set to EVENT_A2.";
      type erienmnrmlrat:ddt-Lrat_ReportConfigEUtraInterFreqPm_a2ThresholdRsrqPm;
      default -195;
    }
    leaf reportQuantityPm {
      description "Quantities included in measurement report.\nValue 0, SAME_AS_TRIGGER_QUANTITY, means that same quantity as triggerQuantityPm is included in measurement report.\nValue 1, BOTH, means both RSRP and RSRQ quantities are included in measurement report.";
      yexte:takes-effect "New connection";
      type erienmnrmlrat:enum-ReportQuantity;
      default BOTH;
    }
    leaf hysteresisPm {
      description "Hysteresis value for trigger condition for measurement report.";
      yexte:takes-effect "New connection";
      yexte:dependencies "Used only when measSelectionEUtraPm is set to EVENT_A1, EVENT_A2, EVENT_A3, EVENT_A4, EVENT_A5 or EVENT_A6.";
      type erienmnrmlrat:ddt-Lrat_ReportConfigEUtraInterFreqPm_hysteresisPm;
      default 10;
    }
    leaf-list reservedBy {
      min-elements 0;
      config false;
      description "Contains a list of MO instances that reserve this MO instance.";
      yexte:dependencies "The managed object cannot be deleted if it is reserved.";
      notife:notifiable-state-data true;
      erienmyext:enm-type MOREF;
      type string;
    }
    leaf maxReportCellsPm {
      description "Maximum number of cells included in measurement report for PM Initiated UE Measurements.";
      yexte:takes-effect "New connection";
      type erienmnrmlrat:ddt-Lrat_ReportConfigEUtraInterFreqPm_maxReportCellsPm;
      default 4;
    }
    leaf a4ThresholdRsrpPm {
      description "RSRP threshold value for eventA4.";
      yexte:takes-effect "New connection";
      yexte:dependencies "Used only when triggerQuantityPm is set to RSRP and measSelectionEUtraPm is set to EVENT_A4.";
      type erienmnrmlrat:ddt-Lrat_ReportConfigEUtraInterFreqPm_a4ThresholdRsrpPm;
      default -140;
    }
    leaf a4ThresholdRsrqPm {
      description "RSRQ threshold value for eventA4.";
      yexte:takes-effect "New connection";
      yexte:dependencies "Used only when triggerQuantityPm is set to RSRQ and measSelectionEUtraPm is set to EVENT_A4.";
      type erienmnrmlrat:ddt-Lrat_ReportConfigEUtraInterFreqPm_a4ThresholdRsrqPm;
      default -195;
    }
  } // end 'grouping moc-ReportConfigEUtraInterFreqPm'
  grouping moc-ExternalEUtranCellTDD-keys {
    description "Key(s) for MOC ExternalEUtranCellTDD";
    leaf id {
      erienmyext:no-notification;
      description "The value component of the Relative Distinguished Name (RDN).\n";
      mandatory true;
      yexte:ecim-name externalEUtranCellTDDId;
      type string;
    }
  } // end 'grouping moc-ExternalEUtranCellTDD-keys'
  grouping moc-ExternalEUtranCellTDD {
    description "This managed object represents a neighbor EUTRAN cell (TDD) in another ENodeB in any MME pool.\n";
    leaf userLabel {
      description "Label for free use.\n";
      type erienmnrmlrat:ddt-Lrat_ExternalEUtranCellTDD_userLabel;
    }
    leaf masterEUtranCellTDDId {
      description "The ID of the EUtranCellTDD that this MO represents for automatically created ExternalEUtranCellTDD managed objects.";
      type erienmnrmlrat:ddt-Lrat_ExternalEUtranCellTDD_masterEUtranCellTDDId;
      default "";
    }
    leaf-list pciConflict {
      min-elements 0;
      max-elements 5;
      description "A PCI confusion exists if a source cell has relations to two neighbor cells where both neighbor cells have the same PCI and frequency. A PCI collision exists if a source cell has a relation to a neighbor cell where both the source cell and neighbor cell have the same PCI and frequency.";
      type erienmnrmlrat:enum-PciConflict;
    }
    leaf csgPhysCellId {
      status deprecated {
        yexte:status-information "Since L16B. Has no functional behavior. Planned to be removed.";
      }
      description "Physical Cell Identity for the CSG (Closed Subscriber Group). It is the start physical cell ID in the SIB4. If value is equal to 1000, it means that csg-PhysCellIdRange IE is not presented in SIB4.";
      yexte:dependencies "This attribute has a dependency to csgPhysCellIdRange.";
      type erienmnrmlrat:ddt-Lrat_ExternalEUtranCellTDD_csgPhysCellId;
      default 1000;
    }
    leaf physicalLayerCellId {
      config false;
      description "Physical-layer cell ID.";
      yexte:dependencies "Equal to 3 x physicalLayerCellIdGroup + physicalLayerSubCellId.";
      notife:notifiable-state-data true;
      type erienmnrmlrat:ddt-Lrat_ExternalEUtranCellTDD_physicalLayerCellId;
    }
    leaf csgPhysCellIdRange {
      status deprecated {
        yexte:status-information "Since L16B. Has no functional behavior. Planned to be removed.";
      }
      description "It is the range of Physical Cell Identity for the CSG (Closed Subscriber Group). The information is broadcasted in SIB4.";
      yexte:dependencies "If csgPhyscellId != 1000, csgPhysCellId + csgPhysCellIdRange <= 504";
      type erienmnrmlrat:ddt-Lrat_ExternalEUtranCellTDD_csgPhysCellIdRange;
      default 1;
    }
    leaf specialSubframePattern {
      config false;
      description "The special subframe pattern configuration for Downlink Part of Time Slot (DwPTS), Guard Period (GP), and Uplink Part of Time Slot (UpPTS) (used to control special subframe in 3GPP TS 36.211). The parameter is set by the RBS at X2 SETUP procedure.\nUndefined value: -1";
      notife:notifiable-state-data true;
      type erienmnrmlrat:ddt-Lrat_ExternalEUtranCellTDD_specialSubframePattern;
    }
    list activePlmnList {
      min-elements 0;
      max-elements 6;
      key auto-generated-struct-key;
      leaf auto-generated-struct-key {
        type uint16;
        description "This leaf has been injected to allow for struct instances in a sequence to be ordered.";
        mandatory true;
      }
      description "Lists the PLMN IDs in the external E-UTRAN cell. The list may include up to 6 PLMN IDs. The list tracks the activePlmnList in the corresponding instance of EUtranCellFDD/TDD in another RBS. It is configured by ANR when ANR feature creates the MO and then set to the PLMN Id from the CGI report. The list is updated via X2 or OSS-RC, or manually.";
      erienmyext:enm-type STRUCT;
      uses erienmnrmlrat:struct-PlmnIdentity;
    } // end 'list activePlmnList'
    leaf mfbiFreqBandIndPrioExt {
      erienmyext:no-notification;
      config false;
      description "Indicates if external cell supports additional frequency band priority. Used during handover procedure.\nUndefined value: UNDEFINED_VALUE";
      yexte:dependencies "Only takes effect if MFBI is active.";
      type erienmnrmlrat:enum-MfbiFreqBandIndPrioExt;
    }
    list pciConflictCell {
      min-elements 0;
      max-elements 5;
      key auto-generated-struct-key;
      leaf auto-generated-struct-key {
        type uint16;
        description "This leaf has been injected to allow for struct instances in a sequence to be ordered.";
        mandatory true;
      }
      description "Indicates the CGI of the other cell that is involved in the PCI collision/confusion. This value is only valid if the attribute pciConflict is \"YES\" or \"YES_CONFLICTING_CELL\".";
      erienmyext:enm-type STRUCT;
      uses erienmnrmlrat:struct-Cgi;
    } // end 'list pciConflictCell'
    leaf lbEUtranCellOffloadCapacity {
      description "This attribute indicates the offload subscription capacity associated with the EUTRAN target cell. The value is used to moderate the offload rate to the EUTRAN target cell.";
      type erienmnrmlrat:ddt-Lrat_ExternalEUtranCellTDD_lbEUtranCellOffloadCapacity;
      default 1000;
    }
    leaf isRemoveAllowed {
      description "Indicates if the Automated Neighbor Relations (ANR) function is allowed to remove this object. It does not restrict operator removal of the object. Objects created by ANR have this parameter set to true initially.";
      type boolean;
      default false;
    }
    leaf remoteCellStateEranUlComp {
      config false;
      description "Whether indicated cell can serve as external cell for Elastic RAN UL CoMP.";
      yexte:dependencies "X2 connection must be operational and software compatible. Remote cell must be operState ENABLED and adminState UNLOCKED.";
      notife:notifiable-state-data true;
      type erienmnrmlrat:enum-OperState;
    }
    leaf tac {
      description "Identifies a Tracking Area Code (TAC) of an external cell.\n";
      mandatory true;
      yexte:takes-effect "New connection";
      type erienmnrmlrat:ddt-Lrat_ExternalEUtranCellTDD_tac;
    }
    leaf channelBandwidth {
      config false;
      description "The downlink channel bandwidth in a cell that is served by a neighboring RBS. In TDD mode, the uplink bandwidth is equal to the downlink bandwidth. The attribute is set by the RBS at X2 SETUP procedure. The value 0 means there is no valid value available.";
      notife:notifiable-state-data true;
      type erienmnrmlrat:ddt-Lrat_ExternalEUtranCellTDD_channelBandwidth;
    }
    leaf sCellCaConfigurationAvailabilty {
      status deprecated {
        yexte:status-information "Since L16B. Has no functional behavior. Planned to be removed.";
      }
      erienmyext:no-notification;
      config false;
      description "Reflects whether the indicated cell is currently able to serve as an SCell. The remoteCellState must be operState ENABLED and Inter-eNodeB license must be active. As well, at least one tunnel connecting the indicated ESCell to this eNodeB must be enabled.  If not, no UEs are configured with this candidate, though UEs already configured with this cell will possibly retain the configuration.";
      yexte:dependencies "Depends on feature license and success of tunnels in TermPointToLbm, interEnbSwCompatibilityState and on remoteCellState.";
      type erienmnrmlrat:enum-OperState;
    }
    leaf eutranFrequencyRef {
      description "Refers to the EUTRAN frequency MO, EUtranFrequency. Cannot be changed as long as this MO is referred to by a EUtranCellRelation MO.";
      mandatory true;
      erienmyext:enm-type MOREF;
      type string;
    }
    leaf freqBand {
      config false;
      description "The primary frequency band the cell belongs to according to its defined EARFCN. This frequency band indicator is broadcasted to the UEs in SystemInformationBlockType1.";
      notife:notifiable-state-data true;
      type erienmnrmlrat:ddt-Lrat_ExternalEUtranCellTDD_freqBand;
    }
    leaf physicalLayerSubCellId {
      description "The physical-layer cell identity group. Physical-layer cell IDs are grouped into 168 unique groups, each group containing 3 unique subidentities.";
      mandatory true;
      type erienmnrmlrat:ddt-Lrat_ExternalEUtranCellTDD_physicalLayerSubCellId;
    }
    list pciDetectingCell {
      min-elements 0;
      max-elements 5;
      key auto-generated-struct-key;
      leaf auto-generated-struct-key {
        type uint16;
        description "This leaf has been injected to allow for struct instances in a sequence to be ordered.";
        mandatory true;
      }
      description "Indicates the CGI of the cell that detected the PCI collision/confusion. This value is only valid if the corresponding attribute pciConflict is \"YES\" or \"YES_CONFLICTING_CELL\". The first cell in the pciDetectingCell list corresponds to the first cell in the pciConflictCell list and the first value of pciConflict. The second cell in the pciDetectingCell list corresponds to the second cell in the pciConflictCell list and the first value of pciConflict.";
      erienmyext:enm-type STRUCT;
      uses erienmnrmlrat:struct-Cgi;
    } // end 'list pciDetectingCell'
    leaf timeOfCreation {
      erienmyext:no-notification;
      config false;
      description "Indicates the time and date when the MO was created.\nFormat: YYYY-MM-DD HH:MM:SS";
      type erienmnrmlrat:ddt-Lrat_ExternalEUtranCellTDD_timeOfCreation;
    }
    leaf subframeAssignment {
      config false;
      description "The assignment of uplink and downlink subframes for the TDD frame structure (called UL/DL configuration in 3GPP TS 36.211). The parameter is set by the RBS at X2 SETUP procedure.\nUndefined value: -1";
      notife:notifiable-state-data true;
      type erienmnrmlrat:ddt-Lrat_ExternalEUtranCellTDD_subframeAssignment;
    }
    leaf physicalLayerCellIdGroup {
      description "The physical-layer cell identity group. Physical-layer cell IDs are grouped into 168 unique groups, each group containing 3 unique subidentities.";
      mandatory true;
      type erienmnrmlrat:ddt-Lrat_ExternalEUtranCellTDD_physicalLayerCellIdGroup;
    }
    leaf timeOfLastModification {
      config false;
      description "Indicates the time and date when the MO was last modified.\nFormat: YYYY-MM-DD HH:MM:SS";
      notife:notifiable-state-data true;
      type erienmnrmlrat:ddt-Lrat_ExternalEUtranCellTDD_timeOfLastModification;
    }
    leaf remoteCellStateInterEnbUlComp {
      erienmyext:no-notification;
      config false;
      description "Whether indicated cell can serve as external cell for inter-eNodeB UL CoMP.";
      yexte:dependencies "X2 connection must be operational and software compatible. Remote cell must be operState ENABLED and adminState UNLOCKED.";
      type erienmnrmlrat:enum-OperState;
    }
    leaf-list additionalFreqBandList {
      min-elements 0;
      max-elements 8;
      config false;
      description "A list of additional frequency bands the cell belongs to, not including the frequency band indicated by the EARFCN value of the cell (primary frequency band). The list is automatically set by the eNB.";
      notife:notifiable-state-data true;
      type erienmnrmlrat:ddt-Lrat_ExternalEUtranCellTDD_additionalFreqBandList;
    }
    leaf createdBy {
      config false;
      description "Indicates whether the MO has been created by the Automated Neighbor Relations (ANR) function or operator or X2";
      notife:notifiable-state-data true;
      type erienmnrmlrat:enum-CreatedByEutran;
    }
    leaf-list reservedBy {
      min-elements 0;
      config false;
      description "Lists the EUtranCellRelation managed object instances that reserve this managed object instance.";
      yexte:dependencies "The managed object cannot be deleted if it is reserved.";
      notife:notifiable-state-data true;
      erienmyext:enm-type MOREF;
      type string;
    }
    leaf lastModification {
      config false;
      description "Indicates whether the MO was last modified by the Automated Neighbor Relations (ANR) function or operator or X2 and if the MO is to be deleted who triggered the deletion";
      notife:notifiable-state-data true;
      type erienmnrmlrat:enum-LastModificationEutran;
    }
    list commonSFAllocList {
      min-elements 0;
      max-elements 8;
      key auto-generated-struct-key;
      leaf auto-generated-struct-key {
        type uint16;
        description "This leaf has been injected to allow for struct instances in a sequence to be ordered.";
        mandatory true;
      }
      description "Shows the subframes that are reserved for MBSFN in DL.";
      erienmyext:enm-type STRUCT;
      uses erienmnrmlrat:struct-SubFrameConfigRO;
    } // end 'list commonSFAllocList'
    leaf localCellId {
      description "RBS internal ID attribute for the ExternalEUtranCellTDD. Must be unique in the RBS. Together with the Node ID and PLMN ID this is a globally unique eUTRAN Cell ID (ECGI).";
      mandatory true;
      type erienmnrmlrat:ddt-Lrat_ExternalEUtranCellTDD_localCellId;
    }
    leaf remoteCellState {
      erienmyext:no-notification;
      config false;
      description "Reflects whether the indicated cell is currently able to serve as an SCell. The remote cell must be operState ENABLED and adminState UNLOCKED.";
      yexte:dependencies "Depends on X2 connection being operational and software compatibility.";
      type erienmnrmlrat:enum-OperState;
    }
    leaf-list activeServiceAreaId {
      min-elements 0;
      max-elements 64;
      description "The active MBMS Service Area Identity of an external cell.";
      type erienmnrmlrat:ddt-Lrat_ExternalEUtranCellTDD_activeServiceAreaId;
    }
    action changeFrequency {
      input {
        leaf earfcn {
          mandatory true;
          description "Changes the frequency of the external cell. This means it should change the value of the attribute eutranFrequencyRef to refer to the correct EUtranFrequency MO (creating it if necessary). It also includes moving the EUtranCellRelation MO:s to the corresponding EUtranFrequencyRelation MO.";
          type erienmnrmlrat:ddt-ExternalEUtranCellTDD_changeFrequency_earfcn;
        }
      }
    }
  } // end 'grouping moc-ExternalEUtranCellTDD'
  grouping moc-Mbms-keys {
    description "Key(s) for MOC Mbms";
    leaf id {
      erienmyext:no-notification;
      description "The value component of the Relative Distinguished Name (RDN).";
      mandatory true;
      yexte:ecim-name mbmsId;
      type string;
    }
  } // end 'grouping moc-Mbms-keys'
  grouping moc-Mbms {
    description "This MO is the top level MO for Multimedia Broadcast Multicast Service (MBMS). It contains attributes, which are common for all parts of MBMS in the node. ";
    leaf userLabel {
      description "Label for free use.";
      type erienmnrmlrat:ddt-Lrat_Mbms_userLabel;
    }
    leaf changeNotificationSIB13 {
      status deprecated {
        yexte:status-information "Since L16B. Replaced by ChangeNotificationSIBs.changeNotificationSIB13 in EUtranCellFDD/EUtranCellTDD::changeNotification. Planned to be removed.";
      }
      description "Indicates, when the SIB13 content is changed, if SI Change Notification shall be broadcasted prior to broadcast of updated SI.";
      yexte:takes-effect "New connection";
      type boolean;
      default true;
    }
    leaf mappingInfoSIB13 {
      status deprecated {
        yexte:status-information "Since L16B. Replaced by MappingInfoSIBs.mappingInfoSIB13 in EUtranCellFDD/EUtranCellTDD::mappingInfo. Planned to be removed.";
      }
      description "Defines to which SI message SIB13 is mapped.";
      yexte:takes-effect "Cell lock/unlock";
      yexte:dependencies "See siWindowLength for further information.";
      type erienmnrmlrat:enum-MappingInfo;
      default NOT_MAPPED;
    }
    leaf synchPeriodLength {
      description "MBMS synchronization period length.";
      yexte:takes-effect "At node restart";
      type erienmnrmlrat:ddt-Lrat_Mbms_synchPeriodLength;
      default 593920;
    }
    leaf tMbmsAuditTimer {
      description "The time the eNB waits with the deletion of ongoing MBMS sessions that are not re-started by MBMS SESSION START after a successful M3 SETUP procedure. ";
      yexte:takes-effect "Node restart";
      type erienmnrmlrat:ddt-Lrat_Mbms_tMbmsAuditTimer;
      default 180;
    }
    leaf m1IpInterfaceRef {
      description "Refers to the InterfaceIPv4 and InterfaceIPv6 MO instances used to configure the IP interface for M1 user plane connections.";
      yexte:disturbances "Changing this attribute can affect traffic.";
      yexte:takes-effect "At node restart";
      erienmyext:enm-type MOREF;
      type string;
    }
  } // end 'grouping moc-Mbms'
  grouping moc-CarrierAggregationFunction-keys {
    description "Key(s) for MOC CarrierAggregationFunction";
    leaf id {
      erienmyext:no-notification;
      description "The value component of the Relative Distinguished Name (RDN).";
      mandatory true;
      yexte:ecim-name carrierAggregationFunctionId;
      type string;
    }
  } // end 'grouping moc-CarrierAggregationFunction-keys'
  grouping moc-CarrierAggregationFunction {
    description "Parameters and constraints for Carrier Aggregation feature.\n\nThe RDN of this MO is CarrierAggregationFunction=1.";
    leaf sCellScheduleSinrThres {
      description "No data is scheduled on SCell if wideband SINR is lower than sCellScheduleSinrThres. If SINR remains below threshold, SCell is deactivated when sCellDeactOutOfCoverageTimer expired.";
      yexte:takes-effect "Cell lock/unlock";
      type erienmnrmlrat:ddt-Lrat_CarrierAggregationFunction_sCellScheduleSinrThres;
      default 0;
    }
    leaf waitForAdditionalSCellOpportunity {
      description "Controls the length of time that elapses until a UE is reconsidered for additional SCell configuration after the eNB was unable to configure this UE with more than one SCell.\n\"-1\" means wait forever.\nChanged value can take effect related to the next SCell configuration during the ongoing connection.";
      yexte:takes-effect "Ongoing connection";
      type erienmnrmlrat:ddt-Lrat_CarrierAggregationFunction_waitForAdditionalSCellOpportunity;
      default 10000;
    }
    leaf waitForCaOpportunity {
      description "Controls the length of time that elapses until a UE is considered once again for SCell configuration after the eNB was not able to configure this UE with a suitable Scell.\n\"-1\" means wait forever.\nChanged value may take effect related to the next SCell configuration during the ongoing connection.";
      yexte:disturbances "Extreme settings can turn off CA for the eNB.";
      yexte:takes-effect "Ongoing connection";
      type erienmnrmlrat:ddt-Lrat_CarrierAggregationFunction_waitForCaOpportunity;
      default 10000;
    }
    leaf dynamicSCellSelectionMethod {
      description "Method used to select SCell candidates.";
      yexte:takes-effect "New connection";
      yexte:dependencies "Only takes effect when feature Dynamic SCell Selection for Carrier Aggregation FAJ 121 3063 and feature Configurable SCell Priority FAJ 121 4701 and/or feature Automatic SCell Priority FAJ 121 4734 are active.";
      type erienmnrmlrat:enum-DynamicSCellSelectionMethod;
      default ROUND_ROBIN;
    }
    leaf sCellDeactDelayTimer {
      description "One SCell is deactivated if minimum time needed to transmit all bits in all priority queues of a UE is less than or equal to sCellActDeactDataThres minus sCellActDeactDataThresHyst for a duration of sCellDeactDelayTimer.";
      yexte:dependencies "sCellActDeactDataThresHyst <= sCellActDeactDataThres";
      type erienmnrmlrat:ddt-Lrat_CarrierAggregationFunction_sCellDeactDelayTimer;
      default 50;
    }
    leaf sCellActDeactDataThres {
      description "One or more SCells can be activated if minimum time needed to transmit all bits in all priority queues of UE is higher than sCellActDeactDataThres.\nWhen deciding the activation of one SCell, minimum time needed to transmit all bits is calculated as the number of bits in all priority queues, divided by the number of bits that can be transmitted in one TTI by all active serving cells prior to activation decision. This is computed as though the UE is given all resources in those cells. If the condition for activating one SCell is satisfied, a second SCell is also considered for activation but the minimum time needed to transmit all bits is now calculated by considering the added capacity of the first new SCell that is already considered for activation.\nFor FDD, the unit \"number of DL subframes\" is equivalent to ms, but for TDD UL/DL subframe configuration 1, there are 6 DL subframes in 10ms, and for UL/DL subframe configuration 2, there are 8 DL subframes in 10ms.\n\"-1\" means the data-triggered activation condition is always satisfied even with no data in the buffer, and also that the data-triggered deactivation condition is never satisfied.";
      yexte:takes-effect "Cell lock/unlock";
      yexte:dependencies "sCellActDeactDataThresHyst <= sCellActDeactDataThres when sCellActDeactDataThres is not equal to -1";
      type erienmnrmlrat:ddt-Lrat_CarrierAggregationFunction_sCellActDeactDataThres;
      default 100;
    }
    leaf pdcchEnhancedLaForVolte {
      description "Enables CA when VoIP and enhanced PDCCH Link Adaptation on FDD PCell are both active. Not used for TDD PCells.";
      yexte:takes-effect "At the next initial SCell selection during the ongoing connection";
      yexte:dependencies "Only takes effect when Carrier Aggregation FAJ 121 3046 and Enhanced PDCCH Link Adaptation FAJ 121 3051 are active, and a VoIP bearer exists for a UE.";
      type boolean;
      default false;
    }
    leaf sCellActDeactUlDataThreshHyst {
      description "If minimum time needed to transmit all bits in all priority queues in UL of a UE is less than sCellActDeactUlDataThresh minus sCellActDeactUlDataThreshHyst, deactivation of one CC is considered.";
      yexte:takes-effect "Cell lock/unlock";
      yexte:dependencies "sCellActDeactUlDataThreshHyst =< sCellActDeactUlDataThresh";
      type erienmnrmlrat:ddt-Lrat_CarrierAggregationFunction_sCellActDeactUlDataThreshHyst;
      default 90;
    }
    leaf laaSCellDeactProhibitTimer {
      description "LAA deactivation prohibit timer. No new LAA SCell deactivation is allowed while this timer is running.";
      yexte:takes-effect "Next cell unlock";
      type erienmnrmlrat:ddt-Lrat_CarrierAggregationFunction_laaSCellDeactProhibitTimer;
      default 200;
    }
    leaf waitForBlindSelSCellRepLessTtt {
      description "Amount of time to wait for blind SCell selection to return a measurement report, excluding the time to trigger. After waitForBlindSelSCellRep = waitForBlindSelSCellRepLessTtt + max(timeToTriggerA1, timeToTriggerA6), if no report is received, this SCell is deemed not to have coverage.";
      yexte:takes-effect "New connection. Also during ongoing connection, related to next SCell configuration during the connection.";
      yexte:dependencies "Only valid for Dynamic SCell selection, with dynamicSCellSelectionMethod in any supported setting.";
      type erienmnrmlrat:ddt-Lrat_CarrierAggregationFunction_waitForBlindSelSCellRepLessTtt;
      default 600;
    }
    leaf sCellActDeactDataThresHyst {
      description "If the minimum time needed to transmit all bits in all priority queues of a UE is less than or equal to sCellActDeactDataThres minus sCellActDeactDataThresHyst, then deactivation of one component carrier is considered.\nMinimum time needed to transmit all bits is calculated as number of bits in all priority queues, divided by the number of bits that can be transmitted in one TTI by all active serving cells after deactivation decision. This is computed as though the UE is given all resources in those cells.\nFor FDD, the unit \"number of DL subframes\" is equivalent to ms, but for TDD UL/DL subframe configuration 1, there are 6 DL subframes in 10ms, and for UL/DL subframe configuration 2, there are 8 DL subframes in 10ms.\nIf sCellActDeactDataThres is set to \"-1\", the data-triggered deactivation condition is never satisfied and the value of sCellActDeactDataThresHyst is ignored.";
      yexte:takes-effect "Cell lock/unlock";
      yexte:dependencies "sCellActDeactDataThresHyst <= sCellActDeactDataThres when sCellActDeactDataThres is not equal to -1";
      type erienmnrmlrat:ddt-Lrat_CarrierAggregationFunction_sCellActDeactDataThresHyst;
      default 90;
    }
    leaf selectionPolicyUlTargetRatio {
      description "A target minimum ratio of UL to DL effective BW, beyond which further SCells with no UL component will not be considered.";
      yexte:takes-effect "Takes effect on next SCell reconfiguration";
      yexte:dependencies "Only active if Configurable SCell Priority or Automatic SCell Priority is enabled.";
      type erienmnrmlrat:ddt-Lrat_CarrierAggregationFunction_selectionPolicyUlTargetRatio;
      default 0;
    }
    leaf selectionPolicyUlWeighting {
      description "Amount of weight given to UL effective BW.\nIf 0, UL is not included in utility function and fully determined by DL.\nIf 100, only UL score is considered, and DL weight is 0.\nIf set to -1, weight policy is disabled.";
      yexte:takes-effect "Takes effect on next SCell reconfiguration";
      yexte:dependencies "Only active if Configurable SCell Priority or Automatic SCell Priority is enabled.";
      type erienmnrmlrat:ddt-Lrat_CarrierAggregationFunction_selectionPolicyUlWeighting;
      default -1;
    }
    leaf useAbsolutePrioForCspEffBw {
      description "Enables absolute priority on CSP effective bandwidth evaluation for prioritized dynamic SCell Selection mode.";
      yexte:takes-effect "New connection";
      yexte:dependencies "Only takes effect when feature Configurable SCell Priority FAJ 121 4701 is active.";
      type boolean;
      default false;
    }
    leaf laaSCellScheduleSinrThres {
      status deprecated {
        yexte:status-information "Since 17.Q1. Has no functional behavior. Planned to be removed.";
      }
      description "No data is scheduled on LAA SCell if wideband SINR is lower than laaSCellScheduleSinrThres. If SINR stays below threshold, LAA SCell eventually becomes deactivated.\nOnly used if LAA is configured in RBS.";
      yexte:takes-effect "Cell lock/unlock";
      type erienmnrmlrat:ddt-Lrat_CarrierAggregationFunction_laaSCellScheduleSinrThres;
      default 0;
    }
    leaf sCellScheduleUlPathlossThresh {
      status deprecated {
        yexte:status-information "Since L16B. Has no functional behavior. Planned to be removed.";
      }
      description "No data is scheduled on the SCell if UL pathloss is higher than sCellScheduleUlPathlossThresh. If the pathloss stays above the threshold, the SCell is eventually deactivated.";
      yexte:takes-effect "Cell lock/unlock";
      type erienmnrmlrat:ddt-Lrat_CarrierAggregationFunction_sCellScheduleUlPathlossThresh;
      default 1400;
    }
    leaf sCellDeactProhibitTimer {
      description "Deactivation prohibit timer. No new SCell deactivation is allowed while this timer is running.";
      yexte:takes-effect "Cell lock/unlock";
      type erienmnrmlrat:ddt-Lrat_CarrierAggregationFunction_sCellDeactProhibitTimer;
      default 200;
    }
    leaf laaSCellActDeactDataThresHyst {
      status deprecated {
        yexte:status-information "Since 17.Q3. Replaced by UnlicensedAccessFunction::laaSCellActDeactDataThresHyst. Planned to be removed.";
      }
      description "If minimum time to transmit all bits is less than laaSCellActDeactDataThres minus laaSCellActDeactDataThresHyst, then deactivation of one component carrier is considered.\nMinimum time to transmit all bits is calculated as number of bits in all priority queues, divided by number of bits transmitted in one TTI by all active serving cells after deactivation decision. Computed as if UE has all resources in those cells.\nFor FDD, the unit \"number of DL subframes\" is equivalent to ms.\nOnly used if LAA is configured in RBS.";
      yexte:takes-effect "Cell lock/unlock";
      yexte:dependencies "laaSCellActDeactDataThresHyst <= laaSCellActDeactDataThres";
      type erienmnrmlrat:ddt-Lrat_CarrierAggregationFunction_laaSCellActDeactDataThresHyst;
      default 90;
    }
    leaf sCellSelectionMode {
      description "Selects the behavior of selecting SCell candidates beyond the first candidate. Warning: There is a risk when using UN_ACK_SIMULTANEOUS_SCELL_SELECTION that the UE may not report a bad SCell.";
      yexte:takes-effect "New connection";
      yexte:dependencies "Only takes effect when Dynamic SCell Selection for Carrier Aggregation FAJ 121 3063 and 3CC DL Carrier Aggregation Extension FAJ 121 3084 are active.";
      type erienmnrmlrat:enum-SCellSelectionMode;
      default ACK_SEQUENTIAL_SCELL_SELECTION;
    }
    leaf sCellDeactOutOfCoverageTimer {
      description "SCell is deactivated if:\n- wideband DL SINR remains below sCellScheduleSinrThres, or\n- no Channel State Information is received by the eNB\nfor a duration of sCellDeactOutOfCoverageTimer.\nDeactivation can be deferred, for example by sCellDeactProhibitTimer.\n\"-1\" means the SCell is not deactivated due to the SINR condition.";
      type erienmnrmlrat:ddt-Lrat_CarrierAggregationFunction_sCellDeactOutOfCoverageTimer;
      default 100;
    }
    leaf sCellActDeactUlDataThresh {
      description "If the minimum time needed to transmit all bits in all priority queues in UL of a UE is higher than sCellActDeactUlDataThresh, activation of one or more secondary cells is considered.";
      yexte:takes-effect "Cell lock/unlock";
      yexte:dependencies "sCellActDeactUlDataThreshHyst =< sCellActDeactUlDataThresh";
      type erienmnrmlrat:ddt-Lrat_CarrierAggregationFunction_sCellActDeactUlDataThresh;
      default 100;
    }
    leaf sCellPdcchOuterLoopMargin {
      description "The SINR margin for secondary cell (sCell) PDCCH outer loop.";
      type erienmnrmlrat:ddt-Lrat_CarrierAggregationFunction_sCellPdcchOuterLoopMargin;
      default 100;
    }
    leaf laaSCellActDeactProhibitTimer {
      status deprecated {
        yexte:status-information "Since 17.Q1. Replaced by laaSCellActProhibitTimer and laaSCellDeactProhibitTimer. Planned to be removed.";
      }
      description "Activation/deactivation prohibit timer. No new activation/deactivation of an LAA SCell is allowed while this timer is running.\nOnly used if LAA is configured in RBS.";
      yexte:takes-effect "Cell lock/unlock";
      type erienmnrmlrat:ddt-Lrat_CarrierAggregationFunction_laaSCellActDeactProhibitTimer;
      default 200;
    }
    leaf fourLayerMimoPreferred {
      description "Whether or not SCell is added when there is no change in effective bandwidth. Applies when enhanced selection of four layer MIMO and carrier aggregation is enabled. If set to true, SCell is not added, otherwise SCell is added.";
      yexte:takes-effect "New connection";
      yexte:dependencies "Only takes effect when Configurable SCell Priority FAJ 121 4701 is active.";
      type boolean;
      default false;
    }
    leaf caRateAdjustCoeff {
      description "Used to adjust factor of CC rate for CA UEs, which is used in scheduler's proportional fairness algorithm. A smaller value gives CA UE a greater advantage over non-CA UE.\nValue 0 sets rate as 0 and this is for testing purpose only; values 1 - 4 set the rate as fraction of the cell rate in increased order; value 5 sets cell based rate; values 6 - 9 set the rate as cell rate plus rate influence from other CCs in increased order; value 10 sets the rate as aggregated rate of all CCs .";
      yexte:takes-effect "Cell lock/unlock";
      type erienmnrmlrat:ddt-Lrat_CarrierAggregationFunction_caRateAdjustCoeff;
      default 10;
    }
    leaf sCellActProhibitTimer {
      description "Activation prohibit timer. No new SCell activation is allowed while this timer is running.";
      yexte:takes-effect "Cell lock/unlock";
      type erienmnrmlrat:ddt-Lrat_CarrierAggregationFunction_sCellActProhibitTimer;
      default 10;
    }
    leaf caPreemptionThreshold {
      description "Configures the resource consumption margin in percentage, beyond which Secondary Cells shall not be configured.";
      yexte:takes-effect "At node restart";
      type erienmnrmlrat:ddt-Lrat_CarrierAggregationFunction_caPreemptionThreshold;
      default 50;
    }
    leaf waitForBetterSCellRep {
      description "Controls the length of time a UE searches for SCells on a particular frequency, or set of frequencies based on measurements when it is in poor SCell coverage.\n\"-1\" means wait forever.\nChanged value can take effect related to the next SCell configuration during the ongoing connection.";
      yexte:takes-effect "Ongoing connection";
      type erienmnrmlrat:ddt-Lrat_CarrierAggregationFunction_waitForBetterSCellRep;
      default 1000;
    }
    leaf effectiveBwImpactDl4Layer {
      description "Expected DL throughput gain of having 4 layers compared with 2, averaged over a large sample of UE locations.";
      yexte:takes-effect "Takes effect on next SCell reconfiguration";
      yexte:dependencies "Only applicable when dynamicSCellSelectionMethod is equal to PRIORITIZED or PRIORITIZED_AUTOMATIC.";
      type erienmnrmlrat:ddt-Lrat_CarrierAggregationFunction_effectiveBwImpactDl4Layer;
      default 150;
    }
    leaf caUsageLimit {
      description "The value configures the number of SCell connections which can be in use for carrier aggregation. A secondary cell (SCell) costs in memory the same as a primary cell (PCell) for each UE. It is preferred to avoid limiting SCell connections with caUsageLimit, and use caPreemptionThreshold instead.";
      yexte:takes-effect "At node restart";
      type erienmnrmlrat:ddt-Lrat_CarrierAggregationFunction_caUsageLimit;
      default 65535;
    }
    leaf caPreference {
      description "Preference between downlink and uplink carrier aggregation.";
      yexte:takes-effect "New connection";
      yexte:dependencies "Only takes effect when 3CC Carrier aggregation Extension Feature (FAJ 121 3084) is enabled and sCellSelectionMode is equal to UN_ACK_SIMULTANEOUS_SCELL_SELECTION or ACK_SIMULTANEOUS_SCELL_SELECTION.";
      type erienmnrmlrat:enum-CaPreference;
      default NONE;
    }
    leaf sCellActDeactProhibitTimer {
      status deprecated {
        yexte:status-information "Since L16B. Replaced by sCellActProhibitTimer and sCellDeactProhibitTimer. Planned to be removed.";
      }
      description "Activation/deactivation prohibit timer. No new activation/deactivation of an SCell is allowed while this timer is running.";
      yexte:takes-effect "Cell lock/unlock";
      type erienmnrmlrat:ddt-Lrat_CarrierAggregationFunction_sCellActDeactProhibitTimer;
      default 200;
    }
    leaf laaSCellActDeactDataThres {
      status deprecated {
        yexte:status-information "Since 17.Q3. Replaced by UnlicensedAccessFunction::laaSCellActDeactDataThres. Planned to be removed.";
      }
      description "If minimum time to transmit all bits is higher than laaSCellActDeactDataThres, activation of one or more secondary cells is considered.\nMinimum time to transmit all bits is calculated as number of bits in all priority queues, divided by number of bits transmitted in one TTI by all active serving cells. Computed as if UE has all resources in those cells.\nFor FDD, the unit \"number of DL subframes\" is equivalent to ms, but for TDD UL/DL subframe configuration 1, there are 6 DL subframes in 10ms, and for UL/DL subframe configuration 2, there are 8 DL subframes in 10ms.\nOnly used if LAA is configured in RBS.";
      yexte:takes-effect "Cell lock/unlock";
      yexte:dependencies "laaSCellActDeactDataThresHyst <= laaSCellActDeactDataThres";
      type erienmnrmlrat:ddt-Lrat_CarrierAggregationFunction_laaSCellActDeactDataThres;
      default 100;
    }
    leaf dcSCellActDeactDataThresHyst {
      description "Deactivation of one component carrier is considered if:\nminimum time to transmit all bits in all priority queues of a UE is less than or equal to dcSCellActDeactDataThres minus dcSCellActDeactDataThresHyst.\nMinimum time is calculated as number of bits in all priority queues, divided by number of bits that can be transmitted in one TTI by all active serving cells (after deactivation decision). Computed as if UE is given all resources in those cells.\nIf dcSCellActDeactDataThres is set to \"-1\", data-triggered deactivation condition is never satisfied and value of dcSCellActDeactDataThresHyst is ignored.\nOnly used for UEs configured with Multi Rat Dual Connectivity.";
      yexte:takes-effect "Next cell unlock";
      yexte:dependencies "dcSCellActDeactDataThresHyst <= dcSCellActDeactDataThres when dcSCellActDeactDataThres is not equal to -1.";
      type erienmnrmlrat:ddt-Lrat_CarrierAggregationFunction_dcSCellActDeactDataThresHyst;
      default 90;
    }
    leaf enhancedSelectionOfMimoAndCa {
      description "Used to enable enhanced selection of four layer MIMO and carrier aggregation. Secondary cell is not added if effective bandwidth is reduced. If effective bandwidth is not changed, tie-breaking rule is governed by fourLayerMimoPreferred. Effective bandwidth includes the number of PRBs and MIMO layer capability of the UE in all serving cells.";
      yexte:takes-effect "New connection";
      yexte:dependencies "Only takes effect when Configurable SCell Priority FAJ 121 4701 is active.";
      type boolean;
      default false;
    }
    leaf laaSCellActProhibitTimer {
      description "LAA activation prohibit timer. No new LAA SCell activation is allowed while this timer is running.";
      yexte:takes-effect "Next cell unlock";
      type erienmnrmlrat:ddt-Lrat_CarrierAggregationFunction_laaSCellActProhibitTimer;
      default 10;
    }
    leaf dcSCellActDeactDataThres {
      description "SCells can be activated if minimum time needed to transmit all bits in all priority queues of UE is higher than dcSCellActDeactDataThres.\nMinimum time is calculated as number of bits in all priority queues, divided by number of bits that can be transmitted in one TTI by all active serving cells (prior to activation decision). Computed as if UE is given all resources in those cells.\nIf condition for activating one SCell is satisfied, a second SCell is also considered for activation. Minimum time needed to transmit all bits is now re-calculated with added capacity of new SCell. Another SCell is added if still over threshold.\n\"-1\" means data-triggered activation condition is always satisfied even with no data in buffer, and also that data-triggered deactivation condition is never satisfied.\nOnly used for UEs configured with Multi Rat Dual Connectivity.";
      yexte:takes-effect "Next cell unlock";
      yexte:dependencies "dcSCellActDeactDataThresHyst <= dcSCellActDeactDataThres when dcSCellActDeactDataThres is not equal to -1.";
      type erienmnrmlrat:ddt-Lrat_CarrierAggregationFunction_dcSCellActDeactDataThres;
      default 100;
    }
    leaf dcSCellDeactDelayTimer {
      description "One SCell is deactivated if minimum time needed to transmit all bits in all priority queues of a UE is less than or equal to dcSCellActDeactDataThres minus dcSCellActDeactDataThresHyst for a duration of dcSCellDeactDelayTimer.\nOnly used for UEs configured with Multi Rat Dual Connectivity.";
      yexte:takes-effect "Next cell unlock";
      yexte:dependencies "dcSCellActDeactDataThresHyst <= dcSCellActDeactDataThres.";
      type erienmnrmlrat:ddt-Lrat_CarrierAggregationFunction_dcSCellDeactDelayTimer;
      default 50;
    }
  } // end 'grouping moc-CarrierAggregationFunction'
  grouping moc-ReportConfigB2Utra-keys {
    description "Key(s) for MOC ReportConfigB2Utra";
    leaf id {
      erienmyext:no-notification;
      description "The value component of the Relative Distinguished Name (RDN).";
      mandatory true;
      yexte:ecim-name reportConfigB2UtraId;
      type string;
    }
  } // end 'grouping moc-ReportConfigB2Utra-keys'
  grouping moc-ReportConfigB2Utra {
    description "This managed object contains report configuration settings for the B2 event for UTRA measurements. The B2 event is used to detect when a UTRAN cell becomes better than threshold2, and serving cell becomes worse than threshold1. The actual threshold values used can be adjusted by frequency relation related offsets if the feature Multi-Layer Service-Triggered Mobility (MLSTM) is enabled.\n\nThe RDN of this MO is ReportConfigB2Utra=1.";
    leaf b2Threshold1Rsrp {
      description "The Reference Signal Received Power (RSRP) threshold1 value for eventB2.";
      yexte:takes-effect "New connection";
      yexte:dependencies "Only used if triggerQuantityB2  is set to RSRP.";
      type erienmnrmlrat:ddt-Lrat_ReportConfigB2Utra_b2Threshold1Rsrp;
      default -140;
    }
    leaf b2Threshold2EcNoUtra {
      description "Ratio of energy per modulation bit to noise spectral density in the ThresholdUTRA, threshold2 value for eventB2.\nNot applicable for UTRA TDD.";
      yexte:takes-effect "New connection";
      yexte:dependencies "Only used when measQuantityUtraFDD is set to ECNO";
      type erienmnrmlrat:ddt-Lrat_ReportConfigB2Utra_b2Threshold2EcNoUtra;
      default -240;
    }
    leaf b2Threshold1Rsrq {
      description "The Reference Signal Received Quality (RSRQ) in the threshold1 value for eventB2.";
      yexte:takes-effect "New connection";
      yexte:dependencies "Only used if triggerQuantityB2 is set to RSRQ.";
      type erienmnrmlrat:ddt-Lrat_ReportConfigB2Utra_b2Threshold1Rsrq;
      default -195;
    }
    leaf triggerQuantityB2 {
      description "The quantity for threshold1 (serving EUTRAN cell) that is sent to the UE, and is used together with threshold2 to trigger the eventB2.";
      yexte:takes-effect "New connection";
      type erienmnrmlrat:enum-TriggerQuantity;
      default RSRP;
    }
    leaf hysteresisB2RsrqOffset {
      description "Offset to obtain the Hysteresis for B2 measurement for trigger quantity RSRQ. hysteresisB2Rsrq = hysteresisB2 + hysteresisB2RsrqOffset";
      yexte:takes-effect "New connection";
      yexte:dependencies "Feature Mobility Control at Poor Coverage must be active.";
      type erienmnrmlrat:ddt-Lrat_ReportConfigB2Utra_hysteresisB2RsrqOffset;
      default 0;
    }
    leaf timeToTriggerB2Rsrq {
      description "Time-to-trigger value for event B2 with trigger quantity RSRQ. If set to -1, this attribute is not used for report configuration.";
      yexte:takes-effect "New connection";
      yexte:dependencies "Feature Mobility Control at Poor Coverage must be active.";
      type erienmnrmlrat:ddt-Lrat_ReportConfigB2Utra_timeToTriggerB2Rsrq;
      default -1;
    }
    leaf hysteresisB2 {
      description "The hysteresis value for the eventB2 measurement";
      yexte:takes-effect "New connection";
      type erienmnrmlrat:ddt-Lrat_ReportConfigB2Utra_hysteresisB2;
      default 10;
    }
    leaf timeToTriggerB2 {
      description "Time-to-trigger value for event B2 measurements. If timeToTriggerB2Rsrq is -1, this attribute is used for both RSRP and RSRQ. But if not set to -1, this attribute is used only for RSRP.";
      yexte:takes-effect "New connection";
      type erienmnrmlrat:ddt-Lrat_ReportConfigB2Utra_timeToTriggerB2;
      default 640;
    }
    leaf b2Threshold2RscpUtra {
      description "Received Signal Code Power in the ThresholdUTRA, threshold2 value for eventB2.";
      yexte:takes-effect "New connection";
      yexte:dependencies "Used when measQuantityUtraFDD is set to RSCP.  Also present for UTRA TDD.";
      type erienmnrmlrat:ddt-Lrat_ReportConfigB2Utra_b2Threshold2RscpUtra;
      default -115;
    }
  } // end 'grouping moc-ReportConfigB2Utra'
  grouping moc-Rcs-keys {
    description "Key(s) for MOC Rcs";
    leaf id {
      erienmyext:no-notification;
      description "The value component of the RDN.\n";
      mandatory true;
      yexte:ecim-name rcsId;
      type string;
    }
  } // end 'grouping moc-Rcs-keys'
  grouping moc-Rcs {
    description "Models the manageable characteristics of Radio Connection Supervision feature.\n\nThe RDN of this MO is Rcs=1.";
    leaf tInactivityTimerBr {
      description "Time a Bandwidth reduced UE can be inactive before it is released.\n86400s = 24 hours.\nSpecial values:\n0 turns timer off. If so, UEs are not released due to inactivity.";
      yexte:takes-effect "New connection";
      type erienmnrmlrat:ddt-Lrat_Rcs_tInactivityTimerBr;
      default 61;
    }
    leaf tInactivityTimer {
      description "The time a UE can be inactive before it is released.\n86400s = 24 hours\nSpecial values:\n0 is used to turn off the use of this timer. This means that a UE will not be released due to inactivity.\n";
      yexte:disturbances "Changing this attribute can cause loss of traffic.";
      yexte:takes-effect "New connection.";
      type erienmnrmlrat:ddt-Lrat_Rcs_tInactivityTimer;
      default 61;
    }
    leaf rlcDlDeliveryFailureAction {
      description "Attribute controls the action when there is an RLC DL Delivery failure on a DRB in a connection. The action can be set to:\n- always make an UE Context release\n- resume the connection if higher ARP prioritized DRBs exist to get better retainability\nIf there is RLC Delivery failure on SRB or on the DRB used for IMS Signaling (indicated by ServiceType in QciProfileOperatorDefined/QciProfilePredefined), the design base behavior applies. In this case, eNodeB triggers a UE Context Release regardless of the value of attribute rlcDlDeliveryFailureAction.";
      yexte:disturbances "Changing this attribute can affect traffic if the value is not set to make a UE context release. When there is a RLC DL Delivery failure on one of several DRBs of a UE, the DRB may be marked as failed and the other DRBs are then retained. The marked DRB cannot be used after the failure until a handover or an RRC Connection Re-establishment initiated by the UE is successful.";
      yexte:dependencies "If this attribute is not set to UE_CONTEXT_RELEASE, the behavior depends on:\n- ARP priority\n- ServiceType attribute";
      type erienmnrmlrat:enum-RlcDlDeliveryFailAction;
      default UE_CONTEXT_RELEASE;
    }
  } // end 'grouping moc-Rcs'
  grouping moc-ExternalCdma20001xRttCell-keys {
    description "Key(s) for MOC ExternalCdma20001xRttCell";
    leaf id {
      erienmyext:no-notification;
      description "Value component of the RDN";
      mandatory true;
      yexte:ecim-name externalCdma20001xRttCellId;
      type string;
    }
  } // end 'grouping moc-ExternalCdma20001xRttCell-keys'
  grouping moc-ExternalCdma20001xRttCell {
    description "The MO represents a CDMA2000 1xRTT cell.";
    leaf userLabel {
      description "Label for free use";
      type erienmnrmlrat:ddt-Lrat_ExternalCdma20001xRttCell_userLabel;
    }
    container mscIdentifier {
      description "MSC identity in CDMA 1xRTT network\nIf this 1xRTT cell is referred by EUtranCellFDD or EUtranCellTDD, this identifier will be used by eNodeB for tunneling of 1xRTT signaling messages towards this MSC. It has to be configured for LTE CSFB to 1xRTT features since it is used to fill a field in S1AP message sent to MME.";
      erienmyext:enm-type STRUCT;
      uses erienmnrmlrat:struct-MSCid;
    } // end 'container mscIdentifier'
    container acBarring1xRttMoData {
      description "Access Barring parameters for CDMA2000 1xRTT capable UE originating signaling\nThe information is broadcast in SIB8. This is controlled by the licensing MO CsfbTo1xRtt and acBarring1xRttForMoDataPresent";
      erienmyext:enm-type STRUCT;
      uses erienmnrmlrat:struct-AcBarringConfig1xRtt;
    } // end 'container acBarring1xRttMoData'
    leaf nid {
      description "Network unique identifier (16 bits) within a system used along with the SID as a pair to control when the UE should register or reregister with the CDMA2000 1xRTT network.\nNID=0 and NID=65535 are reserved.";
      mandatory true;
      type erienmnrmlrat:ddt-Lrat_ExternalCdma20001xRttCell_nid;
    }
    container csfbRegParams1xRttMoData {
      description "Information for preregistration to 1xRTT system\nThe information is broadcast in SIB8. This information, together with the information in mobilityParams1xRttMoData, must be used to build IE in RRC messages: CSFBParametersResponseCDMA2000 and HandoverFromEUTRAPreparationRequest.\nThis is controlled by the licensing MO CsfbTo1xRtt.";
      erienmyext:enm-type STRUCT;
      uses erienmnrmlrat:struct-CsfbRegParams1xRtt;
    } // end 'container csfbRegParams1xRttMoData'
    leaf sid {
      description "System unique identifier (15bits)\nThis attribute is used along with the NID as a pair to control when the UE should register or reregister with the CDMA2000 1xRTT network. SID=0 is reserved. It is broadcast on SIB8.\nIt is also used with CellId, SectorNumber and NID for the 1xRTT cell global identity.";
      mandatory true;
      type erienmnrmlrat:ddt-Lrat_ExternalCdma20001xRttCell_sid;
    }
    leaf acBarring1xRttForMoDataPresent {
      description "Presence indication in SIB8 of Information Element acBarring1xRttMoData";
      type boolean;
      default false;
    }
    container cellIdentifier {
      description "Cell identifier\nIf a 1xRTT cell is referred by EUtranCellFDD or EUtranCellTDD, this cell/sector attribute in conjunction with marketId and switchNumber shall be used to set the IE CDMA2000 Sector ID in Uplink S1 CDMA2000 tunneling message.";
      erienmyext:enm-type STRUCT;
      uses erienmnrmlrat:struct-Cdma1xRttCellId;
    } // end 'container cellIdentifier'
    container mobilityParams1xRttMoData {
      description "Information for registration/reregistration to 1xRTT system\nThe information, together with the information in csfbRegParams1xRttMoData, is used to build the IE in RRC messages: CSFBParametersResponseCDMA2000 and HandoverFromEUTRAPreparationRequest.\nThis is controlled by the licensing MO CsfbTo1xRtt.";
      erienmyext:enm-type STRUCT;
      uses erienmnrmlrat:struct-MobilityParams1xRtt;
    } // end 'container mobilityParams1xRttMoData'
    leaf srvccCapability {
      description "Describes the SRVCC capability of the external cell.";
      yexte:takes-effect "New connection";
      type erienmnrmlrat:enum-SrvccCapability;
      default NOT_SUPPORTED;
    }
    leaf-list reservedBy {
      min-elements 0;
      config false;
      description "List of MO instances that reserve this MO instance";
      yexte:dependencies "The MO cannot be deleted if it is reserved.";
      notife:notifiable-state-data true;
      erienmyext:enm-type MOREF;
      type string;
    }
    leaf pnOffset {
      description "CDMA physical cell identity";
      mandatory true;
      yexte:takes-effect "New connection";
      type erienmnrmlrat:ddt-Lrat_ExternalCdma20001xRttCell_pnOffset;
    }
  } // end 'grouping moc-ExternalCdma20001xRttCell'
  grouping moc-EUtraNetwork-keys {
    description "Key(s) for MOC EUtraNetwork";
    leaf id {
      erienmyext:no-notification;
      description "The value component of the Relative Distinguished Name (RDN).\n";
      mandatory true;
      yexte:ecim-name eUtraNetworkId;
      type string;
    }
  } // end 'grouping moc-EUtraNetwork-keys'
  grouping moc-EUtraNetwork {
    description "Container for MOs related to EUTRA networks.\n\nThe RDN of this MO is EUtraNetwork=1.";
    leaf userLabel {
      description "User-defined alphanumeric label, maximum 128 characters including spaces.\n";
      type erienmnrmlrat:ddt-Lrat_EUtraNetwork_userLabel;
    }
  } // end 'grouping moc-EUtraNetwork'
  grouping moc-UtranFreqRelation-keys {
    description "Key(s) for MOC UtranFreqRelation";
    leaf id {
      erienmyext:no-notification;
      description "The value component of the Relative Distinguished Name (RDN).\n";
      mandatory true;
      yexte:ecim-name utranFreqRelationId;
      type string;
    }
  } // end 'grouping moc-UtranFreqRelation-keys'
  grouping moc-UtranFreqRelation {
    description "This Managed Object represents a UTRAN FDD mobility relation between a EUtranCellFDD or EUtranCellTDD and an UtranFrequency. It contains parameters that are specific for this relation.\n\nDeleting this MO while the parent EUtranCellFDD/EUtranCellTDD has operationalState set to ENABLED is not recommended as it may affect traffic.";
    leaf userLabel {
      description "Label for free use.\n";
      type erienmnrmlrat:ddt-Lrat_UtranFreqRelation_userLabel;
    }
    list utranFreqToQciProfileRelation {
      min-elements 0;
      max-elements 23;
      key auto-generated-struct-key;
      leaf auto-generated-struct-key {
        type uint16;
        description "This leaf has been injected to allow for struct instances in a sequence to be ordered.";
        mandatory true;
      }
      description "QCI profile relation\nThe attribute encapsulates parameters for service specific load management for specific QCI profiles.";
      erienmyext:enm-type STRUCT;
      uses erienmnrmlrat:struct-UtranFreqToQciProfileRelation;
    } // end 'list utranFreqToQciProfileRelation'
    leaf altCsfbTargetPrioEc {
      description "Prioritizes UTRAN frequencies for emergency calls among all frequencies related to the cell for UEs in connected mode.\nSets the priority to the alternative target frequency/frequency group to which to make release with redirect when measurement or handover to selected target fails for emergency calls.\nValue -1 means the frequency is excluded.\nValue 0 means the lowest priority.\nValue 7 means the highest priority.";
      yexte:takes-effect "New connection";
      type erienmnrmlrat:ddt-Lrat_UtranFreqRelation_altCsfbTargetPrioEc;
      default 0;
    }
    leaf b2Thr1RsrqUtraFreqOffset {
      description "The frequency-relation specific offset for the absolute threshold b2Threshold1Rsrq, RSRQ threshold1 for event B2, used for Multi-Layer Service-Triggered Mobility.";
      yexte:takes-effect "Ongoing connection";
      type erienmnrmlrat:ddt-Lrat_UtranFreqRelation_b2Thr1RsrqUtraFreqOffset;
      default 0;
    }
    leaf mobilityAction {
      description "The preferred way to transfer a UE in connected mode to a UTRAN FDD frequency in case of coverage triggered mobility.";
      yexte:takes-effect "New connection";
      type erienmnrmlrat:enum-MobilityActionUtran;
      default HANDOVER;
    }
    leaf pMaxUtra {
      description "Used to calculate the parameter Pcompensation (defined in 3GPP TS 36.304) at cell reselection to a UTRAN cell.";
      type erienmnrmlrat:ddt-Lrat_UtranFreqRelation_pMaxUtra;
      default 33;
    }
    leaf altCsfbTargetPrio {
      description "Prioritizes UTRAN frequencies among all frequencies related to the cell for UEs in connected mode.\nSets the priority to the alternative target frequency/frequency group to which  to make release with redirect when measurement or handover to selected target fails.\nValue -1 means the frequency is excluded.\nValue 0 means the lowest priority.\nValue 7 means the highest priority.";
      yexte:takes-effect "New connection";
      type erienmnrmlrat:ddt-Lrat_UtranFreqRelation_altCsfbTargetPrio;
      default 0;
    }
    leaf threshXLowQ {
      description "Specifies the quality level threshold used by the UE when reselecting towards a lower priority UTRA frequency than the current serving frequency.\nCorresponds to ThreshX, LowQ in 3GPP TS 36.304";
      yexte:dependencies "This parameter is included in SIB6 if the threshServingLowQ in SIB3 is included in systemInformationBlockType3.";
      type erienmnrmlrat:ddt-Lrat_UtranFreqRelation_threshXLowQ;
      default 0;
    }
    list b2UtranOffsetPerPC {
      min-elements 0;
      max-elements 2;
      key auto-generated-struct-key;
      leaf auto-generated-struct-key {
        type uint16;
        description "This leaf has been injected to allow for struct instances in a sequence to be ordered.";
        mandatory true;
      }
      description "The frequency-relation specific offset for the absolute threshold, RSRP threshold1 for event B2, used for Multi-Layer Service-Triggered Mobility and High Power UE.";
      erienmyext:enm-type STRUCT;
      uses erienmnrmlrat:struct-B2UtranPCOffsetMCPC;
    } // end 'list b2UtranOffsetPerPC'
    leaf maxNrUtranCellRelations {
      config false;
      description "This parameter specifies the maximum number of UtranCellRelations per UtranFreqRelation. The value is set by the action with name SetMaxNrUtranCellRelations.";
      notife:notifiable-state-data true;
      type erienmnrmlrat:ddt-Lrat_UtranFreqRelation_maxNrUtranCellRelations;
    }
    list allowedPlmnList {
      min-elements 0;
      max-elements 15;
      key auto-generated-struct-key;
      leaf auto-generated-struct-key {
        type uint16;
        description "This leaf has been injected to allow for struct instances in a sequence to be ordered.";
        mandatory true;
      }
      description "List of all Public Land Mobile Network (PLMN) IDs allowed for this frequency relation.\n\nA UE that does not support one of the IDs included in the allowedPlmnList does not measure on this frequency, according to the UE Handover Restriction List.\n\nNo values in allowedPlmnList imply that the frequency has no restrictions for PLMN.\n\nThe PLMN ID contains the following parts:\n1. MobileCountryCode, MCC, 3 digits\n2. MobileNetworkCode, MNC, 2 or 3 digits (the correct number of digits is set in the mncLength member of this Struct)\n\nFor example, if MCC=125 and MNC=46, then plmnId=12546.";
      erienmyext:enm-type STRUCT;
      uses erienmnrmlrat:struct-PlmnIdentity;
    } // end 'list allowedPlmnList'
    leaf b2Thr2RscpUtraFreqOffset {
      description "The frequency-relation specific offset for the absolute threshold b2Threshold2Rscp, RSCP in the ThresholdUTRA for event B2, used for Multi-Layer Service-Triggered Mobility.";
      yexte:takes-effect "Ongoing connection";
      type erienmnrmlrat:ddt-Lrat_UtranFreqRelation_b2Thr2RscpUtraFreqOffset;
      default 0;
    }
    leaf threshXLow {
      description "The threshold used in reselection towards a lower frequency priority from a higher priority frequency. Each frequency of UTRAN may have a specific threshold. The threshold is specified as parameter Thresx,low in 3GPP TS 36.304.";
      type erienmnrmlrat:ddt-Lrat_UtranFreqRelation_threshXLow;
      default 0;
    }
    leaf anrMeasOn {
      description "ANR performs measurement on the referenced frequency if this parameter is set to true. Otherwise, ANR does not perform any measurements on this frequency.";
      yexte:takes-effect "New connection";
      type boolean;
      default true;
    }
    leaf b2Thr2EcNoUtraFreqOffset {
      description "The frequency-relation specific offset for the absolute threshold b2Threshold2EcNo, Ratio of energy for each modulation bit to noise spectral density in the ThresholdUTRA for event B2, used for Multi-Layer Service-Triggered Mobility.";
      yexte:takes-effect "Ongoing connection";
      type erienmnrmlrat:ddt-Lrat_UtranFreqRelation_b2Thr2EcNoUtraFreqOffset;
      default 0;
    }
    leaf qRxLevMin {
      description "The required minimum received Rx level in the UTRAN frequency used in cell reselection. Corresponds to parameter Qrxlevmin in 3GPP TS 36.304.";
      type erienmnrmlrat:ddt-Lrat_UtranFreqRelation_qRxLevMin;
      default -119;
    }
    leaf b2Thr1RsrpUtraFreqOffset {
      description "The frequency-relation specific offset for the absolute threshold b2Threshold1Rsrp, RSRP threshold1 for event B2, used for Multi-Layer Service-Triggered Mobility.";
      yexte:takes-effect "Ongoing connection";
      type erienmnrmlrat:ddt-Lrat_UtranFreqRelation_b2Thr1RsrpUtraFreqOffset;
      default 0;
    }
    leaf cellReselectionPriority {
      description "The absolute priority of the carrier frequency used by the cell reselection procedure. Corresponds to parameter priority in 3GPP TS 36.304.\nValue 0 means lowest priority. The UE behavior when the field is empty if applicable, is specified in 3GPP TS 36.304.";
      yexte:dependencies "The value must be unique and not already used by other RAT, i.e. equal priorities between RATs are not supported.";
      type erienmnrmlrat:ddt-Lrat_UtranFreqRelation_cellReselectionPriority;
      default 6;
    }
    leaf qOffsetFreq {
      description "Indicates a frequency-specific offset to apply when evaluating triggering conditions for measurement reporting.";
      yexte:takes-effect "New connection";
      type erienmnrmlrat:ddt-Lrat_UtranFreqRelation_qOffsetFreq;
      default 0;
    }
    leaf csFallbackPrioEC {
      description "Prioritizes UTRAN frequencies for emergency calls among all frequencies/frequency groups related to the cell for UEs in connected mode.\nSets the priority to which frequency to make emergency call CS Fallback to.\nThe value -1 means the frequency is excluded.\nThe value 0 means the lowest priority.\nThe value 7 means the highest priority.";
      yexte:takes-effect "New connection";
      type erienmnrmlrat:ddt-Lrat_UtranFreqRelation_csFallbackPrioEC;
      default 0;
    }
    leaf csFallbackPrio {
      description "Prioritizes UTRAN frequencies among all frequencies related to the cell for UEs in connected mode.\nSets the priority to which frequency/frequency group to make CS Fallback to.\nThe value -1 means the frequency is excluded.\nThe value 0 means the lowest priority.\nThe value 7 means the highest priority.";
      yexte:takes-effect "New connection";
      type erienmnrmlrat:ddt-Lrat_UtranFreqRelation_csFallbackPrio;
      default 0;
    }
    leaf connectedModeMobilityPrio {
      description "Prioritizes UTRA frequencies among all frequencies related to the cell for UEs in connected mode.\n(0 means the lowest priority. -1 means the frequency is excluded.)";
      yexte:takes-effect "New connection";
      type erienmnrmlrat:ddt-Lrat_UtranFreqRelation_connectedModeMobilityPrio;
      default 6;
    }
    leaf mobilityActionCsfb {
      description "The preferred way to transfer a UE in connected mode to a UTRAN FDD frequency in case of CS Fallback.";
      yexte:takes-effect "New connection";
      type erienmnrmlrat:enum-MobilityActionCsfbUtranFDD;
      default RELEASE_WITH_REDIRECT;
    }
    leaf utranFrequencyRef {
      yexte:restricted;
      description "Reference to the UTRAN frequency MO, UtranFreq.\n";
      mandatory true;
      erienmyext:enm-type MOREF;
      type string;
    }
    leaf threshXHighQ {
      description "Specifies the quality level threshold used by the UE when reselecting towards a higher priority UTRA frequency than the current serving frequency.\nCorresponds to ThreshX, HighQ in 3GPP TS 36.304";
      yexte:dependencies "This parameter is included in SIB6 if the threshServingLowQ in SIB3 is included in systemInformationBlockType3.";
      type erienmnrmlrat:ddt-Lrat_UtranFreqRelation_threshXHighQ;
      default 0;
    }
    leaf atoAllowed {
      description "Specifies whether Admission-triggered offload (ATO) is activated from the current cell towards a certain UTRAN frequency.";
      yexte:disturbances "Changing this attribute can affect traffic.";
      type boolean;
      default false;
    }
    leaf lbBnrPolicy {
      description "Specifies the policy for updating the loadBalancing attribute by the feature Best Neighbor Relations for WCDMA IRAT Offload. The policy is valid for all cell relations corresponding to this UtranFreqRelation.";
      type erienmnrmlrat:enum-UtranLbBnrPolicyVals;
      default OFFLOAD_ONLY;
    }
    leaf threshXHigh {
      description "The threshold used by the UE when reselecting towards a higher priority frequency from the current serving frequency. Each UTRAN frequency may have a specific threshold. The threshold is specified as parameter Thresx,high in 3GPP TS 36.304.";
      type erienmnrmlrat:ddt-Lrat_UtranFreqRelation_threshXHigh;
      default 4;
    }
    leaf voicePrio {
      description "Prioritizes UTRAN frequencies among all frequencies related to the cell for UEs in connected mode. Sets the priority to which frequency to perform mobility to for a voice session.\nThe value -1 means the frequency is excluded.\nThe value 0 means the lowest priority.\nThe value 7 means the highest priority.";
      yexte:takes-effect "New connection";
      type erienmnrmlrat:ddt-Lrat_UtranFreqRelation_voicePrio;
      default 0;
    }
    leaf qQualMin {
      description "Minimum required quality level in the cell (dB). Corresponds to parameter Qqualmin in 3GPP TS 25.304";
      type erienmnrmlrat:ddt-Lrat_UtranFreqRelation_qQualMin;
      default -18;
    }
    action setMaxNrUtranCellRelations {
      description "This MO action is used for setting the maximum number of UtranCellRelations per UtranFreqRelation. This action will remove UtranCellRelations so the number of relations goes down to the value of MaxNrUtranCellRelation. Relations that were latest used are kept.";
      input {
        leaf maxNrUtranCellRelations {
          mandatory true;
          description "This specifies the maximum number of UtranCellRelations.";
          type erienmnrmlrat:ddt-UtranFreqRelation_setMaxNrUtranCellRelations_maxNrUtranCellRelations;
        }
      }
    }
  } // end 'grouping moc-UtranFreqRelation'
  grouping moc-EndcProfile-keys {
    description "Key(s) for MOC EndcProfile";
    leaf id {
      erienmyext:no-notification;
      description "The value component of the RDN.";
      mandatory true;
      yexte:ecim-name endcProfileId;
      type string;
    }
  } // end 'grouping moc-EndcProfile-keys'
  grouping moc-EndcProfile {
    description "EN-DC profiles and EN-DC parameters that map to different QCIs.";
    leaf userLabel {
      description "Label for free use.";
      type erienmnrmlrat:ddt-Lrat_EndcProfile_userLabel;
    }
    leaf meNbS1TermReqArpLev {
      description "Controls how S1-U is terminated for EN-DC capable UEs.\nIf ARP.PriorityLevel is equal to or lower than meNbS1TermReqArpLev, bearer must not be setup as SN terminated.\nIf ARP.PriorityLevel is higher than meNbS1TermReqArpLev, bearer can be setup as SN terminated.\nValue 0 means the bearer can be set up as SN Terminated irrespectively of ARP.";
      yexte:takes-effect "New connection";
      yexte:dependencies "Only relevant if license for Basic Intelligent Connectivity is present and feature is active.";
      type erienmnrmlrat:ddt-Lrat_EndcProfile_meNbS1TermReqArpLev;
      default 7;
    }
    leaf-list reservedBy {
      min-elements 0;
      config false;
      description "Contains a list of MO instances that reserve this MO instance.";
      notife:notifiable-state-data true;
      erienmyext:enm-type MOREF;
      type string;
    }
  } // end 'grouping moc-EndcProfile'
  grouping moc-ReportConfigB2UtraUlTrig-keys {
    description "Key(s) for MOC ReportConfigB2UtraUlTrig";
    leaf id {
      erienmyext:no-notification;
      description "The value component of the RDN.";
      mandatory true;
      yexte:ecim-name reportConfigB2UtraUlTrigId;
      type string;
    }
  } // end 'grouping moc-ReportConfigB2UtraUlTrig-keys'
  grouping moc-ReportConfigB2UtraUlTrig {
    description "Contains report configuration settings for the B2 event for UTRA measurements initiated by Uplink-Triggered Inter-Frequency Mobility. The actual threshold values used can be adjusted by frequency relation or QCI related offsets if the feature Multi-Layer Service-Triggered Mobility (MLSTM) is enabled.\n\nThe RDN of this MO is ReportConfigB2UtraUlTrig=1.";
    leaf b2Threshold2EcNoUtra {
      description "Ratio of energy per modulation bit to noise spectral density in the ThresholdUTRA, threshold2 value for eventB2.\nNot applicable for UTRA TDD.\nUsed when UeMeasControl::measQuantityUtraFDD is set to ECNO.";
      yexte:takes-effect "New connection";
      type erienmnrmlrat:ddt-Lrat_ReportConfigB2UtraUlTrig_b2Threshold2EcNoUtra;
      default -240;
    }
    leaf hysteresisB2 {
      description "The hysteresis value for the event B2.";
      yexte:takes-effect "New connection";
      type erienmnrmlrat:ddt-Lrat_ReportConfigB2UtraUlTrig_hysteresisB2;
      default 10;
    }
    leaf timeToTriggerB2 {
      description "Time-to-trigger value for event B2.";
      yexte:takes-effect "New connection";
      type erienmnrmlrat:ddt-Lrat_ReportConfigB2UtraUlTrig_timeToTriggerB2;
      default 640;
    }
    leaf b2Threshold2RscpUtra {
      description "Received Signal Code Power in the ThresholdUTRA, threshold2 value for eventB2.\nAlso present for UTRA TDD.\nUsed when UeMeasControl::measQuantityUtraFDD is set to RSCP.";
      yexte:takes-effect "New connection";
      type erienmnrmlrat:ddt-Lrat_ReportConfigB2UtraUlTrig_b2Threshold2RscpUtra;
      default -115;
    }
    leaf reportIntervalB2 {
      description "The interval for event triggered periodical reporting for B2 event.";
      yexte:takes-effect "New connection";
      type erienmnrmlrat:enum-ReportInterval;
      default MS_2048;
    }
  } // end 'grouping moc-ReportConfigB2UtraUlTrig'
  grouping moc-EUtranFreqRelation-keys {
    description "Key(s) for MOC EUtranFreqRelation";
    leaf id {
      erienmyext:no-notification;
      description "The value component of the Relative Distinguished Name (RDN).\n";
      mandatory true;
      yexte:ecim-name eUtranFreqRelationId;
      type string;
    }
  } // end 'grouping moc-EUtranFreqRelation-keys'
  grouping moc-EUtranFreqRelation {
    description "This MO represents a mobility relation between a EUtranCellFDD and a EUtranFrequency. It contains parameters that are specific for this relation.\nTo include SIB3 in System Information, one instance of this MO must be created which refers to a EUtranFrequency MO with the parameter arfcnValueEUtranDl set to the same value as the parent EUtranCellFDD/EUtranCellTDDs parameter earfcndl.\n\n It is only allowed to remove the EUtranFreqRelation, refering to the same frequency as the parent MO EUtranCellFDD/EUtranCellTDD has, when the EUtranCellFDD/EUtranCellTDD is locked.\n\nDeleting this MO while the parent EUtranCellFDD/EUtranCellTDD has operationalState set to ENABLED is not recommended as it may affect traffic.\n";
    leaf interFreqMeasTypeUlSinr {
      description "The type of event based measurements used for inter-frequency LTE measurements when the measurements are uplink triggered.";
      yexte:takes-effect "New connection";
      type erienmnrmlrat:enum-InterFreqMeasType;
      default EVENT_A5;
    }
    leaf a3RsrpFreqOffsetAdjustment {
      description "Frequency-relation specific offset adjustment for absolute offset a3OffsetRsrp for event A3, used for Multi-Layer Service-Triggered Mobility.";
      type erienmnrmlrat:ddt-Lrat_EUtranFreqRelation_a3RsrpFreqOffsetAdjustment;
      default 0;
    }
    leaf a5Thr2RsrpFreqOffset {
      description "The frequency-relation specific offset for the absolute threshold a5Threshold2Rsrp, RSRP threshold2 for event A5, used for Multi-Layer Service-Triggered Mobility.";
      yexte:takes-effect "Ongoing connection";
      type erienmnrmlrat:ddt-Lrat_EUtranFreqRelation_a5Thr2RsrpFreqOffset;
      default 0;
    }
    leaf csgPhysCellId {
      description "PCI for the closed access mode CSG cell. It is the start physical cell ID in the SIB4. If value is equal to 1000, it means that csg-PhysCellIdRange IE is not presented in SIB4.";
      yexte:dependencies "If csgPhysCellId != 1000, csgPhysCellId + csgPhysCellIdRange <= 504";
      type erienmnrmlrat:ddt-Lrat_EUtranFreqRelation_csgPhysCellId;
      default 1000;
    }
    leaf threshXLowQ {
      description "Parameter \"ThreshX, LowQ\" in TS 36.304.\nFor the EUtranFreqRelation that points to the intra frequency EUtranFrequency MO, the attribute is invalid, that is, this attribute does not affect SIB3.";
      yexte:dependencies "The field is mandatory present if the Struct Member threshServingLowQ in SIB3 is used in systemInformationBlockType3.";
      type erienmnrmlrat:ddt-Lrat_EUtranFreqRelation_threshXLowQ;
      default 0;
    }
    leaf csgCellTargetIdType {
      description "Target eNodeB ID type for the CSG and Hybrid CSG neighbor cell. Attribute is used to encode the message Handover Required when it is defined in TS36.413 ch. 9.1.5.1, S1AP parameter Global eNB ID.";
      type erienmnrmlrat:enum-NonPlannedPciTargetIdType;
      default MACRO_ENODEB_ID;
    }
    list allowedPlmnList {
      min-elements 0;
      max-elements 15;
      key auto-generated-struct-key;
      leaf auto-generated-struct-key {
        type uint16;
        description "This leaf has been injected to allow for struct instances in a sequence to be ordered.";
        mandatory true;
      }
      description "Lists all Public Land Mobile Network (PLMN) IDs allowed for this frequency relation.\n\nA UE that does not support a PLMN included in allowedPlmnList does not measure on this frequency according to the UE Handover Restriction List.\n\nNo values in allowedPlmnList imply that the frequency has no restrictions for PLMN.\n\nThe PLMN identity consists of the following parts:\n1. MobileCountryCode, MCC, 3 digits\n2. MobileNetworkCode, MNC, 2 or 3 digits (the correct number of digits is set in the mncLength member of this Struct)\n\nFor example, if MCC=125 and MNC=46, then plmnId=12546.";
      erienmyext:enm-type STRUCT;
      uses erienmnrmlrat:struct-PlmnIdentity;
    } // end 'list allowedPlmnList'
    leaf mobilityActionBr {
      description "Preferred transfer of CAT-M UE in connected mode to this E-UTRA frequency. Value 0 means Release with redirect, value 1 means Handover.";
      yexte:takes-effect "New connection";
      type erienmnrmlrat:enum-MobilityActionEUtran;
      default HANDOVER;
    }
    list blackListEntry {
      min-elements 0;
      max-elements 32;
      key auto-generated-struct-key;
      leaf auto-generated-struct-key {
        type uint16;
        description "This leaf has been injected to allow for struct instances in a sequence to be ordered.";
        mandatory true;
      }
      description "This parameter specifies a list of PCI that are blacklisted in EUTRAN measurements as described in 3GPP TS 36.331.";
      erienmyext:enm-type STRUCT;
      uses erienmnrmlrat:struct-BlackListEntry;
    } // end 'list blackListEntry'
    leaf lbA5Thr1RsrpFreqOffset {
      description "The frequency-relation specific offset for the absolute threshold a5Threshold1Rsrp, RSRP threshold1 for event A5, used for Inter-frequency load balancing.";
      yexte:takes-effect "Ongoing connection";
      type erienmnrmlrat:ddt-Lrat_EUtranFreqRelation_lbA5Thr1RsrpFreqOffset;
      default 0;
    }
    leaf hybridCsgPhysCellId {
      description "PCI for the Hybrid CSG cell. It is the start physical cell ID of Hybrid CSG cell. If value is equal to 1000, it means that Hybrid CSG cell is not supported for this frequency relation.";
      yexte:dependencies "If hybridCsgPhysCellId != 1000, hybridCsgPhysCellId + hybridCsgPhysCellIdRange <= 504";
      type erienmnrmlrat:ddt-Lrat_EUtranFreqRelation_hybridCsgPhysCellId;
      default 1000;
    }
    leaf eutranFrequencyRef {
      yexte:restricted;
      description "Refers to the EUTRAN frequency MO, EUtranFrequency.";
      mandatory true;
      erienmyext:enm-type MOREF;
      type string;
    }
    leaf qOffsetFreq {
      description "Frequency specific offset for E-UTRAN frequencies used in connected mode. In idle mode,  the negative value of this offset is used.\nSpecification: 3GPP TS 36.331";
      type erienmnrmlrat:ddt-Lrat_EUtranFreqRelation_qOffsetFreq;
      default 0;
    }
    list eutranFreqToQciProfileRelation {
      min-elements 0;
      max-elements 23;
      key auto-generated-struct-key;
      leaf auto-generated-struct-key {
        type uint16;
        description "This leaf has been injected to allow for struct instances in a sequence to be ordered.";
        mandatory true;
      }
      description "Encapsulates parameters for service specific load management for a certain QCI profile.";
      erienmyext:enm-type STRUCT;
      uses erienmnrmlrat:struct-EUtranFreqToQciProfileRelation;
    } // end 'list eutranFreqToQciProfileRelation'
    leaf connectedModeMobilityPrio {
      description "Prioritizes EUTRAN frequencies among all frequencies related to the cell for UEs in connected mode.\n(0 means the lowest priority. -1 means the frequency is excluded.)";
      yexte:takes-effect "New connection";
      type erienmnrmlrat:ddt-Lrat_EUtranFreqRelation_connectedModeMobilityPrio;
      default 7;
    }
    leaf nonPlannedPciCIO {
      description "Cell Individual Offset value for the Non-planned PCI, CSG or Hybrid CSG neighbor cell. Used when UE is in connected mode.";
      yexte:takes-effect "New connection";
      type erienmnrmlrat:ddt-Lrat_EUtranFreqRelation_nonPlannedPciCIO;
      default 0;
    }
    leaf tReselectionEutraCe {
      description "The cell reselection timer TreselectionEUTRA_CE for E-UTRA.";
      type erienmnrmlrat:ddt-Lrat_EUtranFreqRelation_tReselectionEutraCe;
      default 2;
    }
    leaf nonPlannedPhysCellIdRange {
      description "PCI range for the Non-planned PCI.";
      yexte:dependencies "If nonPlannedPhysCellId != 1000, nonPlannedPhysCellId + nonPlannedPhysCellIdRange <= 504";
      type erienmnrmlrat:ddt-Lrat_EUtranFreqRelation_nonPlannedPhysCellIdRange;
      default 1;
    }
    leaf threshXHighQ {
      description "Parameter \"ThreshX, HighQ\" in TS 36.304.\nFor the EUtranFreqRelation that points to the intra frequency EUtranFrequency MO, the attribute is invalid, that is, this attribute does not affect SIB3.";
      yexte:dependencies "The field is mandatory present if the Struct Member threshServingLowQ in SIB3 is used in systemInformationBlockType3.";
      type erienmnrmlrat:ddt-Lrat_EUtranFreqRelation_threshXHighQ;
      default 2;
    }
    leaf a5Thr1RsrpFreqOffset {
      description "The frequency-relation specific offset for the absolute threshold a5Threshold1Rsrp, RSRP threshold1 for event A5, used for Multi-Layer Service-Triggered Mobility.";
      yexte:takes-effect "Ongoing connection";
      type erienmnrmlrat:ddt-Lrat_EUtranFreqRelation_a5Thr1RsrpFreqOffset;
      default 0;
    }
    leaf qQualMinRsrqCe {
      description "Min quality level (RSRQ) in cell for UE in enhanced coverage mode.\nCorresponds to Qqualmin_CE in TS 36.304. Sent in SIB3 or SIB5. Depends on whether related frequency is intra- or inter-frequency. If 0, it is not sent and UE applies default value of negative infinity for Qqualmin_CE.";
      type erienmnrmlrat:ddt-Lrat_EUtranFreqRelation_qQualMinRsrqCe;
      default 0;
    }
    leaf arpPrio {
      description "Prioritizes EUTRAN frequencies among all frequencies related to the cell. Sets the priority to which frequency to perform mobility for a bearer with specific ARP Priority Level when the feature Service or Priority-Triggered Inter-Frequency Handover is activated.\nThe value -1 means the frequency is excluded.\nThe value 0 means the lowest priority.\nThe value 7 means the highest priority.";
      yexte:takes-effect "New connection";
      type erienmnrmlrat:ddt-Lrat_EUtranFreqRelation_arpPrio;
      default 0;
    }
    leaf tReselectionEutraSfHigh {
      description "The attribute t-ReselectionEUTRA is multiplied with this factor if the UE is in high mobility state. Corresponds to the parameter Speed dependent ScalingFactor for TreselectionEUTRAN for medium high state in 3GPP TS 36.304.\nValue mapping:\n25 = 0.25\n50 = 0.5\n75 = 0.75\n100 = 1.0";
      type erienmnrmlrat:ddt-Lrat_EUtranFreqRelation_tReselectionEutraSfHigh;
      default 100;
    }
    leaf atoAllowed {
      description "Specifies whether Admission-triggered offload (ATO) is activated from the current cell towards a certain EUTRAN frequency.";
      yexte:disturbances "Changing this attribute can affect traffic.";
      type boolean;
      default false;
    }
    leaf voicePrio {
      description "Prioritizes EUTRAN frequencies among all frequencies related to the cell for UEs in connected mode. Sets the priority to which frequency to perform mobility to for a voice session.\nThe value -1 means the frequency is excluded.\nThe value 0 means the lowest priority.\nThe value 7 means the highest priority.";
      yexte:takes-effect "New connection";
      type erienmnrmlrat:ddt-Lrat_EUtranFreqRelation_voicePrio;
      default 0;
    }
    leaf tReselectionEutraSfMedium {
      description "The attribute t-ReselectionEUTRA is multiplied with this factor if the UE is in medium mobility state. Corresponds to the parameter Speed dependent ScalingFactor for TreselectionEUTRAN for medium mobility state in 3GPP TS 36.304.\nValue mapping:\n25 = 0.25\n50 = 0.5\n75 = 0.75\n100 = 1.0";
      type erienmnrmlrat:ddt-Lrat_EUtranFreqRelation_tReselectionEutraSfMedium;
      default 100;
    }
    leaf qQualMin {
      description "Parameter \"Qqualmin\" in TS 36.304.\nValue 0 means that it is not sent and UE applies in such case the (default) value of negative infinity for Qqualmin. Sent in SIB3 or SIB5.\n";
      type erienmnrmlrat:ddt-Lrat_EUtranFreqRelation_qQualMin;
      default 0;
    }
    leaf hybridCsgPhysCellIdRange {
      description "The range of PCI for the Hybrid CSG cell.";
      yexte:dependencies "If hybridCsgPhysCellId != 1000, hybridCsgPhysCellId + hybridCsgPhysCellIdRange <= 504";
      type erienmnrmlrat:ddt-Lrat_EUtranFreqRelation_hybridCsgPhysCellIdRange;
      default 1;
    }
    leaf userLabel {
      description "Label for free use.\n";
      type erienmnrmlrat:ddt-Lrat_EUtranFreqRelation_userLabel;
    }
    leaf connectedModeMobilityPrioBr {
      description "E-UTRAN frequency priority among frequencies related to cell for CAT-M UEs in connected mode. Value 0 means lowest priority, value -1 means frequency is excluded.";
      yexte:takes-effect "New connection";
      type erienmnrmlrat:ddt-Lrat_EUtranFreqRelation_connectedModeMobilityPrioBr;
      default 7;
    }
    leaf mobilityAction {
      description "The preferred way to transfer a UE in connected mode to this EUTRA frequency.";
      type erienmnrmlrat:enum-MobilityActionEUtran;
      default HANDOVER;
    }
    leaf nonPlannedPciTargetIdType {
      description "Target eNodeB Identity type for the Non-planned PCI neighbor cell. Attribute is used to encode the message Handover Required when it is defined in TS36.413 ch. 9.1.5.1, S1AP parameter Global eNB ID.";
      type erienmnrmlrat:enum-NonPlannedPciTargetIdType;
      default MACRO_ENODEB_ID;
    }
    leaf csgPhysCellIdRange {
      description "The range of PCI for the closed access mode CSG cell. The information is broadcasted in SIB4.";
      yexte:dependencies "If csgPhysCellId != 1000, csgPhysCellId + csgPhysCellIdRange <= 504";
      type erienmnrmlrat:ddt-Lrat_EUtranFreqRelation_csgPhysCellIdRange;
      default 1;
    }
    leaf voicePrioBr {
      description "E-UTRAN frequency priority among frequencies related to cell for UEs in connected mode. Priority of frequency to perform mobility to for a voice session. Value -1 means frequency is excluded, value 0 means lowest priority, value 7 means highest priority.";
      yexte:takes-effect "New connection";
      type erienmnrmlrat:ddt-Lrat_EUtranFreqRelation_voicePrioBr;
      default 0;
    }
    leaf csmUeCapMonitorEnabled {
      description "Whether or not UE capability monitoring for the coverage frequency on capacity cell is enabled.";
      type boolean;
      default false;
    }
    leaf threshXLow {
      description "The threshold used in reselection towards frequency X priority from a higher priority frequency. Each frequency of E-UTRAN can have a specific threshold. Corresponds to parameter Thresx,low in 3GPP TS 36.304.";
      type erienmnrmlrat:ddt-Lrat_EUtranFreqRelation_threshXLow;
      default 0;
    }
    leaf anrMeasOn {
      description "ANR performs measurement on the referenced frequency if this parameter is set to true. Otherwise, ANR does not perform any measurements on this frequency.";
      yexte:takes-effect "New connection";
      type boolean;
      default true;
    }
    leaf qRxLevMin {
      description "The required minimum received Reference Symbol Received Power\n(RSRP) level in the (E-UTRA) frequency for cell reselection. Corresponds to parameter Qrxlevmin in 3GPP TS 36.304. This attribute is broadcast in SIB3 or SIB5, depending on whether the related frequency is intra- or inter-frequency.";
      type erienmnrmlrat:ddt-Lrat_EUtranFreqRelation_qRxLevMin;
      default -140;
    }
    leaf csmUeCapMonitorTime {
      description "Length of time that sleep criteria monitors UE capability for coverage frequency. Only valid if attribute csmUeCapMonitorEnabled is set to true. Value 0 means that sleep criteria checks connected UEs.";
      type erienmnrmlrat:ddt-Lrat_EUtranFreqRelation_csmUeCapMonitorTime;
      default 60;
    }
    leaf tReselectionEutra {
      description "The cell reselection timer TreselectionRAT for E-UTRA. Value in seconds.";
      type erienmnrmlrat:ddt-Lrat_EUtranFreqRelation_tReselectionEutra;
      default 2;
    }
    leaf cellReselectionPriority {
      description "The absolute priority of the carrier frequency used by the cell reselection procedure. Corresponds to the parameter priority in 3GPP TS 36.304.\nValue 0 means lowest priority. The UE behavior when no value is entered is specified in 3GPP TS 36.304.";
      yexte:dependencies "The value must be unique and not already used by other RAT, i.e. equal priorities between RATs are not supported.";
      type erienmnrmlrat:ddt-Lrat_EUtranFreqRelation_cellReselectionPriority;
      default 7;
    }
    leaf caFreqPriority {
      description "Prioritizes EUTRAN frequency carriers from which to pick SCells for carrier aggregation. 0 means lowest priority. -1 means the frequency is excluded from SCell selection.";
      yexte:takes-effect "New connection";
      yexte:dependencies "Only applicable when CarrierAggregationFunction::dynamicSCellSelectionMethod == PRIORITIZED. Can also be applied to dynamicSCellSelectionMethod == PRIORITIZED_AUTOMATIC as long as Configurable SCell Priority is licensed.";
      type erienmnrmlrat:ddt-Lrat_EUtranFreqRelation_caFreqPriority;
      default 4;
    }
    leaf caTriggeredRedirectionActive {
      description "Parameter used to specify whether or not CA triggered redirection is activated from the current cell towards a certain frequency.";
      yexte:disturbances "Changing this attribute can affect traffic";
      yexte:takes-effect "New connection";
      type boolean;
      default true;
    }
    list blackListEntryIdleMode {
      min-elements 0;
      max-elements 16;
      key auto-generated-struct-key;
      leaf auto-generated-struct-key {
        type uint16;
        description "This leaf has been injected to allow for struct instances in a sequence to be ordered.";
        mandatory true;
      }
      description "This parameter specifies blacklisted cells in SIB4 and SIB5.";
      erienmyext:enm-type STRUCT;
      uses erienmnrmlrat:struct-BlackListEntry;
    } // end 'list blackListEntryIdleMode'
    leaf pMax {
      description "Calculates the parameter Pcompensation (defined in 3GPP TS 36.304), at cell reselection to an E-UTRAN Cell. Corresponds to parameter PEMAX in 3GPP TS 36.101.\nValue 1000 means the parameter is not sent in the system information block.";
      type erienmnrmlrat:ddt-Lrat_EUtranFreqRelation_pMax;
      default 1000;
    }
    leaf cioQci1Enabled {
      description "Enables cellIndividualOffsetEUtranQci1 on frequency relation level.";
      type boolean;
      default false;
    }
    leaf presenceAntennaPort1 {
      description "Indicates if all the neighboring cells use Antenna Port 1.  When set to TRUE, the UE expects that at least two cell-specific antenna ports are used in all neighboring cells.";
      type boolean;
      default false;
    }
    leaf amoAllowed {
      description "Whether or not AMO function is allowed. Used to turn off AMO function on frequency relation level.";
      type boolean;
      default true;
    }
    list a5OffsetPerPC {
      min-elements 0;
      max-elements 2;
      key auto-generated-struct-key;
      leaf auto-generated-struct-key {
        type uint16;
        description "This leaf has been injected to allow for struct instances in a sequence to be ordered.";
        mandatory true;
      }
      description "The frequency-relation specific offset for the absolute threshold, RSRP/RSRQ threshold1 and threshold2 for event A5, used for Multi-Layer Service-Triggered Mobility and high power UE.";
      erienmyext:enm-type STRUCT;
      uses erienmnrmlrat:struct-A5PCOffsetMCPC;
    } // end 'list a5OffsetPerPC'
    leaf timeOfCreation {
      erienmyext:no-notification;
      config false;
      description "Indicates the time and date when the MO was created.\nFormat: YYYY-MM-DD HH:MM:SS";
      type erienmnrmlrat:ddt-Lrat_EUtranFreqRelation_timeOfCreation;
    }
    list candNeighborRel {
      min-elements 0;
      max-elements 256;
      key auto-generated-struct-key;
      leaf auto-generated-struct-key {
        type uint16;
        description "This leaf has been injected to allow for struct instances in a sequence to be ordered.";
        mandatory true;
      }
      description "The neighbor relations candidate list.";
      erienmyext:enm-type STRUCT;
      uses erienmnrmlrat:struct-CandNeighborRelInfoRO;
    } // end 'list candNeighborRel'
    leaf qRxLevMinCe {
      description "Min received RSRP level in E-UTRA frequency for cell reselection for UE in enhanced coverage mode. Corresponds to parameter Qrxlevmin_CE in 3GPP TS 36.304. This attribute is broadcast in SIB1-BR. This attribute is broadcast in SIB3 or SIB5. Depends on whether related frequency is intra- or inter-frequency.";
      type erienmnrmlrat:ddt-Lrat_EUtranFreqRelation_qRxLevMinCe;
      default -140;
    }
    leaf cellSleepCovCellMeasOn {
      description "Cell sleep mode performs measurement on the referenced frequency for coverage cell discovery if this parameter is set to true. Otherwise, cell sleep mode does not perform any measurements on this frequency.";
      yexte:takes-effect "New connection";
      type boolean;
      default true;
    }
    leaf mdtMeasOn {
      description "If true, MDT measures referenced frequency. Otherwise, MDT does not perform any MDT measurements on this frequency. This attribute is only applicable for MDT reportingTrigger set to PERIODICAL.";
      yexte:takes-effect "New connection";
      type boolean;
      default true;
    }
    leaf allowedMeasBandwidth {
      description "The maximum allowed measurement bandwidth on a carrier frequency.\nNote: The values indicate the number of resource blocks and correspond to the channel bandwidth 1,4MHz, 3MHz, 5MHz, 10MHz, 15MHz, 20MHz respectively specified in 3GPP TS 36.104.";
      yexte:disturbances "Changing this attribute can cause loss of traffic.";
      type erienmnrmlrat:ddt-Lrat_EUtranFreqRelation_allowedMeasBandwidth;
      default 6;
    }
    leaf a5Thr2RsrqFreqOffset {
      description "The frequency-relation specific offset for the absolute threshold a5Threshold2Rsrq, RSRQ threshold2 for event A5, used for Multi-Layer Service-Triggered Mobility.";
      yexte:takes-effect "Ongoing connection";
      type erienmnrmlrat:ddt-Lrat_EUtranFreqRelation_a5Thr2RsrqFreqOffset;
      default 0;
    }
    leaf timeOfLastModification {
      config false;
      description "Indicates the time and date when the MO was last modified.\nFormat: YYYY-MM-DD HH:MM:SS";
      notife:notifiable-state-data true;
      type erienmnrmlrat:ddt-Lrat_EUtranFreqRelation_timeOfLastModification;
    }
    leaf a3RsrqFreqOffsetAdjustment {
      description "Frequency-relation specific offset adjustment for absolute offset a3OffsetRsrq for event A3, used for Multi-Layer Service-Triggered Mobility.";
      type erienmnrmlrat:ddt-Lrat_EUtranFreqRelation_a3RsrqFreqOffsetAdjustment;
      default 0;
    }
    leaf a5Thr1RsrqFreqOffset {
      description "The frequency-relation specific offset for the absolute threshold a5Threshold1Rsrq, RSRQ threshold1 for event A5, used for Multi-Layer Service-Triggered Mobility.";
      yexte:takes-effect "Ongoing connection";
      type erienmnrmlrat:ddt-Lrat_EUtranFreqRelation_a5Thr1RsrqFreqOffset;
      default 0;
    }
    leaf interFreqMeasType {
      description "The type of event based measurements on other LTE frequencies.";
      yexte:takes-effect "New connection";
      type erienmnrmlrat:enum-InterFreqMeasType;
      default EVENT_A5;
    }
    leaf neighCellConfig {
      description "Provides to the UE information related to MBSFN and TDD UL/DL configuration of neighbor cells.\nFor TDD, the values DIFF_MBSFN_SUBFRAMES, SAME_MBSFN_SUBFRAMES and NO_MBSFN_SUBFRAMES indicates same UL/DL allocation in neighboring cells compared to the serving cell.\nThe value is included in SIB3, SIB5 and MeasObjectEUTRA.";
      type erienmnrmlrat:enum-NeighCellConfig;
      default SAME_MBSFN_SUBFRAMES;
    }
    leaf caFreqProportion {
      description "In conjunction with caPrioThreshold the value sets a threshold for the number of SCells on this frequency carrier that can be configured using prioritized SCell selection. A normalized value is applied. When frequency carriers have same priority, SCells are selected on the carrier with the lowest proportional SCell utilization.";
      yexte:takes-effect "New connection";
      yexte:dependencies "Only applicable when CarrierAggregationFunction::dynamicSCellSelectionMethod == PRIORITIZED.";
      type erienmnrmlrat:ddt-Lrat_EUtranFreqRelation_caFreqProportion;
      default 100;
    }
    leaf createdBy {
      config false;
      description "Indicates whether the MO has been created by the Automated Neighbor Relations (ANR) function or operator or X2";
      notife:notifiable-state-data true;
      type erienmnrmlrat:enum-CreatedByEutran;
    }
    leaf lbBnrPolicy {
      description "Specifies the policy for updating the loadBalancing attribute by the feature Best Neighbor Relations for Intra-LTE Load Management. The policy is valid for all cell relations corresponding to this EUtranFreqRelation.";
      type erienmnrmlrat:enum-EUtranLbBnrPolicyVals;
      default AUTO;
    }
    leaf nonPlannedPhysCellId {
      description "Specific PCI reserved by operator for Femto Cell. It is the initial physical cell ID of Non-planned PCI. If value equals 1000, Non-planned PCI is not configured for this frequency relation.";
      yexte:dependencies "This attribute has a dependency to nonPlannedPhysCellIdRange.";
      type erienmnrmlrat:ddt-Lrat_EUtranFreqRelation_nonPlannedPhysCellId;
      default 1000;
    }
    leaf lbActivationThreshold {
      description "The minimum target cell load (subscription ratio) the source cell takes into account when determining the amount of load balancing action to a cell using this carrier frequency.";
      type erienmnrmlrat:ddt-Lrat_EUtranFreqRelation_lbActivationThreshold;
      default 0;
    }
    leaf threshXHigh {
      description "The threshold used by the UE when reselecting towards the higher priority frequency X from the current serving frequency. Each frequency of E-UTRAN can have a specific threshold. Refer to the parameter Thresx,high in 3GPP TS 36.304.";
      type erienmnrmlrat:ddt-Lrat_EUtranFreqRelation_threshXHigh;
      default 4;
    }
    leaf lastModification {
      config false;
      description "Indicates whether the MO was last modified by the Automated Neighbor Relations (ANR) function or operator or X2 and if the MO is to be deleted who triggered the deletion";
      notife:notifiable-state-data true;
      type erienmnrmlrat:enum-LastModificationEutran;
    }
  } // end 'grouping moc-EUtranFreqRelation'
  grouping moc-DataRadioBearer-keys {
    description "Key(s) for MOC DataRadioBearer";
    leaf id {
      erienmyext:no-notification;
      description "The value component of the RDN.";
      mandatory true;
      yexte:ecim-name dataRadioBearerId;
      type string;
    }
  } // end 'grouping moc-DataRadioBearer-keys'
  grouping moc-DataRadioBearer {
    description "Radio Bearer configuration.\n\nThe RDN of this MO is DataRadioBearer=1.";
    leaf tPollRetransmitUl {
      description "Time lapsed before request for new poll if no STATUS report arrives for the Sequence Number that is contained in the UL RLC Data PDU where the poll bit is set.";
      yexte:disturbances "Changing this attribute can cause significantly higher drop rate.";
      yexte:takes-effect "New connection.";
      type erienmnrmlrat:ddt-Lrat_DataRadioBearer_tPollRetransmitUl;
      default 80;
    }
    leaf tPollRetransmitDl {
      description "Time lapsed before request for new poll if no STATUS report arrives for the Sequence Number that is contained in the DL RLC Data PDU where the poll bit is set.";
      yexte:takes-effect "Cell lock/unlock";
      type erienmnrmlrat:ddt-Lrat_DataRadioBearer_tPollRetransmitDl;
      default 80;
    }
    leaf dlMaxRetxThreshold {
      description "Maximum number RLC re-transmissions in DL before stopping and indicating to RRC that the RLC threshold is reached.";
      yexte:takes-effect "Cell lock/unlock";
      type erienmnrmlrat:ddt-Lrat_DataRadioBearer_dlMaxRetxThreshold;
      default 8;
    }
    leaf ulMaxRetxThreshold {
      description "Maximum number RLC re-transmissions in UL before stopping and indicating to RRC that the RLC threshold is reached.";
      yexte:disturbances "Lowering the value of this attribute can cause significantly higher drop rate.";
      yexte:takes-effect "New connection.";
      type erienmnrmlrat:ddt-Lrat_DataRadioBearer_ulMaxRetxThreshold;
      default 8;
    }
  } // end 'grouping moc-DataRadioBearer'
  grouping moc-ReportConfigEUtraBadCovPrim-keys {
    description "Key(s) for MOC ReportConfigEUtraBadCovPrim";
    leaf id {
      erienmyext:no-notification;
      description "The value component of the Relative Distinguished Name (RDN).\n";
      mandatory true;
      yexte:ecim-name reportConfigEUtraBadCovPrimId;
      type string;
    }
  } // end 'grouping moc-ReportConfigEUtraBadCovPrim-keys'
  grouping moc-ReportConfigEUtraBadCovPrim {
    description "This managed object contains the Report Configuration settings for primary bad coverage UE measurements.\n\nThe RDN of this MO is ReportConfigEUtraBadCovPrim=1.";
    leaf a2ThresholdRsrpPrim {
      description "The primary Reference Signal Received Power (RSRP) threshold value for eventA2. Used only when triggerQuantityA2Prim is set to RSRP.\nPrimary and secondary measurement attributes refer to the option to use different settings for two simultaneous measurements for eventA2.";
      yexte:takes-effect "New connection";
      type erienmnrmlrat:ddt-Lrat_ReportConfigEUtraBadCovPrim_a2ThresholdRsrpPrim;
      default -140;
    }
    leaf a2ThrRsrpPrimOffsetCeABr {
      description "CAT-M UE in CE mode A Bad coverage Offset for the absolute threshold a2ThresholdRsrpPrim.";
      yexte:takes-effect "New connection";
      type erienmnrmlrat:ddt-Lrat_ReportConfigEUtraBadCovPrim_a2ThrRsrpPrimOffsetCeABr;
      default 0;
    }
    leaf hysteresisA2Prim {
      description "The hysteresis value for the primary eventA2 measurement. Primary and secondary measurement parameters refer to the option to use different settings for two simultaneous measurements for eventA2.\n";
      yexte:takes-effect "New connection";
      type erienmnrmlrat:ddt-Lrat_ReportConfigEUtraBadCovPrim_hysteresisA2Prim;
      default 10;
    }
    leaf timeToTriggerA2Prim {
      description "The time-to-trigger value for the primary eventA2 measurement. Primary and secondary measurement parameters refer to the option to use different settings for two simultaneous measurements for eventA2.";
      yexte:takes-effect "New connection";
      type erienmnrmlrat:ddt-Lrat_ReportConfigEUtraBadCovPrim_timeToTriggerA2Prim;
      default 640;
    }
    leaf triggerQuantityA2Prim {
      description "The quantity that triggers the eventA2 and eventA1 for the primary eventA2 and eventA1 measurement. Primary and secondary measurement parameters refer to the option to use different settings for two simultaneous measurements for eventA2 and eventA1.";
      yexte:takes-effect "New connection";
      type erienmnrmlrat:enum-TriggerQuantity;
      default RSRP;
    }
    leaf a2ThresholdRsrqPrim {
      description "The primary Reference Signal Received Quality (RSRQ) threshold value for eventA2. Used only when triggerQuantityA2Prim is set to RSRQ.\nPrimary and secondary measurement attributes refer to the option to use different settings for two simultaneous measurements for eventA2.";
      yexte:takes-effect "New connection";
      type erienmnrmlrat:ddt-Lrat_ReportConfigEUtraBadCovPrim_a2ThresholdRsrqPrim;
      default -195;
    }
  } // end 'grouping moc-ReportConfigEUtraBadCovPrim'
  grouping moc-RATFreqPrio-keys {
    description "Key(s) for MOC RATFreqPrio";
    leaf id {
      erienmyext:no-notification;
      description "The value component of the RDN";
      mandatory true;
      yexte:ecim-name rATFreqPrioId;
      type string;
    }
  } // end 'grouping moc-RATFreqPrio-keys'
  grouping moc-RATFreqPrio {
    description "Contains data that overrides information in the IdleModeMobilityControlInfo and RedirectedCarrierInfo (sent to UE in RRC Connection Release) that is configured for the cell. It also contains attributes that control load balancing and offloading. Only UEs that have a SPID value matching the list in this MOC are affected.";
    list bandClassPrioListCDMA1xRtt {
      min-elements 0;
      max-elements 128;
      key auto-generated-struct-key;
      leaf auto-generated-struct-key {
        type uint16;
        description "This leaf has been injected to allow for struct instances in a sequence to be ordered.";
        mandatory true;
      }
      description "CDMA2000 1xRTT frequency prioritization.\nThis attribute prioritizes CDMA2000 1xRTT frequencies among all frequencies related to the cell for UE cell reselection procedure and for UEs in connected mode. It is not possible to create every possible frequency and band relation since that would require too many instances using this representation.";
      erienmyext:enm-type STRUCT;
      uses erienmnrmlrat:struct-BandClassPrioCdma1xRtt;
    } // end 'list bandClassPrioListCDMA1xRtt'
    list freqGroupPrioListGERAN {
      min-elements 0;
      max-elements 96;
      key auto-generated-struct-key;
      leaf auto-generated-struct-key {
        type uint16;
        description "This leaf has been injected to allow for struct instances in a sequence to be ordered.";
        mandatory true;
      }
      description "Prioritizes GERAN frequencies among all frequencies related to the cell for UE cell reselection procedure and for UEs in connected mode.";
      erienmyext:enm-type STRUCT;
      uses erienmnrmlrat:struct-FreqGroupPrioGERAN;
    } // end 'list freqGroupPrioListGERAN'
    leaf userLabel {
      description "Label for free use.\n";
      type erienmnrmlrat:ddt-Lrat_RATFreqPrio_userLabel;
    }
    leaf-list spidList {
      min-elements 0;
      max-elements 20;
      description "A list that includes all UEs that are affected by the RAT priorities specified in this MOC.\nNote: When value is configured to -1000, the parameter is ignored.";
      yexte:takes-effect "Ongoing connection";
      type erienmnrmlrat:ddt-Lrat_RATFreqPrio_spidList;
      default -1000;
      default -1000;
      default -1000;
      default -1000;
      default -1000;
      default -1000;
      default -1000;
      default -1000;
      default -1000;
      default -1000;
      default -1000;
      default -1000;
      default -1000;
      default -1000;
      default -1000;
      default -1000;
      default -1000;
      default -1000;
      default -1000;
      default -1000;
    }
    list bandClassPrioListCDMA2000 {
      min-elements 0;
      max-elements 128;
      key auto-generated-struct-key;
      leaf auto-generated-struct-key {
        type uint16;
        description "This leaf has been injected to allow for struct instances in a sequence to be ordered.";
        mandatory true;
      }
      description "Prioritizes CDMA2000 frequencies among all frequencies related to the cell for UE cell reselection procedure and for Ues in connected mode. It is not possible to create every possible frequency and band relation since that would require to many instances using this representation.";
      erienmyext:enm-type STRUCT;
      uses erienmnrmlrat:struct-BandClassPrioCDMA2000;
    } // end 'list bandClassPrioListCDMA2000'
    leaf t320 {
      description "Validity time for cell reselection priority information provided by dedicated signalling. Used by the UE. This parameter is only used in the optional feature 'subscriber triggered mobility' when setting new cell reselection priorities based on SPID value for a specific UE.";
      yexte:takes-effect "Ongoing connection";
      type erienmnrmlrat:ddt-Lrat_RATFreqPrio_t320;
      default 30;
    }
    list freqPrioListEUTRA {
      min-elements 0;
      max-elements 24;
      key auto-generated-struct-key;
      leaf auto-generated-struct-key {
        type uint16;
        description "This leaf has been injected to allow for struct instances in a sequence to be ordered.";
        mandatory true;
      }
      description "Prioritizes EUTRAN frequencies among all frequencies related to the cell for UE cell reselection procedure and for UEs in connected mode.";
      erienmyext:enm-type STRUCT;
      uses erienmnrmlrat:struct-FreqPrioEUTRA;
    } // end 'list freqPrioListEUTRA'
    list freqPrioListUTRA {
      min-elements 0;
      max-elements 64;
      key auto-generated-struct-key;
      leaf auto-generated-struct-key {
        type uint16;
        description "This leaf has been injected to allow for struct instances in a sequence to be ordered.";
        mandatory true;
      }
      description "Prioritizes UTRAN frequencies among all frequencies related to the cell for UE cell reselection procedure and for Ues in connected mode.";
      erienmyext:enm-type STRUCT;
      uses erienmnrmlrat:struct-FreqPrioUTRAN;
    } // end 'list freqPrioListUTRA'
  } // end 'grouping moc-RATFreqPrio'
  grouping moc-PreschedulingProfile-keys {
    description "Key(s) for MOC PreschedulingProfile";
    leaf id {
      erienmyext:no-notification;
      description "The value component of the Relative Distinguished Name (RDN).";
      mandatory true;
      yexte:takes-effect "Object unlocked";
      yexte:ecim-name preschedulingProfileId;
      type string;
    }
  } // end 'grouping moc-PreschedulingProfile-keys'
  grouping moc-PreschedulingProfile {
    description "Contains prescheduling profiles, prescheduling parameters, to map towards the different QCIs.\n\nThe RDN of this MO is PreschedulingProfile=initial.";
    leaf preschedulingDuration {
      description "Prescheduling is stopped if there are no UL transmissions during this time.";
      yexte:takes-effect "Object unlocked";
      type erienmnrmlrat:ddt-Lrat_PreschedulingProfile_preschedulingDuration;
      default 200;
    }
    leaf preschedulingDataSize {
      description "Granted data size during prescheduling period.";
      yexte:takes-effect "Object unlocked";
      type erienmnrmlrat:ddt-Lrat_PreschedulingProfile_preschedulingDataSize;
      default 86;
    }
    leaf preschedulingPeriod {
      description "Period in ms lapsed between granted prescheduling instances.";
      yexte:takes-effect "Object unlocked";
      type erienmnrmlrat:ddt-Lrat_PreschedulingProfile_preschedulingPeriod;
      default 5;
    }
  } // end 'grouping moc-PreschedulingProfile'
  grouping moc-GtpuApplicationTunnel-keys {
    description "Key(s) for MOC GtpuApplicationTunnel";
    leaf id {
      erienmyext:no-notification;
      description "The value component of the Relative Distinguished Name (RDN).";
      mandatory true;
      yexte:ecim-name gtpuApplicationTunnelId;
      type string;
    }
  } // end 'grouping moc-GtpuApplicationTunnel-keys'
  grouping moc-GtpuApplicationTunnel {
    description "Designates a GTP-U tunnel used to support a baseband-to-baseband application.\n\nThe RDNs of these MOs are GtpuApplicationTunnel=0 to GtpuApplicationTunnel=1.";
  } // end 'grouping moc-GtpuApplicationTunnel'
  grouping moc-BbLink-keys {
    description "Key(s) for MOC BbLink";
    leaf id {
      erienmyext:no-notification;
      description "The value component of the RDN.";
      mandatory true;
      yexte:ecim-name bbLinkId;
      type string;
    }
  } // end 'grouping moc-BbLink-keys'
  grouping moc-BbLink {
    description "Models a eRAN application link between the basebands of the eNodeB and a neighboring eNodeB.\n\nThe RDNs of these MOs are BbLink=1 to BbLink=5.\n\nThe BbLink MO under ExternalENodeBFunction is deprecated since L17A and will be removed. The new parent MO is EranInterMeLink.";
    leaf localPort {
      status deprecated {
        yexte:status-information "Since L17A. Has no functional behavior. Planned to be removed.";
      }
      erienmyext:no-notification;
      config false;
      description "The EthernetPortId for the local end of the BB link.";
      type erienmnrmlrat:ddt-Lrat_BbLink_localPort;
    }
    leaf vlanId {
      status deprecated {
        yexte:status-information "Since L17A. Has no functional behavior. Planned to be removed.";
      }
      erienmyext:no-notification;
      config false;
      description "The VLAN identifier for receiving and transmitting traffic for the BB link on an EthernetPort.";
      type erienmnrmlrat:ddt-Lrat_BbLink_vlanId;
    }
    leaf localAddress {
      erienmyext:no-notification;
      config false;
      description "Local baseband entity MAC address.";
      type erienmnrmlrat:ddt-MacAddressStr;
    }
    leaf remotePort {
      status deprecated {
        yexte:status-information "Since L17A. Has no functional behavior. Planned to be removed.";
      }
      erienmyext:no-notification;
      config false;
      description "The EthernetPortId for the remote end of the BB link.";
      type erienmnrmlrat:ddt-Lrat_BbLink_remotePort;
    }
    leaf-list availabilityStatus {
      min-elements 0;
      erienmyext:no-notification;
      config false;
      description "The availability status. It contains details about operationalState.";
      type erienmnrmlrat:enum-AvailStatus;
    }
    leaf operationalState {
      erienmyext:no-notification;
      config false;
      description "The operational state.";
      type erienmnrmlrat:enum-OperState;
    }
    leaf remoteAddress {
      erienmyext:no-notification;
      config false;
      description "Remote baseband entity MAC address.";
      type erienmnrmlrat:ddt-MacAddressStr;
    }
  } // end 'grouping moc-BbLink'
  grouping moc-ReportConfigSearch-keys {
    description "Key(s) for MOC ReportConfigSearch";
    leaf id {
      erienmyext:no-notification;
      description "The value component of the Relative Distinguished Name (RDN).";
      mandatory true;
      yexte:ecim-name reportConfigSearchId;
      type string;
    }
  } // end 'grouping moc-ReportConfigSearch-keys'
  grouping moc-ReportConfigSearch {
    description "Contains report configuration settings for search area measurements that relate to features Mobility Control at Poor Coverage and Multi-Layer Service-Triggered Mobility (MLSTM). Corresponds to parameters needed for A2search, A1Search, A2OuterSearch and A2Critical events and QCI specific offsets to such parameters.\n\nThe RDN of this MO is ReportConfigSearch=1.";
    leaf timeToTriggerA2Critical {
      description "Time-to-trigger value for measurement in event A2Critical. If timeToTriggerA2CriticalRsrq is -1, this attribute is used for both RSRP and RSRQ. But if not set to -1, this attribute is used only for RSRP.";
      yexte:takes-effect "New connection";
      type erienmnrmlrat:ddt-Lrat_ReportConfigSearch_timeToTriggerA2Critical;
      default 40;
    }
    leaf timeToTriggerA2CriticalRsrq {
      description "Time-to-trigger value for measurement in event A2Critical with trigger quantity RSRQ. The value -1 means that this attribute is not used for report configuration.";
      yexte:takes-effect "New connection";
      type erienmnrmlrat:ddt-Lrat_ReportConfigSearch_timeToTriggerA2CriticalRsrq;
      default -1;
    }
    leaf hysteresisA1A2UlSearch {
      description "Hysteresis value for UL events A1 UL search and A2 UL search measurements.";
      type erienmnrmlrat:ddt-Lrat_ReportConfigSearch_hysteresisA1A2UlSearch;
      default 20;
    }
    leaf inhibitA2SearchConfig {
      description "Inhibit type of A2Search Report configuration.";
      yexte:takes-effect "New connection";
      type erienmnrmlrat:enum-InhibitA2SearchConfig;
      default NOT_INHIBIT;
    }
    leaf a1a2UlSearchThreshold {
      description "UL-normalized SINR max threshold value for events A1 UL and A2 UL search.\nConfiguring this parameter to a value greater than 320 rarely allows UEs into Uplink Good Coverage zone.";
      yexte:dependencies "a1a2UlSearchThreshold >= a2UlCriticalThreshold";
      type erienmnrmlrat:ddt-Lrat_ReportConfigSearch_a1a2UlSearchThreshold;
      default -150;
    }
    leaf a2CriticalThrQci1RsrqOffset {
      description "QCI1 offset on cell level for threshold a2CriticalThresholdRsrq, RSRQ threshold value for events A2Critical. Note: RSRQ thresholds are configured in 0.5dB steps according to 3GPP TS36.331. Use multiples of 5 for this attribute. Other values are rounded down to the closest lower multiple of 5.";
      yexte:takes-effect "New connection";
      type erienmnrmlrat:ddt-Lrat_ReportConfigSearch_a2CriticalThrQci1RsrqOffset;
      default 0;
    }
    leaf timeToTriggerA2OutSearch {
      description "Time-to-trigger value for measurement in event A2OuterSearch. If timeToTriggerA2OutSearchRsrq is -1, this attribute is used for both RSRP and RSRQ. But if not set to -1, this attribute is used only for RSRP.";
      yexte:takes-effect "New connection";
      type erienmnrmlrat:ddt-Lrat_ReportConfigSearch_timeToTriggerA2OutSearch;
      default 40;
    }
    leaf timeToTriggerA2UlSearch {
      description "Time-to-trigger value for UL measurement in event A2 UL search.";
      type erienmnrmlrat:ddt-Lrat_ReportConfigSearch_timeToTriggerA2UlSearch;
      default 40;
    }
    leaf timeToTriggerA1SearchRsrq {
      description "Time-to-trigger value for measurement in event A1Search with trigger quantity RSRQ. The value -1 means that this attribute is not used for report configuration.";
      yexte:takes-effect "New connection";
      type erienmnrmlrat:ddt-Lrat_ReportConfigSearch_timeToTriggerA1SearchRsrq;
      default -1;
    }
    leaf hysteresisA1A2SearchRsrq {
      description "The hysteresis value for RSRQ in events A1Search and A2Search measurements.";
      yexte:takes-effect "New connection";
      type erienmnrmlrat:ddt-Lrat_ReportConfigSearch_hysteresisA1A2SearchRsrq;
      default 15;
    }
    leaf a2OuterSearchThrRsrqOffset {
      description "Offset for threshold a1a2SearchThresholdRsrq to configure RSRQ threshold value for events A2OuterSearch. Note: RSRQ thresholds are configured in 0.5dB steps according to 3GPP TS36.331. Use multiples of 5 for this attribute. Other values are rounded down to the closest lower multiple of 5.";
      yexte:takes-effect "New connection";
      type erienmnrmlrat:ddt-Lrat_ReportConfigSearch_a2OuterSearchThrRsrqOffset;
      default 0;
    }
    leaf hysteresisA2UlCritical {
      description "Hysteresis value for UL event A2 UL critical measurements.";
      type erienmnrmlrat:ddt-Lrat_ReportConfigSearch_hysteresisA2UlCritical;
      default 20;
    }
    leaf timeToTriggerA1Search {
      description "Time-to-trigger value for measurement in event A1Search. If timeToTriggerA1SearchRsrq is -1, this attribute is used for both RSRP and RSRQ. But if not set to -1, this attribute is used only for RSRP.";
      yexte:takes-effect "New connection";
      type erienmnrmlrat:ddt-Lrat_ReportConfigSearch_timeToTriggerA1Search;
      default 640;
    }
    list qciA1A2ThrOffsets {
      min-elements 0;
      max-elements 19;
      key auto-generated-struct-key;
      leaf auto-generated-struct-key {
        type uint16;
        description "This leaf has been injected to allow for struct instances in a sequence to be ordered.";
        mandatory true;
      }
      description "Parameters for adding QCI profile specific offsets to threshold values for events A1Search and A2Search used for mobility decisions. Applicable if Multi-Layer Service-Triggered Mobility is active.";
      erienmyext:enm-type STRUCT;
      uses erienmnrmlrat:struct-ReportConfigParamsQciOffset;
    } // end 'list qciA1A2ThrOffsets'
    leaf timeToTriggerA2OutSearchRsrq {
      description "Time-to-trigger value for measurement in event A2OuterSearch with trigger quantity RSRQ. The value -1 means that this attribute is not used for report configuration.";
      yexte:takes-effect "New connection";
      type erienmnrmlrat:ddt-Lrat_ReportConfigSearch_timeToTriggerA2OutSearchRsrq;
      default -1;
    }
    leaf hysteresisA2OuterSearchRsrp {
      description "Hysteresis value for RSRP in events A2OuterSearch measurements.";
      yexte:takes-effect "New connection";
      type erienmnrmlrat:ddt-Lrat_ReportConfigSearch_hysteresisA2OuterSearchRsrp;
      default 20;
    }
    leaf a1a2SearchThresholdRsrp {
      description "The Reference Signal Received Power (RSRP) threshold value for events A1Search and A2Search.\nIf Multi-Layer Service Triggered Mobility feature is enabled QCI offsets in QciProfilePredefined configuration is overridden by this feature QCI configuration.";
      yexte:takes-effect "New connection";
      type erienmnrmlrat:ddt-Lrat_ReportConfigSearch_a1a2SearchThresholdRsrp;
      default -134;
    }
    leaf hysteresisA2OuterSearchRsrq {
      description "Hysteresis value for RSRQ in events A2OuterSearch measurements.";
      yexte:takes-effect "New connection";
      type erienmnrmlrat:ddt-Lrat_ReportConfigSearch_hysteresisA2OuterSearchRsrq;
      default 15;
    }
    leaf a1a2SearchThresholdRsrq {
      description "The Reference Signal Received Quality (RSRQ) threshold value for events A1Search and A2Search.\nIf Multi-Layer Service Triggered Mobility feature is enabled QCI offsets in QciProfilePredefined configuration is overridden by this feature QCI configuration.";
      yexte:takes-effect "New connection";
      type erienmnrmlrat:ddt-Lrat_ReportConfigSearch_a1a2SearchThresholdRsrq;
      default -165;
    }
    leaf timeToTriggerA2UlCritical {
      description "Time-to-trigger value for UL measurement in event A2 UL critical.";
      type erienmnrmlrat:ddt-Lrat_ReportConfigSearch_timeToTriggerA2UlCritical;
      default 40;
    }
    leaf hysteresisA1A2SearchRsrp {
      description "The hysteresis value for RSRP in events A1Search and A2Search measurements.";
      yexte:takes-effect "New connection";
      type erienmnrmlrat:ddt-Lrat_ReportConfigSearch_hysteresisA1A2SearchRsrp;
      default 20;
    }
    leaf timeToTriggerA2Search {
      description "Time-to-trigger value for measurement in event A2Search. If timeToTriggerA2SearchRsrq is -1, this attribute is used for both RSRP and RSRQ. But if not set to -1, this attribute is used only for RSRP.";
      yexte:takes-effect "New connection";
      type erienmnrmlrat:ddt-Lrat_ReportConfigSearch_timeToTriggerA2Search;
      default 40;
    }
    list a2CriticalOffsetPerPC {
      min-elements 0;
      max-elements 2;
      key auto-generated-struct-key;
      leaf auto-generated-struct-key {
        type uint16;
        description "This leaf has been injected to allow for struct instances in a sequence to be ordered.";
        mandatory true;
      }
      description "The high power UE specific offset for the absolute threshold. RSRP/RSRQ threshold value for event A2Critical.";
      erienmyext:enm-type STRUCT;
      uses erienmnrmlrat:struct-A2CriticalPCOffsetMCPC;
    } // end 'list a2CriticalOffsetPerPC'
    leaf hysteresisA2CriticalRsrp {
      description "The hysteresis value for RSRP in event A2Critical measurement.";
      yexte:takes-effect "New connection";
      type erienmnrmlrat:ddt-Lrat_ReportConfigSearch_hysteresisA2CriticalRsrp;
      default 10;
    }
    leaf timeToTriggerA1UlSearch {
      description "Time-to-trigger value for UL measurement in event A1 UL search.";
      type erienmnrmlrat:ddt-Lrat_ReportConfigSearch_timeToTriggerA1UlSearch;
      default 40;
    }
    leaf hysteresisA2CriticalRsrq {
      description "The hysteresis value for RSRQ in event A2Critical measurement.";
      yexte:takes-effect "New connection";
      type erienmnrmlrat:ddt-Lrat_ReportConfigSearch_hysteresisA2CriticalRsrq;
      default 10;
    }
    leaf a2CriticalThrQci1RsrpOffset {
      description "QCI1 offset on cell level for threshold a2CriticalThresholdRsrp, RSRP threshold value for events A2Critical.";
      yexte:takes-effect "New connection";
      type erienmnrmlrat:ddt-Lrat_ReportConfigSearch_a2CriticalThrQci1RsrpOffset;
      default 0;
    }
    leaf timeToTriggerA2SearchRsrq {
      description "Time-to-trigger value for measurement in event A2Search with trigger quantity RSRQ. The value -1 means that this attribute is not used for report configuration.";
      yexte:takes-effect "New connection";
      type erienmnrmlrat:ddt-Lrat_ReportConfigSearch_timeToTriggerA2SearchRsrq;
      default -1;
    }
    leaf a2CriticalThresholdRsrp {
      description "The Reference Signal Received Power (RSRP) threshold value for event A2Critical.";
      yexte:takes-effect "New connection";
      type erienmnrmlrat:ddt-Lrat_ReportConfigSearch_a2CriticalThresholdRsrp;
      default -140;
    }
    leaf a2CriticalThresholdRsrq {
      description "The Reference Signal Received Quality (RSRQ) threshold value for event A2Critical.";
      yexte:takes-effect "New connection";
      type erienmnrmlrat:ddt-Lrat_ReportConfigSearch_a2CriticalThresholdRsrq;
      default -195;
    }
    leaf a2UlCriticalThreshold {
      description "UL-normalized SINR max threshold value for event A2 UL critical.";
      yexte:dependencies "a1a2UlSearchThreshold >= a2UlCriticalThreshold";
      type erienmnrmlrat:ddt-Lrat_ReportConfigSearch_a2UlCriticalThreshold;
      default -150;
    }
    list qciA1A2UlThrOffsets {
      min-elements 0;
      max-elements 19;
      key auto-generated-struct-key;
      leaf auto-generated-struct-key {
        type uint16;
        description "This leaf has been injected to allow for struct instances in a sequence to be ordered.";
        mandatory true;
      }
      description "Array of structure type ReportConfigParamsUlQciOffset, containing parameters for addition of QCI profile specific offsets to UL threshold values for events A1 UL and A2 UL search used for mobility decisions.\nApplicable if Multi-Layer Service-Triggered Mobility is active.";
      erienmyext:enm-type STRUCT;
      uses erienmnrmlrat:struct-ReportConfigParamsUlQciOffset;
    } // end 'list qciA1A2UlThrOffsets'
    leaf a2OuterSearchThrRsrpOffset {
      description "Offset for threshold a1a2SearchThresholdRsrp to configure RSRP threshold value for events A2OuterSearch.";
      yexte:takes-effect "New connection";
      type erienmnrmlrat:ddt-Lrat_ReportConfigSearch_a2OuterSearchThrRsrpOffset;
      default 0;
    }
  } // end 'grouping moc-ReportConfigSearch'
  grouping moc-FlexibleQoSFunction-keys {
    description "Key(s) for MOC FlexibleQoSFunction";
    leaf id {
      erienmyext:no-notification;
      description "The value component of the RDN.";
      mandatory true;
      yexte:ecim-name flexibleQoSFunctionId;
      type string;
    }
  } // end 'grouping moc-FlexibleQoSFunction-keys'
  grouping moc-FlexibleQoSFunction {
    description "Contains eNB specific configuration used for feature Flexible QoS.\n\nThe RDN of this MO is FlexibleQoSFunction=1.";
  } // end 'grouping moc-FlexibleQoSFunction'
  grouping moc-RlfProfile-keys {
    description "Key(s) for MOC RlfProfile";
    leaf id {
      erienmyext:no-notification;
      description "The value component of the RDN.";
      mandatory true;
      yexte:ecim-name rlfProfileId;
      type string;
    }
  } // end 'grouping moc-RlfProfile-keys'
  grouping moc-RlfProfile {
    description "Contains RLF profiles and RLF parameters to map to the different QCIs. The first instance, RlfProfileId 0, is the default RLF profile.\n\nThe RDNs of these MOs are RlfProfile=0 to RlfProfile=22.\n\nThe timers and constants settings are provided to the UE by dedicated signaling.";
    leaf t301 {
      description "UE timer to supervise a response to RRC Connection Reestablishment Request (according to 3GPP TS 36.331), during a radio connection re-establishment procedure. The UE returns to Idle and optionally starts to reconnect over NAS when the timer expires.";
      yexte:disturbances "Lowering the value can increase drop rate.";
      yexte:takes-effect "New connection";
      type erienmnrmlrat:ddt-Lrat_RlfProfile_t301;
      default 400;
    }
    leaf n310 {
      description "Maximum number of consecutive \"out of sync\" indications received from lower layers.";
      yexte:disturbances "Lowering the value can increase drop rate.";
      yexte:takes-effect "New connection";
      type erienmnrmlrat:ddt-Lrat_RlfProfile_n310;
      default 20;
    }
    leaf n311 {
      description "Maximum number of consecutive \"in-sync\" indications received from lower layers.";
      yexte:disturbances "Increasing the value can increase drop rate.";
      yexte:takes-effect "New connection";
      type erienmnrmlrat:ddt-Lrat_RlfProfile_n311;
      default 1;
    }
    leaf-list reservedBy {
      min-elements 0;
      config false;
      description "Contains a list of QciProfile instances that reserve this MO instance.";
      notife:notifiable-state-data true;
      erienmyext:enm-type MOREF;
      type string;
    }
    leaf t311 {
      description "UE timer triggered at radio link failure to supervise the period where the UE tries to re-establish the radio connection, either by performing RRC Connection Reestablishment (according to 3GPP TS 36.331), or by finding a suitable cell on another RAT. The UE returns to Idle and optionally starts to reconnect over NAS when the timer expires.";
      yexte:disturbances "Lowering the value can increase drop rate.";
      yexte:takes-effect "New connection";
      type erienmnrmlrat:ddt-Lrat_RlfProfile_t311;
      default 3000;
    }
    leaf t310 {
      description "Waiting time for radio link failure.\nUsed by the UE.";
      yexte:disturbances "Lowering the value can increase drop rate.";
      yexte:takes-effect "New connection";
      type erienmnrmlrat:ddt-Lrat_RlfProfile_t310;
      default 2000;
    }
  } // end 'grouping moc-RlfProfile'
  grouping moc-EUtranCellFDD-keys {
    description "Key(s) for MOC EUtranCellFDD";
    leaf id {
      erienmyext:no-notification;
      description "The value component of the RDN.\n";
      mandatory true;
      yexte:ecim-name eUtranCellFDDId;
      type string;
    }
  } // end 'grouping moc-EUtranCellFDD-keys'
  grouping moc-EUtranCellFDD {
    description "This MO represents a Cell and contains parameters needed by the cell. It also contains parameters for the mandatory common channels.\n";
    leaf ns05LowBandSchedMode {
      description "Controls if the low band can be allocated to NS_05 UEs. When ns05LowBandSchedMode is configured to 'ALWAYS_PROHIBIT', the low band cannot be allocated to the NS_05 UEs. When ns05LowBandSchedMode is configured to 'ALWAYS_AVAILABLE', the low band can always be allocated to the NS_05 UEs. When ns05LowBandSchedMode is configured to 'ADAPTIVE_AVAILABLE_BY_REPEATER_DETECTION', the low band can only be allocated to the NS_05 UEs which are detected as not in repeater zone.";
      yexte:dependencies "Only takes effect if:\n- license for NS 05 Additional Maximum Power Reduction Support is present and the feature is active, and\n- attribute networkSignallingValue in MOC EUtranCellFDD/TDD is NS_05.";
      type erienmnrmlrat:enum-Ns05LBSchedMode;
      default ALWAYS_PROHIBIT;
    }
    leaf ulInterferenceManagementActive {
      description "Specifies if uplink interference management is enabled or disabled.";
      yexte:takes-effect "Object unlocked";
      type boolean;
      default true;
    }
    leaf iuaMaxResourcePerCell {
      status deprecated {
        yexte:status-information "Since 18.Q3. Replaced by InstantUplinkAccess::iuaCellResourceLimit. Planned to be removed.";
      }
      description "Maximum percentage of UL PRBs and SEs that are used by IUA at cell level. The actual number of resources per cell depends on iuaMaxResourcePerBbm.";
      type erienmnrmlrat:ddt-Lrat_EUtranCellFDD_iuaMaxResourcePerCell;
      default 20;
    }
    leaf physicalLayerCellId {
      config false;
      description "Physical-layer cell ID.";
      yexte:dependencies "Equal to 3 x physicalLayerCellIdGroup + physicalLayerSubCellId.";
      notife:notifiable-state-data true;
      type erienmnrmlrat:ddt-Lrat_EUtranCellFDD_physicalLayerCellId;
    }
    leaf hpueCaSwitchThres {
      description "SINR threshold for triggering a switch to high power UE.";
      type erienmnrmlrat:ddt-Lrat_EUtranCellFDD_hpueCaSwitchThres;
      default -150;
    }
    leaf ulHarqVolteBlerTarget {
      description "The UL BLER target to be used for VoLTE UEs. This BLER target will be used for all UL transmissions for UEs that have a QCI1 bearer configured. If a UE does not have QCI1 bearer configured the normal UL BLER target will be used.";
      yexte:takes-effect "Object unlocked";
      type erienmnrmlrat:ddt-Lrat_EUtranCellFDD_ulHarqVolteBlerTarget;
      default 5;
    }
    leaf extGUtranCellRef {
      description "Reference to an instance of ExternalGUtranCell. If set, indicated GUTRAN cell must have coverage over this cell.";
      yexte:takes-effect "New connection";
      erienmyext:enm-type MOREF;
      type string;
    }
    leaf pdcchOuterLoopInitialAdj {
      description "The initial value for PDCCH outer loop adjustment for UEs that do not have any secondary cell configured and do not have any bearer mapped to a QCI with serviceType of VoIP. In TDD, this parameter applies only to UEs which are configured with HARQ-ACK bundling.";
      yexte:takes-effect "Object unlocked";
      type erienmnrmlrat:ddt-Lrat_EUtranCellFDD_pdcchOuterLoopInitialAdj;
      default -70;
    }
    leaf dummyCdmaBandClass {
      description "Dummy CDMA frequency band in the MobilityParametersCDMA2000 information element that can be used to force registration each time the UE moves across LTE and CDMA 1xRTT networks. This can be achieved by setting both this parameter to a dummy band class that is not used in the native CDMA 1xRTT network and by setting the powerUpReg flag to TRUE in SIB-8. The default value of 99 or UNDEFINED_VALUE means the value configured in Cdma2000FreqBand::cdmaBandClass is sent in the MobilityParametersCDMA2000 information element which is the same value as the one  sent in SIB-8.";
      yexte:takes-effect "New connection";
      type erienmnrmlrat:enum-HrpdBandClass;
      default UNDEFINED_VALUE;
    }
    leaf cellBarred {
      description "Indicates if the cell is barred and should not be accessible to random UEs.";
      yexte:disturbances "Changing this attribute to BARRED blocks all traffic in the cell.";
      type erienmnrmlrat:enum-CellBarred;
      default NOT_BARRED;
    }
    leaf-list additionalSpectrumEmissionValues {
      min-elements 0;
      max-elements 8;
      config false;
      description "A list of network signaling values, where each value corresponds to the frequency band on the same position in additionalFreqBandList. Enables additional spectrum emission requirements according to 3GPP TS 36.101, table 6.2.4-1 when the feature Multiple Frequency Band Indicators is enabled in the cell. The content of this list is based on spectrumEmissionReqMapping. This list will be broadcasted in SIB2 as multiBandInfoList.";
      notife:notifiable-state-data true;
      type erienmnrmlrat:enum-NetworkSignallingValue;
    }
    leaf cceDynUeAdmCtrlOverloadThr {
      description "Highest allowed control channel element radio resource utilization ratio for admission of a non-privileged UE. Resource utilization is checked against this threshold for all new, re-established, or incoming handover RRC connections.";
      yexte:disturbances "Changing this attribute can affect the following:\n- the number of RRC-connected users\n- cell throughput and the number of rejected non-privileged RRC connection requests\n- rejected non-privileged RRC connection re-establishment requests and rejected\n  non-privileged incoming handover requests.";
      yexte:dependencies "cceDynUeAdmCtrlOverloadThr >= cceDynUeAdmCtrlRetDiffThr";
      type erienmnrmlrat:ddt-Lrat_EUtranCellFDD_cceDynUeAdmCtrlOverloadThr;
      default 600;
    }
    leaf dlDynUeAdmCtrlRetDiffThr {
      description "Highest allowed DL radio resource utilization ratio for admission of a new non-privileged UE. Applies to each DL resource considered by Dynamic UE Admission Control. Resource utilization is checked against this threshold for all new RRC connections.";
      yexte:disturbances "Changing this attribute can affect the following:\n- the number of RRC-connected users\n- cell throughput and the number of rejected non-privileged RRC connection requests.";
      yexte:dependencies "dlDynUeAdmCtrlRetDiffThr =< dlDynUeAdmCtrlOverloadThr";
      type erienmnrmlrat:ddt-Lrat_EUtranCellFDD_dlDynUeAdmCtrlRetDiffThr;
      default 500;
    }
    leaf preambleInitialReceivedTargetPower {
      description "Initial preamble power value in dBm, according to 3GPP specification 36.331 and 36.321.";
      yexte:takes-effect "Cell lock/unlock";
      type erienmnrmlrat:ddt-Lrat_EUtranCellFDD_preambleInitialReceivedTargetPower;
      default -110;
    }
    leaf enableUeAssistedSigReduction {
      description "Enable or disable the UE-Assisted Signaling Reduction feature.";
      yexte:takes-effect "Object unlocked";
      type boolean;
      default true;
    }
    leaf dynUeAdmCtrlEnabled {
      description "Enable Dynamic UE Admission Control at cell level.";
      yexte:disturbances "Changing this attribute can affect the following:\n- the number of RRC-connected users\n- cell throughput and the number of rejected non-privileged RRC connection requests\n- rejected non-privileged RRC connection re-establishment requests and rejected\n  non-privileged incoming handover requests.";
      yexte:takes-effect "Cell lock/unlock";
      yexte:dependencies "Only relevant if the license for Dynamic UE Admission Control is present and the feature is active.";
      type boolean;
      default false;
    }
    leaf cellSubscriptionCapacity {
      description "Normalized subscription capacity of the cell. The value represents the total capacity of the cell used for traffic load balancing purposes.";
      yexte:disturbances "Low values reduce cell capacity.";
      type erienmnrmlrat:ddt-Lrat_EUtranCellFDD_cellSubscriptionCapacity;
      default 1000;
    }
    leaf plmnPabBarringPriorityLevel {
      config false;
      description "Current PLMN priority level based on PLMN Progressive Access Barring algorithm.";
      notife:notifiable-state-data true;
      type erienmnrmlrat:enum-AcBarringPlmnPriorityLevel;
    }
    leaf maxSoftLockBackoffTime {
      description "Indicates a maximum handover backoff time. The value is applied to inhibit further handover attempts to a EUTRAN target cell that rejects incoming handover for soft-lock of cell.";
      type erienmnrmlrat:ddt-Lrat_EUtranCellFDD_maxSoftLockBackoffTime;
      default 90;
    }
    leaf acBarringPlmnPabEnabled {
      description "Enables Prioritized PLMN Progressive Access Barring in cell.";
      yexte:disturbances "Changing this attribute can cause loss of traffic.";
      type boolean;
      default false;
    }
    leaf outOfCoverageThreshold {
      description "Threshold for when UE is considered to be Out Of Coverage (OOC). If the number of OOC trigger events is greater than or equal to the threshold, the UE is in the OOC state; if the number of OOC trigger events is less than the threshold, the UE is not in the OOC state.";
      yexte:takes-effect "Cell lock/unlock";
      type erienmnrmlrat:ddt-Lrat_EUtranCellFDD_outOfCoverageThreshold;
      default 20;
    }
    leaf freqBand {
      config false;
      description "The primary frequency band the cell belongs to according to its defined EARFCN.";
      notife:notifiable-state-data true;
      type erienmnrmlrat:ddt-Lrat_EUtranCellFDD_freqBand;
    }
    leaf ttiBundlingAfterHo {
      description "Controls if UE remains in TTI bundling mode after handover.";
      type erienmnrmlrat:enum-TtiBundlingModeAfterHandover;
      default NO_TTI_BUNDLING;
    }
    leaf plmn1AbConfProfileRef {
      description "Reference to an instance of PlmnAbConfProfile. Points to the PLMN Access Barring configuration profile.";
      yexte:disturbances "Changing this attribute can cause loss of traffic.";
      yexte:dependencies "References plmn1AbConfProfileRef, plmn2AbConfProfileRef and plmn3AbConfProfileRef must point to unique PlmnAbConfProfile MO instance.";
      erienmyext:enm-type MOREF;
      type string;
    }
    leaf ailgAutoRestartEnabled {
      description "If set to true, AILG is automatically restarted when:\n- cell disabled followed by cell enabled, for example at node start or restart.";
      yexte:takes-effect "Object disabled/enabled";
      type boolean;
      default false;
    }
    leaf cellCapMaxCellSubCap {
      description "Maximum value for the estimated cell capacity.";
      yexte:dependencies "cellCapMinCellSubCap < cellCapMaxCellSubCap";
      type erienmnrmlrat:ddt-Lrat_EUtranCellFDD_cellCapMaxCellSubCap;
      default 1500;
    }
    leaf loadBasedCaEnabled {
      description "Enables Load-Based CA SCell Handling.";
      yexte:takes-effect "Next cell unlock";
      yexte:dependencies "Only relevant if license for Load-Based CA SCell Handling is present and feature is active.";
      type boolean;
      default false;
    }
    container eutranCellCoverage {
      description "Models the cell coverage area used for UE positioning. The cell coverage area is defined by the cell bearing, cell opening angle and cell radius.\n\nThis attribute has no operational impact.";
      erienmyext:enm-type STRUCT;
      uses erienmnrmlrat:struct-EutranCellArea;
    } // end 'container eutranCellCoverage'
    leaf measGapShareSchemeCeABr {
      description "Measurement gap sharing scheme for CAT-M UE. Values based on 3GPP 36.133 table 8.13.2.1.1.1-2.";
      yexte:takes-effect "New connection";
      type erienmnrmlrat:enum-MeasGapShareScheme;
      default SCHEME_ZERO;
    }
    leaf servOrPrioIFHoSetupBearer {
      description "Determines whether a bearer that fulfills the criteria for the feature Service- or Priority-Triggered Inter-Frequency Handover is set up, or rejected in UE .";
      type boolean;
      default true;
    }
    leaf filterUeDlThpTimeThr {
      description "Defines DRB transport time threshold for counter pmUeThpDlMbbFilteredDistr. UE session with DRB transport time less than this threshold is filtered out.";
      yexte:takes-effect "Next ROP";
      type erienmnrmlrat:ddt-Lrat_EUtranCellFDD_filterUeDlThpTimeThr;
      default 50;
    }
    leaf elcEnabled {
      description "Enables Ericsson Lean Carrier functionality in the cell.";
      yexte:takes-effect "Object unlocked";
      yexte:dependencies "Only relevant if the licence for ELC is present and the feature is active.";
      type boolean;
      default false;
    }
    leaf rtpTimeout {
      description "Enables operator configuration of the RTP timeout value at the eNodeB at a cell level that corresponds to the RTP timeout value get set at the IMS layer.";
      type erienmnrmlrat:ddt-Lrat_EUtranCellFDD_rtpTimeout;
      default 10;
    }
    leaf uncertSemiMajor {
      description "Semi-major axis of uncertainty. The uncertainty (r) is derived from the uncertainty code (k) by:\nr = 10 * ((1.1^k) - 1).";
      type erienmnrmlrat:ddt-Lrat_EUtranCellFDD_uncertSemiMajor;
      default 0;
    }
    leaf uncertSemiMinor {
      description "Semi-minor axis of uncertainty. The uncertainty (r) is derived from the uncertainty code (k) by:\nr = 10 * ((1.1^k) - 1).";
      type erienmnrmlrat:ddt-Lrat_EUtranCellFDD_uncertSemiMinor;
      default 0;
    }
    leaf ulImprovedUeSchedLastEnabled {
      description "Whether or not UL scheduler is enabled to force allocation of PRBs to Data-Aware, UL-Scheduling UEs last.";
      type boolean;
      default true;
    }
    leaf prsPeriod {
      description "The period of Positioning Reference Signal (PRS) occasions. Valid periods include 160 ms, 320 ms, 640 ms and 1280 ms.\nprsPeriod is used to calculate the prsConfigIndex to avoid PRS sub-frame collisions with SIB1 sub-frames.";
      yexte:takes-effect "Object unlocked";
      type erienmnrmlrat:enum-PrsPerVals;
      default PP160;
    }
    list commonSFAllocList {
      min-elements 0;
      max-elements 8;
      key auto-generated-struct-key;
      leaf auto-generated-struct-key {
        type uint16;
        description "This leaf has been injected to allow for struct instances in a sequence to be ordered.";
        mandatory true;
      }
      description "Shows the subframes that are reserved for MBSFN in DL.";
      erienmyext:enm-type STRUCT;
      uses erienmnrmlrat:struct-SubFrameConfigRO;
    } // end 'list commonSFAllocList'
    leaf lbabBarringPriorityLevel {
      config false;
      description "Current barring priority level based on Progressive Access Barring or PLMN-Specific Access Barring algorithms.";
      yexte:dependencies "Only takes effect when feature Progressive Access Barring is activated.";
      notife:notifiable-state-data true;
      type erienmnrmlrat:enum-AcBarringPriorityLevel;
    }
    leaf operationalState {
      config false;
      description "The operational state.  This attribute is set by the application in the RBS.\n";
      notife:notifiable-state-data true;
      type erienmnrmlrat:enum-OperState;
    }
    leaf servOrPrioTriggeredErabAction {
      description "Specifies the action performed when a S1AP:E-RAB SETUP REQUEST arrives and both the feature Service or Priority-Triggered Inter-Frequency Handover is active and the conditions for the bearer request are fulfilled.";
      yexte:takes-effect "New connection";
      yexte:dependencies "This attribute only takes effect when attribute servOrPrioTriggeredIFHo has value 'QCI'.";
      type erienmnrmlrat:enum-ServOrPrioTriggeredErabActionType;
      default REJECT;
    }
    leaf pdcchOuterLoopUpStep {
      description "PDCCH outer loop up step size for UEs that do not have any secondary cell configured and do not have any bearer mapped to a QCI with serviceType of VoIP. In TDD, this parameter applies only to UEs which are configured with HARQ-ACK bundling.";
      yexte:takes-effect "Object unlocked";
      type erienmnrmlrat:ddt-Lrat_EUtranCellFDD_pdcchOuterLoopUpStep;
      default 8;
    }
    leaf ssacBarringForMMTELVideoPresent {
      status deprecated {
        yexte:status-information "Since 17.Q3. Replaced by AcBarringPresence.acBarringForMmtelVideoPresence in EUtranCellFDD/EUtranCellTDD::acBarringPresence. Planned to be removed.";
      }
      description "Specifies presence of Information Element ssac-BarringForMMTEL-Video-r9 in SIB2.";
      yexte:disturbances "Changing this attribute can block video calls in the cell.";
      type boolean;
      default false;
    }
    leaf externalCdma20001xRttCellRef {
      erienmyext:no-notification;
      description "Reference to an ExternalCdma20001xRttCell";
      erienmyext:enm-type MOREF;
      type string;
    }
    leaf puschMaxNrOfPrbsPerUe {
      description "Maximum number of physical resource blocks allowed on PUSCH for each UE.";
      yexte:takes-effect "Object unlocked";
      yexte:dependencies "This parameter only takes effect if the feature PUCCH Overdimensioning is activated.";
      type erienmnrmlrat:ddt-Lrat_EUtranCellFDD_puschMaxNrOfPrbsPerUe;
      default 100;
    }
    leaf maxValidSubframeDlBr {
      description "Upper limit of valid subframes for DL transmission of BR traffic.";
      yexte:takes-effect "Next cell unlock";
      type erienmnrmlrat:ddt-Lrat_EUtranCellFDD_maxValidSubframeDlBr;
      default 100;
    }
    leaf latitude {
      description "The degree of latitude of the transmitter antenna position.\nIn case of Combined Cell (multi-sector cell):\n   For indoor system, antenna of any sector.\n   For outdoor system,antenna of macro sector.";
      type erienmnrmlrat:ddt-Lrat_EUtranCellFDD_latitude;
      default 0;
    }
    container ssacBarringForMMTELVoice {
      description "Service specific access class barring parameters for MMTEL voice originating calls.\nInformation broadcasted in SIB2.";
      erienmyext:enm-type STRUCT;
      uses erienmnrmlrat:struct-AcBarringConfig;
    } // end 'container ssacBarringForMMTELVoice'
    leaf noOfPucchFormat1PrbPairsPerFrame {
      erienmyext:no-notification;
      config false;
      description "PRB usage for PUCCH Format1. Based on PUCCH SR, CFI and Carrier Aggregation user configuration.";
      type erienmnrmlrat:ddt-Lrat_EUtranCellFDD_noOfPucchFormat1PrbPairsPerFrame;
    }
    leaf sCellHandlingAtVolteCall {
      description "SCell handling during VoLTE calls.";
      yexte:takes-effect "New connection";
      type erienmnrmlrat:enum-SCellHandlingWithVolte;
      default KEEP_SCELLS;
    }
    leaf eDrxAllowed {
      description "Set to true when idle mode eDRX shall be allowed in the cell.";
      yexte:takes-effect "Next cell unlock";
      type boolean;
      default false;
    }
    leaf covTriggerdBlindHoAllowed {
      description "Says whether a blind Handover from this cell can be initiated when a UE reports bad coverage, or not. Note that even if the value is True, the eNB will only initiate a blind handover if it finds a suitable cell.";
      type boolean;
      default true;
    }
    leaf sCellHpueEnabled {
      status deprecated {
        yexte:status-information "Since 17.Q3. Has no functional behavior. Planned to be removed.";
      }
      description "Whether or not SCell selection for high power UE that is not capable of CA simultaneously is enabled.";
      type boolean;
      default true;
    }
    leaf prsConfigIndex {
      description "The Positioning Reference Signal (PRS) index value for the cell defines the periodicity of the PRS occasions and the PRS subframe offset, as defined in 3GPP TS 36.211. The value -1 (default) means that this parameter will not be used for setting the PRS period and prsSubframeOffset. Instead the parameter prsPeriod shall be used to directly set the PRS period while prsSubframeOffset will be set by the system to guarantee non collision with SIB1.";
      yexte:takes-effect "Object unlocked";
      type erienmnrmlrat:ddt-Lrat_EUtranCellFDD_prsConfigIndex;
      default -1;
    }
    container acBarringForMoData {
      description "Access class barring parameters for mobile originating calls.\nInformation broadcasted in SIB2.";
      erienmyext:enm-type STRUCT;
      uses erienmnrmlrat:struct-AcBarringConfig;
    } // end 'container acBarringForMoData'
    leaf-list additionalPlmnReservedList {
      min-elements 0;
      max-elements 5;
      description "For the list of PLMN IDs in the cell, indicates if they are reserved for operator use. The list must have the same number of entries as additonalPlmnList. The PLMN ID appearing in additionalPlmnList[x] is reserved when additionalPlmnListReserved[x] is set to true.";
      yexte:disturbances "Changing this attribute can cause loss of traffic.";
      yexte:dependencies "The length of this list must be the same as the list in addtionalPlmnList.";
      type boolean;
      default false;
      default false;
      default false;
      default false;
      default false;
    }
    leaf eranUlCompUserSelSinrThr {
      description "SINR threshold for Elastic RAN UL CoMP user selection.";
      yexte:dependencies "Must be used together with eranUlCompUserSelSinrHys.";
      type erienmnrmlrat:ddt-Lrat_EUtranCellFDD_eranUlCompUserSelSinrThr;
      default 150;
    }
    leaf cceDynUeAdmCtrlRetDiffThr {
      description "Highest allowed control channel element radio resource utilization ratio for admission of a new non-privileged UE. Resource utilization is checked against this threshold for all new RRC connections.";
      yexte:disturbances "Changing this attribute can affect the following:\n- the number of RRC-connected users\n- cell throughput and the number of rejected non-privileged RRC connection requests.";
      yexte:dependencies "cceDynUeAdmCtrlRetDiffThr =< cceDynUeAdmCtrlOverloadThr";
      type erienmnrmlrat:ddt-Lrat_EUtranCellFDD_cceDynUeAdmCtrlRetDiffThr;
      default 500;
    }
    leaf csiRsConfigType8TxFDD {
      description "This attribute specifies configuration type of CSI-RS (Channel State Information Reference Signal) for FDD 8Tx.";
      yexte:takes-effect "Cell lock/unlock";
      type erienmnrmlrat:enum-CsiRsConfigType8TxFDD;
      default NZP_CSIRS;
    }
    leaf otdoaCheckEnabled {
      description "Determines if the OTDOA functionality should be considered in the feature Service or Priority-Triggered Inter-Frequency Handover.";
      yexte:takes-effect "New connection";
      type boolean;
      default false;
    }
    leaf pdcchTargetBlerPCell {
      description "PDCCH target error rate for primary cells in case of carrier aggregation. This applies to UEs that have at least one secondary cell configured and do not have any bearer mapped to a QCI with serviceType of VoIP. In TDD, this parameter is not used.";
      yexte:takes-effect "Object unlocked";
      type erienmnrmlrat:ddt-Lrat_EUtranCellFDD_pdcchTargetBlerPCell;
      default 22;
    }
    leaf ttiBundlingAtSetup {
      description "Activation method of TTI Bundling with establishment of QCI1 bearer.";
      yexte:takes-effect "Next cell unlock";
      type erienmnrmlrat:enum-TtiBundlingAtSetup;
      default OFF;
    }
    leaf modificationPeriodCoeff {
      description "The modification period, expressed in number of radio frames = modificationPeriodCoeff * defaultPagingCycle. See MO Paging for information about defaultPagingCycle.";
      yexte:takes-effect "When EUtranCellFDD/TDD object is unlocked";
      yexte:dependencies "modificationPeriodCoeff * defaultPagingCycle must be equal or less than 1024 radio frames. See MO Paging for information about defaultPagingCycle.";
      type erienmnrmlrat:ddt-Lrat_EUtranCellFDD_modificationPeriodCoeff;
      default 2;
    }
    leaf ulChannelBandwidth {
      description "The uplink channel bandwidth in the cell.\nValid values: 1400, 3000, 5000, 10000, 15000, 20000\n";
      yexte:disturbances "Changes may affect traffic.";
      yexte:takes-effect "Object disabled/enabled.";
      yexte:dependencies "This attribute is dependent on and shall be set to the same as dlChannelBandwidth.";
      type erienmnrmlrat:ddt-Lrat_EUtranCellFDD_ulChannelBandwidth;
      default 10000;
    }
    leaf beamWeightSet16TrTm9 {
      description "Index that represents beam weight vector applied for beam forming when 16TR TM9 feature is used. If value is 0, feature is not active.";
      yexte:disturbances "Changing this attribute can affect traffic. A cell lock/unlock is required.";
      yexte:takes-effect "Next cell unlock";
      type erienmnrmlrat:ddt-Lrat_EUtranCellFDD_beamWeightSet16TrTm9;
      default 0;
    }
    leaf physicalLayerCellIdGroup {
      description "Physical layer cell ID group.\nPhysical layer cell IDs are grouped into 168 unique physical layer cell ID groups. Each group contains 3 unique subidentities.\nUsed with physicalLayerSubCellId to calculate physical layer cell ID.";
      mandatory true;
      yexte:disturbances "Changes may affect traffic.";
      type erienmnrmlrat:ddt-Lrat_EUtranCellFDD_physicalLayerCellIdGroup;
    }
    list additionalMultipleNSPmax {
      min-elements 0;
      max-elements 8;
      key auto-generated-struct-key;
      leaf auto-generated-struct-key {
        type uint16;
        description "This leaf has been injected to allow for struct instances in a sequence to be ordered.";
        mandatory true;
      }
      description "The attribute in broadcast in SIB1 as multiBandInfoList-v10j0. A list of additionalPmax and additionalSpectrumEmission values. If E-UTRAN includes multiBandInfoList-v10j0, it includes the same number of entries, and listed in the same order, as in multiBandInfoList.";
      erienmyext:enm-type STRUCT;
      uses erienmnrmlrat:struct-MultipleNSPmaxListRO;
    } // end 'list additionalMultipleNSPmax'
    leaf ptmCellProfileRef {
      description "Reference to an instance of PtmCellProfile that contains configuration for the cell.\nIf not set, PTM is disabled on the cell.";
      yexte:disturbances "Changing this attribute can affect traffic.";
      erienmyext:enm-type MOREF;
      type string;
    }
    leaf timeOfLastModification {
      description "Indicates the time and date when the MO was last modified.\nFormat: YYYY-MM-DD HH:MM:SS";
      type erienmnrmlrat:ddt-Lrat_EUtranCellFDD_timeOfLastModification;
      default "";
    }
    leaf deallocThrPucchFormat1 {
      description "Threshold in terms of number of remaining SR resources available for the cell. Above this threshold, deallocTimerPucchFormat1 for deallocation of a PUCCH format 1 PRB pair is triggered. Occurs if  feature Dynamic PUCCH  is activated.";
      type erienmnrmlrat:ddt-Lrat_EUtranCellFDD_deallocThrPucchFormat1;
      default 100;
    }
    leaf highestSupportedCeLevelBr {
      description "Max CE level for BR low-complexity UEs.\n0 enables CE level 0. 1 enables CE levels 0 and 1.";
      yexte:takes-effect "Next cell unlock";
      type erienmnrmlrat:ddt-Lrat_EUtranCellFDD_highestSupportedCeLevelBr;
      default 0;
    }
    leaf maxSentCrsAssistCells {
      description "Maximum number of neighbor cells whose CRS Assistance Information is sent to UE.";
      yexte:takes-effect "New connection";
      type erienmnrmlrat:ddt-Lrat_EUtranCellFDD_maxSentCrsAssistCells;
      default 8;
    }
    leaf uncertAltitude {
      description "The uncertainty altitude (h) expressed in meters is derived from the uncertainty altitude (k) by h = 45*((1.025)^k - 1).";
      type erienmnrmlrat:ddt-Lrat_EUtranCellFDD_uncertAltitude;
      default 0;
    }
    leaf ulBlerTargetEnabled {
      description "Turns feature Configurable UL BLER Target on and off.";
      type boolean;
      default false;
    }
    leaf-list reservedBy {
      min-elements 0;
      config false;
      description "Contains a list of managed object instances that reserves this managed object instance.\n";
      yexte:dependencies "The managed object cannot be deleted if it is reserved.";
      notife:notifiable-state-data true;
      erienmyext:enm-type MOREF;
      type string;
    }
    leaf tUeBlockingTimer {
      description "Length of time eNodeB rejects traffic requests from non-privileged UEs when detecting high procedure latency. Used in Procedure Latency Supervision. Privileged traffic, such as High Priority Access (HPA) and Emergency, is never rejected due to high procedure latency conditions.";
      yexte:takes-effect "Next cell unlock";
      type erienmnrmlrat:ddt-Lrat_EUtranCellFDD_tUeBlockingTimer;
      default 200;
    }
    leaf incrPrioServingFreqActive {
      status deprecated {
        yexte:status-information "Since 17.Q3. Has no functional behavior. Planned to be removed.";
      }
      description "Specifies whether or not the function to set the serving frequency as sticky carrier is active in the current cell.";
      yexte:disturbances "Changing this attribute can affect traffic.";
      type boolean;
      default false;
    }
    leaf mbsfnSubframesForTm9 {
      description "Enables PDSCH transmissions to UEs in Transmission Mode 9, and defines subframes within a frame configured as MBSFN subframe for this.\nEnabling causes TM9-capable UEs to be reconfigured to TM9. Performance of these UEs improves due to reduced inter-cell interference from cell-specific reference signals. UEs not supporting TM9 cannot be scheduled in MBSFN subframes, leading to worse performance. CSI-RS is transmitted when feature is enabled.";
      yexte:takes-effect "Next cell unlock";
      yexte:dependencies "Only takes effect if the licenses for CRS Interference Reduction for TM9 using MBSFN Subframes, and Dual-Antenna Downlink Performance Package are activated. For four transmit antenna systems, also the license for 4x2 Quad Antenna Downlink Performance Package must be activated. Feature will not take effect when enabled together with feature LTE Broadcast.";
      type erienmnrmlrat:enum-MbsfnSubframesForTm9;
      default DISABLED;
    }
    leaf qciTableRef {
      description "Refers to an instance of QciTable and assigns a QciTable to a cell. The QciTable defines Quality of Service Class Indicator (QCI) to use in the cell.\nRefers to the QciTable instance corresponding to Local Distinguished Name (LDN) = ManagementElement=1, ENodeBFunction=1, QciTable=default";
      yexte:takes-effect "New connection.";
      yexte:dependencies "It is assumed that the QciTable MO has been created.";
      erienmyext:enm-type MOREF;
      type string;
    }
    leaf prsMutingPattern {
      config false;
      description "Used for storing the calculated muting pattern for the cell. This parameter cannot be manually set.";
      yexte:takes-effect "Object unlocked";
      notife:notifiable-state-data true;
      type erienmnrmlrat:ddt-Lrat_EUtranCellFDD_prsMutingPattern;
    }
    leaf-list sectorCarrierRef {
      min-elements 0;
      max-elements 12;
      description "Reference to a list of instances of SectorCarrier MO.";
      yexte:disturbances "Change can affect traffic";
      yexte:takes-effect "Object disabled/enabled";
      erienmyext:enm-type MOREF;
      type string;
    }
    list mappingInfoBr {
      min-elements 0;
      max-elements 2;
      key auto-generated-struct-key;
      leaf auto-generated-struct-key {
        type uint16;
        description "This leaf has been injected to allow for struct instances in a sequence to be ordered.";
        mandatory true;
      }
      description "SI message to which each SIB is mapped.\nNote: SIB2 is always mapped to SI message 1 according to 3GPP TS 36.331.";
      status deprecated {
        yexte:status-information "Since 17.Q4. Planned to be removed.";
      }
      erienmyext:enm-type STRUCT;
      uses erienmnrmlrat:struct-MappingInfoSIBsBr;
    } // end 'list mappingInfoBr'
    leaf qRxLevMinOffset {
      description "The offset applied to the signaled Qrxlevmin. Corresponds to parameter Qrxlevminoffset in 3GPP TS 36.304. Value 1000 means it is not sent and the UE sets Qrxlevminoffset=0dB.";
      type erienmnrmlrat:ddt-Lrat_EUtranCellFDD_qRxLevMinOffset;
      default 1000;
    }
    leaf rateShapingActive {
      description "Indicates if End-user bitrate shaping functionality is activated in this cell.";
      yexte:takes-effect "Cell lock/unlock";
      yexte:dependencies "Only relevant if the license for End-user bitrate shaping is present and the feature is active.";
      type boolean;
      default false;
    }
    leaf channelSelectionSetSize {
      description "Determines the number of Channel Selection (CS) PUCCH resources in a CS set.\nSet to 1 when all SCell candidates are configured with transmission mode 1 or 2. Set to 2 when at least one SCell candidate is configured with transmission mode 3 or higher.";
      yexte:takes-effect "Object unlocked";
      yexte:dependencies "Applicable only when attribute noOfChannelSelectionSets > 0.\nOnly SCell candidates with TM mode resource requirements that match the CS set size are considered for carrier aggregation.";
      type erienmnrmlrat:ddt-Lrat_EUtranCellFDD_channelSelectionSetSize;
      default 2;
    }
    container loadBasedCaMsrThr {
      description "High and low MSR thresholds for Load-Based CA SCell Handling.";
      erienmyext:enm-type STRUCT;
      uses erienmnrmlrat:struct-LoadBasedCaMsrThr;
    } // end 'container loadBasedCaMsrThr'
    list activePlmnList {
      min-elements 0;
      max-elements 6;
      key auto-generated-struct-key;
      leaf auto-generated-struct-key {
        type uint16;
        description "This leaf has been injected to allow for struct instances in a sequence to be ordered.";
        mandatory true;
      }
      description "Lists the PLMN IDs served by at least one MME. The PLMN ID is defined in the attribute eNodeBPlmnId in the parent ENodeBFunction. PLMN IDs from additionalPlmnList also appear in this list. The list may include up to 6 PLMNs.";
      erienmyext:enm-type STRUCT;
      uses erienmnrmlrat:struct-PlmnIdentityRO;
    } // end 'list activePlmnList'
    leaf filterUeDlThpVolThr {
      description "Defines PDCP volume threshold for counter pmUeThpDlMbbFilteredDistr. UE session with PDCP volume less than this threshold is filtered out.";
      yexte:takes-effect "Next ROP";
      type erienmnrmlrat:ddt-Lrat_EUtranCellFDD_filterUeDlThpVolThr;
      default 100;
    }
    leaf pdcchTargetBlerVolte {
      description "PDCCH target error rate for UEs with any bearer mapped to a QCI with serviceType of VoIP. In TDD, this parameter applies only to UEs which are configured with HARQ-ACK bundling.";
      yexte:takes-effect "Object unlocked";
      type erienmnrmlrat:ddt-Lrat_EUtranCellFDD_pdcchTargetBlerVolte;
      default 22;
    }
    leaf cellRange {
      description "Defines the maximum distance from the base station where a connection to a UE can be setup and/or maintained.\n";
      yexte:disturbances "Changes may affect traffic.";
      yexte:takes-effect "Object unlocked";
      type erienmnrmlrat:ddt-Lrat_EUtranCellFDD_cellRange;
      default 15;
    }
    container siPeriodicity {
      description "The periodicity of System Information (SI) messages. If a System Information Block (SIB) is not mapped to a SI message, the SI message is not transmitted.";
      erienmyext:enm-type STRUCT;
      uses erienmnrmlrat:struct-PeriodicitySI;
    } // end 'container siPeriodicity'
    list pciConflictCell {
      min-elements 0;
      max-elements 5;
      key auto-generated-struct-key;
      leaf auto-generated-struct-key {
        type uint16;
        description "This leaf has been injected to allow for struct instances in a sequence to be ordered.";
        mandatory true;
      }
      description "Indicates the CGI of the other cell that is involved in the PCI collision/confusion. This value is only valid if the attribute pciConflict is \"YES\" or \"YES_CONFLICTING_CELL\".";
      erienmyext:enm-type STRUCT;
      uses erienmnrmlrat:struct-Cgi;
    } // end 'list pciConflictCell'
    leaf ailgActive {
      config false;
      description "The state of the feature Air Interface Load Generator. Indicates if it is running or stopped.";
      notife:notifiable-state-data true;
      type boolean;
    }
    container mappingInfoCe {
      description "SI message to which each SIB is mapped.\nNote: SIB2 is always mapped to SI message 1 according to 3GPP TS 36.331.";
      erienmyext:enm-type STRUCT;
      uses erienmnrmlrat:struct-MappingInfoSIBsBr;
    } // end 'container mappingInfoCe'
    leaf ulInternalChannelBandwidth {
      description "Internal UL channel bandwidth in the cell with reduced channel bandwidth. Reduced bandwidth for an LTE carrier creates free space for carriers of other radio technologies to use within a standard spectrum 5 MHz or 10 MHz. Other spectrum will generate the undefined value 0. Reduced channel bandwidth is only supported on some radios.";
      yexte:disturbances "Changes may affect traffic";
      yexte:takes-effect "Object disabled/enabled";
      yexte:dependencies "Value must be the same dlInternalChannelBandwidth value.\nulInternalChannelBandwidth values 4200, 4400, 4600 and 4800 are only allowed when ulChannelBandwidth is 5000.\nulInternalChannelBandwidth value 9000 is only allowed when ulChannelBandwidth is 10000.";
      type erienmnrmlrat:ddt-Lrat_EUtranCellFDD_ulInternalChannelBandwidth;
      default 0;
    }
    leaf dlPowerRatio {
      description "Ratio of downlink output power.\nValue less than 100 reduces cell TX power from the initially configured cell TX power. After value is changed, cell TX power changes with rate dlPowerChangeRate.";
      yexte:disturbances "Changing this attribute can cause loss of traffic.";
      yexte:precondition "Setting this attribute is not allowed when dlPowerState is CHANGING.";
      yexte:dependencies "Only relevant if the license for Soft Reduction of Cell Tx Power is present and the feature is active.";
      type erienmnrmlrat:ddt-Lrat_EUtranCellFDD_dlPowerRatio;
      default 100;
    }
    leaf administrativeState {
      description "The administrative state.\n";
      yexte:disturbances "Changing this attribute to LOCKED or SHUTTINGDOWN causes loss of traffic. Changing this attribute can cause all unlocked NBIoT cells to change administrativeState to LOCKED and then UNLOCKED. This happens when one of the following thresholds is crossed: 18 EUTRAN cells + 1 NBIoT cell or 9 NBIoT cells.";
      type erienmnrmlrat:enum-AdmState;
      default LOCKED;
    }
    leaf lbabThreshTimeHigh {
      description "Time period to measure RRC Connection Reject Ratio against threshold lbabThreshRejectRateHigh.";
      yexte:dependencies "Only takes effect when Load-Based Access Barring is activated.";
      type erienmnrmlrat:ddt-Lrat_EUtranCellFDD_lbabThreshTimeHigh;
      default 30;
    }
    leaf dynLoadCtrlMinNewConn {
      description "Minimum number of initial accesses and incoming handovers allowed during Cell Connection Intensity Window.\nIf dynLoadCtrlMinNewConn above what supported by hardware, hardware maximum value will be used.";
      yexte:takes-effect "Next cell unlock";
      yexte:dependencies "Applicable only when serviceState = OPERABLE for Dynamic Load Control.";
      type erienmnrmlrat:ddt-Lrat_EUtranCellFDD_dynLoadCtrlMinNewConn;
      default 1;
    }
    leaf advCellSupAction {
      description "Controls which recovery actions to be performed when ACS detects a sleeping cell.";
      type erienmnrmlrat:enum-AdvCellSupActions;
      default NO_ACTION;
    }
    leaf pdcchAdmEnabled {
      status deprecated {
        yexte:status-information "Since L16A. Has no functional behavior. Planned to be removed.";
      }
      description "Enable the pdcch admission control feature. All rejects will be logged in counter pmCellAdmControlPdcchRej. If set to false we will not reject any Ues due to this function but the potential rejects will be logged in counter pmCellAdmControlPdcchRejMeas.";
      yexte:takes-effect "Cell lock/unlock";
      type boolean;
      default false;
    }
    leaf hoOptAdjThresholdPercQci1 {
      description "Permillage threshold for adjusted handover failure rate required to adjust cellIndividualOffsetEUtranQci1.";
      yexte:disturbances "Changing this attribute can stop outgoing HO.";
      type erienmnrmlrat:ddt-Lrat_EUtranCellFDD_hoOptAdjThresholdPercQci1;
      default 50;
    }
    leaf siWindowLength {
      description "Length of the System Information (SI) window within which each SI message is transmitted. Applies to all SI messages.\nNote:  An SI window of 1 ms may be configured only when a maximum of 5 SI messages is configured for broadcast by attribute mappingInfo, to avoid collision with SIB1 transmission in subframe #5.";
      yexte:takes-effect "When EUtranCellFDD/TDD object is unlocked";
      yexte:dependencies "siWindowLength must be 10 ms or above in case PWS SI messages are broadcasted.";
      type erienmnrmlrat:ddt-Lrat_EUtranCellFDD_siWindowLength;
      default 10;
    }
    leaf siValidityTimeBr {
      description "SI validity timer. The timer is set to 3h or 24h.";
      yexte:takes-effect "Object unlocked";
      type erienmnrmlrat:enum-ValidityTime;
      default VALIDITY_TIME_3H;
    }
    leaf noOfCrsPorts {
      config false;
      description "Number of CRS ports used for a cell that is sending CRS over air interface. -1 means undefined when a cell is not sending CRS over air interface. For example when a cell is locked or disabled.";
      notife:notifiable-state-data true;
      type erienmnrmlrat:ddt-Lrat_EUtranCellFDD_noOfCrsPorts;
    }
    leaf ulSrsEnable {
      description "Controls whether sounding shall be enabled or not for the functionality that supports sounding.";
      yexte:takes-effect "Cell lock/unlock";
      type boolean;
      default false;
    }
    leaf ulDynUeAdmCtrlRetDiffThr {
      description "Highest allowed UL radio resource utilization ratio for admission of a new non-privileged UE. Applies to each UL resource considered by Dynamic UE Admission Control. Resource utilization is checked against this threshold for all new RRC connections.";
      yexte:disturbances "Changing this attribute can affect the following:\n- the number of RRC-connected users\n- cell throughput and the number of rejected non-privileged RRC connection requests.";
      yexte:dependencies "ulDynUeAdmCtrlRetDiffThr =< ulDynUeAdmCtrlOverloadThr";
      type erienmnrmlrat:ddt-Lrat_EUtranCellFDD_ulDynUeAdmCtrlRetDiffThr;
      default 500;
    }
    leaf dynCellSubscrCap {
      erienmyext:no-notification;
      config false;
      description "Parameter that contains the automatically estimated cell capacity value. The value 0 indicates that no estimated value exists.";
      type erienmnrmlrat:ddt-Lrat_EUtranCellFDD_dynCellSubscrCap;
    }
    list additionalPlmnList {
      min-elements 0;
      max-elements 5;
      key auto-generated-struct-key;
      leaf auto-generated-struct-key {
        type uint16;
        description "This leaf has been injected to allow for struct instances in a sequence to be ordered.";
        mandatory true;
      }
      description "Lists additional PLMN IDs supported in the cell.\n\nThe list may include up to 5 PLMNs, and they must be the same in all EUtranCells in the node.";
      erienmyext:enm-type STRUCT;
      uses erienmnrmlrat:struct-PlmnIdentity;
    } // end 'list additionalPlmnList'
    leaf lbUtranOffloadThreshold {
      description "Threshold for eNodeB\nThe value applies for offload towards UTRAN target cells. The eNodeB attempts to offload traffic from the source cell corresponding to the subscription ratio above the threshold.";
      yexte:disturbances "Changing this attribute can cause loss of traffic.";
      type erienmnrmlrat:ddt-Lrat_EUtranCellFDD_lbUtranOffloadThreshold;
      default 100;
    }
    leaf pdschTypeBGain {
      description "Sets the DL power of the PDSCH type B resource elements relatively the PDSCH type A resource elements. Values pdschTypeBGain=(0,1,2,3) define the gains (5/4,1,3/4,1/2) respectively, corresponding to the multi-antenna scenario specified in 3GPP TS 36.213.\nExample: If the pdschTypeBGain is 3 (gain=1/2), the power of the PDSCH type B resource elements is a factor 1/ 2 of the power of the PDSCH type A resource elements.\nPDSDH type A resource elements are located in symbols that do not contain cell specific reference signals (CRS). PDSCH type B resource elements are located in symbols that contain CRS.";
      yexte:takes-effect "Cell lock/unlock";
      yexte:dependencies "The pdschTypeBGain=0 (gain=5/4) is not allowed if crsGain=1.77,3.0, 4.77,6.0 dB. This combination causes over allocation of DL mean radio power and attribute pdschTypeBGain is set to 1 (gain=1).\nThe pdschTypeBGain only takes effect if the configured number of antenna ports is 2,4, or 8.  In the one port case, the power of resource elements for  PDSCH type A and B is equal.";
      type erienmnrmlrat:ddt-Lrat_EUtranCellFDD_pdschTypeBGain;
      default 0;
    }
    leaf deallocTimerPucchFormat1 {
      description "A guard time. After this time, a PUCCH format 1 PRB pair is deallocated if threshold deallocThrPucchFormat1 is still passed.";
      type erienmnrmlrat:ddt-Lrat_EUtranCellFDD_deallocTimerPucchFormat1;
      default 6000;
    }
    leaf ulSCellPriority {
      description "Relative priority in initial SCell selection for cells that can be configured with UL Carrier Aggregation. Applicable where several SCells are initially configured simultaneously. Lowest value has highest priority.";
      yexte:takes-effect "New connection";
      yexte:dependencies "Applicable when 3CC Carrier aggregation Extension Feature (FAJ 121 3084) is enabled and sCellSelectionMode is equal to UN_ACK_SIMULTANEOUS_SCELL_SELECTION or ACK_SIMULTANEOUS_SCELL_SELECTION.";
      type erienmnrmlrat:ddt-Lrat_EUtranCellFDD_ulSCellPriority;
      default 5;
    }
    leaf cellId {
      yexte:restricted;
      description "RBS internal ID attribute for EUtranCell. Must be unique in the RBS. Together with the Node ID and Public Land Mobile Network (PLMN) this is a universally unique cell ID.\nRange 0-255.";
      mandatory true;
      yexte:disturbances "Changing this attribute can cause loss of traffic.";
      type erienmnrmlrat:ddt-Lrat_EUtranCellFDD_cellId;
    }
    leaf enableSinrUplinkClpc {
      description "Specifies if SINR-based UL power control can be used or not. If enabled, SNR-based closed-loop power control and SINR-based closed-loop power control can be adaptively selected.";
      yexte:dependencies "Attribute only has effect if feature Differential Uplink Power Control is activated.";
      type boolean;
      default false;
    }
    leaf srProcessingLevel {
      description "Defines how many SRs eNodeB must receive in a row in order to process it. Used together with srDetectHighThres to reduce false SR detection.";
      yexte:takes-effect "Cell lock/unlock";
      type erienmnrmlrat:enum-SrProcessingLevel;
      default NO_ADDITIONAL_SR_NEEDED;
    }
    leaf tm9Tm4ModeSwitchingEnabled {
      description "Enables dynamic switching between TM9 and TM4.";
      yexte:takes-effect "Next cell unlock";
      yexte:dependencies "Only takes effect if radio equipment supports AAS functionality.";
      type boolean;
      default false;
    }
    leaf acBarringInfoPresent {
      description "Specifies presence of the following IEs:\n- ac-BarringInfo\n- ssac-BarringForMMTEL-Voice-r9\n- ssac-BarringForMMTEL-Video-r9\n- ac-BarringForCSFB-r10\n- ac-BarringSkipForMMTELVoice-r12\n- ac-BarringSkipForMMTELVideo-r12\n- ac-BarringSkipForSMS-r12 in SIB2";
      yexte:disturbances "Changing this attribute can cause loss of traffic.";
      type boolean;
      default false;
    }
    leaf lbabThreshRejectRateHigh {
      description "RRC Connection Reject Ratio threshold above which Load-Based Access Barring increases access class barring probability or Progressive Access Barring, or PLMN-Specific Access Barring proceeds to higher priority.";
      yexte:dependencies "Only takes effect when Load-Based Access Barring is activated.";
      type erienmnrmlrat:ddt-Lrat_EUtranCellFDD_lbabThreshRejectRateHigh;
      default 200;
    }
    leaf hpueCaSwitchHyst {
      description "Hysteresis of SINR threshold for triggering a switch to high power UE.";
      type erienmnrmlrat:ddt-Lrat_EUtranCellFDD_hpueCaSwitchHyst;
      default 20;
    }
    leaf interferenceThresholdSinrClpc {
      description "Threshold value for measured noise plus interference level. If measured noise plus interference is higher than interferenceThresholdSinrClpc, then SINR-based UL closed-loop power control can be considered.";
      yexte:dependencies "Threshold only has effect if attribute enableSinrUplinkClpc is true.";
      type erienmnrmlrat:ddt-Lrat_EUtranCellFDD_interferenceThresholdSinrClpc;
      default -105;
    }
    leaf beamWeightSet16Tr {
      description "Specifies the index representing the beam weight vector to be applied for beam forming using the 16TR feature. If the value is equal to 0, the feature is not active.";
      yexte:disturbances "Changing this attribute can affect traffic. A cell lock/unlock is required.";
      yexte:takes-effect "Next cell unlock";
      type erienmnrmlrat:ddt-Lrat_EUtranCellFDD_beamWeightSet16Tr;
      default 0;
    }
    leaf primaryPlmnAlarmSuppr {
      description "Indicates if the primary PLMN ID in the cell is suppressed for alarms PLMN Service Degraded and PLMN Service Unavailable when primary PLMN is not available in the cell.\nThe primary PLMN ID is suppressed if this attribute is set to true.\nIf the configured PLMN ID is not a served PLMN ID, then the alarm is suppressed independent of the configured settings.";
      type boolean;
      default false;
    }
    leaf rwrSearchZoneAllowed {
      description "Allows for release-with-redirect in search zone when EUtranFreqRelation::mobilityAction attribute is configured as HANDOVER.";
      yexte:takes-effect "New connection";
      yexte:dependencies "Mobility control at poor coverage must be active.";
      type boolean;
      default true;
    }
    leaf liteMcsReduction {
      description "LiteMcsReduction feature mode.";
      type erienmnrmlrat:enum-LiteMcsReductionMode;
      default ON;
    }
    leaf qQualMin {
      description "Specifies the minimum required quality level (RSRQ) in the cell in dB.\nCorresponds to Qqualmin in TS 36.304, sent in SIB1. Value 0 means that it is not sent and UE applies in such case the (default) value of negative infinity for Qqualmin.";
      yexte:dependencies "The field is mandatory present if the Struct Member threshServingLowQ in SIB3 is used in systemInformationBlockType3.";
      type erienmnrmlrat:ddt-Lrat_EUtranCellFDD_qQualMin;
      default 0;
    }
    leaf gpsTimeSFN0Seconds {
      config false;
      description "The integer part of the GPS time for the most recent occurrence of SFN=0 in the cell.";
      notife:notifiable-state-data true;
      type erienmnrmlrat:ddt-Lrat_EUtranCellFDD_gpsTimeSFN0Seconds;
    }
    leaf userLabel {
      description "Label for free use.\n";
      type erienmnrmlrat:ddt-Lrat_EUtranCellFDD_userLabel;
    }
    leaf expectedMaxNoOfUsersInCell {
      description "The expected max number of UE in RRC_CONNECTED mode in the cell. Will be used at unlock of the cell to distribute cells to different cores in Digital Units and Baseband Units with a multicore Main Processor. A value of -1 indicates that measuredMaxNoOfUsersInCell will be used to control the cell distribution.";
      yexte:takes-effect "Object unlocked";
      type erienmnrmlrat:ddt-Lrat_EUtranCellFDD_expectedMaxNoOfUsersInCell;
      default -1;
    }
    leaf primaryPlmnReserved {
      description "Indicates if the primary PLMN ID in the cell is reserved for operator use. The primary PLMN ID is reserved if this attribute is set to true.";
      yexte:disturbances "Changing this attribute can block traffic in the cell.";
      yexte:dependencies "the attribute eNodeBPlmnId in the parent ENodeBFunction will hold the value of the primary PLMN ID.";
      type boolean;
      default false;
    }
    leaf dlConfigurableFrequencyStart {
      description "Specifies the start frequency offset for the allocation of resources when the downlink interference management is disabled expressed as a percentage of the configured bandwidth.";
      yexte:takes-effect "Object unlocked";
      yexte:dependencies "dlInterferenceManagementActive shall be disabled before this parameter takes effect.";
      type erienmnrmlrat:ddt-Lrat_EUtranCellFDD_dlConfigurableFrequencyStart;
      default 0;
    }
    leaf pucchOverdimensioning {
      description "Number of resource blocks outside each Physical Uplink Control Channel (PUCCH) region that are available for scheduling Physical Uplink Shared Channel (PUSCH).\nNote: Both the value of this attribute and the amount of resources allocated for PUCCH impacts where the resource allocation of the PRACH starts.";
      yexte:takes-effect "Object disabled/enabled.";
      type erienmnrmlrat:ddt-Lrat_EUtranCellFDD_pucchOverdimensioning;
      default 0;
    }
    leaf cioLowerLimitAdjBySon {
      description "Indicates the lower limit value of cellIndividualOffsetEUtran range that the SON function is allowed to adjust.";
      yexte:disturbances "Changing this attribute can stop outgoing HO.";
      type erienmnrmlrat:ddt-Lrat_EUtranCellFDD_cioLowerLimitAdjBySon;
      default -3;
    }
    leaf puschPwrOffset64qam {
      description "Power offset to the target-received PUSCH Power Spectral Density (PSD) for 64-QAM-capable UEs. Used to control the received SINR target.\nIt is used to enable maximum throughput for 64QAM, which in some configurations is not possible otherwise, see dependencies.";
      yexte:disturbances "Changes can affect traffic.";
      yexte:dependencies "Only relevant if the license for 64-QAM Uplink is present and the\nfeature is active.\nFor 2Rx, pZeroNominalPusch + puschPwrOffset64qam needs to be -100 dBm or higher to achieve maximum throughput.\npuschPwrOffset64Qam should be set to 0 when both UL 64QAM and UL MU-MIMO are enabled in eNB.";
      type erienmnrmlrat:ddt-Lrat_EUtranCellFDD_puschPwrOffset64qam;
      default 0;
    }
    leaf noOfPucchCqiUsers {
      description "The number of Channel Quality Indicator (CQI) resources available on the PUCCH channel.\nFor 1.4 MHz system bandwidth the recommended value is 50.\n\n";
      yexte:disturbances "Cell runs new set-up procedure. All cell-connected UEs are released and connected again.";
      type erienmnrmlrat:ddt-Lrat_EUtranCellFDD_noOfPucchCqiUsers;
      default 160;
    }
    leaf hoOptStatTime {
      description "The operational cycle of the handover optimization function.";
      type erienmnrmlrat:ddt-Lrat_EUtranCellFDD_hoOptStatTime;
      default 24;
    }
    leaf drxActive {
      description "Indicates if the DRX function in the cell is activated.";
      yexte:takes-effect "New connection";
      type boolean;
      default false;
    }
    leaf pdcchOuterLoopInitialAdjPCell {
      description "The initial value for primary cell PDCCH outer loop adjustment in case of carrier aggregation. This applies to UEs that have at least one secondary cell configured and do not have any bearer mapped to a QCI with serviceType of VoIP. In TDD, this parameter is not used.";
      yexte:takes-effect "Object unlocked";
      type erienmnrmlrat:ddt-Lrat_EUtranCellFDD_pdcchOuterLoopInitialAdjPCell;
      default -70;
    }
    leaf cfraEnable {
      description "This parameter controls if Contention Free Random Access (CFRA, known as non-contention based random access in 3GPP term) shall be enabled or not. When enabled, a portion of random access preambles should be allocated for CFRA and CFRA can be used for incoming HO and PDCCH ordered uplink re-sync.";
      yexte:takes-effect "Cell lock/unlock";
      type boolean;
      default false;
    }
    leaf lbEUtranCellOffloadCapacity {
      description "This attribute indicates the offload subscription capacity associated with the EUTRAN target cell. The value is used to moderate the offload rate to the EUTRAN target cell.";
      yexte:disturbances "Changing this attribute can cause loss of traffic.";
      type erienmnrmlrat:ddt-Lrat_EUtranCellFDD_lbEUtranCellOffloadCapacity;
      default 1000;
    }
    leaf dynUeAdmCtrlFilterConst {
      description "Time constant of the exponential-weighted moving average filter applied to the radio resource utilization ratios considered by Dynamic UE Admission Control.";
      yexte:disturbances "Changing this attribute can affect the following:\n- the number of RRC-connected users\n- cell throughput and the number of rejected non-privileged RRC connection requests\n- rejected non-privileged RRC connection re-establishment requests and rejected\n  non-privileged incoming handover requests.";
      type erienmnrmlrat:ddt-Lrat_EUtranCellFDD_dynUeAdmCtrlFilterConst;
      default 3000;
    }
    leaf enableServiceSpecificHARQ {
      description "Enable/disable service-specific HARQ on cell level. Function must have valid license.";
      yexte:takes-effect "New connection";
      type boolean;
      default false;
    }
    leaf acBarringSkipForMmtelVideo {
      description "Indicates whether or not access attempts for MMTEL video from UEs are to skip Access Class Barring functionality.";
      yexte:disturbances "Changing this attribute can block Video calls.";
      type boolean;
      default false;
    }
    leaf alpha {
      description "The pathloss compensation factor for power control of the Physical Uplink Shared Channel (PUSCH).";
      yexte:disturbances "Changing this attribute can affect traffic.";
      type erienmnrmlrat:ddt-Lrat_EUtranCellFDD_alpha;
      default 10;
    }
    leaf srDetectHighThres {
      description "Defines how many dB higher than the original SR detection threshold can be used as high SR detection threshold. Used together with srProcessingLevel to reduce false SR detection.";
      yexte:takes-effect "Cell lock/unlock";
      type erienmnrmlrat:ddt-Lrat_EUtranCellFDD_srDetectHighThres;
      default 70;
    }
    leaf interEnbUlCompUserSelSinrHys {
      description "Hysteresis of SINR threshold for inter-eNodeB UL CoMP user selection.";
      yexte:disturbances "If changed, system performance can be affected. As values get bigger, gaps for triggering Inter-eNodeB Uplink CoMP user switching get bigger.";
      yexte:dependencies "Must be used together with interEnbUlCompUserSelSinrThr.";
      type erienmnrmlrat:ddt-Lrat_EUtranCellFDD_interEnbUlCompUserSelSinrHys;
      default 10;
    }
    leaf catmMbmsDlSubframes {
      description "Controls which DL subframes are unavailable for Cat-M DL due to MBMS operation.\nFewer unavailable subframes optimize Cat-M1 DL max throughput, but change of unavailable subframes can cause Cat-M1 connection drops and temporary difficulties to page certain UEs. Avoided by less dynamic setting (lower value).\n0: Unavailable subframes due to MBMS set according to MbsfnArea::commonSFAllocList and MbsfnArea::mbsfnAreaCellRelation.\n1: Unavailable subframes due to MBMS set according to MbsfnArea::commonSFAllocList and MbsfnArea::mbsfnAreaCellRelation if any MBSFN service is active in the cell, otherwise no unavailable subframes due to MBMS.\n2: Unavailable subframes due to MBMS set according to subframes blocked by active MBSFN services.";
      yexte:takes-effect "Next cell unlock";
      type erienmnrmlrat:ddt-Lrat_EUtranCellFDD_catmMbmsDlSubframes;
      default 0;
    }
    leaf dlPowerChangeRate {
      description "Change rate for downlink output power to reach dlPowerRatio.";
      type erienmnrmlrat:ddt-Lrat_EUtranCellFDD_dlPowerChangeRate;
      default 1;
    }
    leaf-list availabilityStatus {
      min-elements 0;
      config false;
      description "The availability status. It contains details about operationalState. This attribute is set by the application in the RBS.\n";
      notife:notifiable-state-data true;
      type erienmnrmlrat:enum-AvailStatus;
    }
    leaf gpsTimeSFN0DecimalSecond {
      config false;
      description "The decimal part of the GPS time for the most recent occurrence of System Frame Number (SFN)=0 in the cell.\nUnit: 2^(-32) second";
      notife:notifiable-state-data true;
      type erienmnrmlrat:ddt-Lrat_EUtranCellFDD_gpsTimeSFN0DecimalSecond;
    }
    leaf-list validDlBrSubframes {
      min-elements 0;
      max-elements 4;
      config false;
      description "Shows valid subframes for DL BR transmissions, indicated by broadcasted SIB1-BR.\n1: Corresponding subframe is valid DL BR subframe.\n0: Corresponding subframe not valid DL BR subframe.\nFirst element in the list corresponds to radio frames satisfying SFN mod 4 = 0, the next to radio frames satisfying SFN mod 4 = 1 and so on.\nEach least significant bit represents subframe #0 of the corresponding SFN.\nIf SIB1-BR not broadcasted (Cat-M not supported in cell), list is empty.";
      notife:notifiable-state-data true;
      type erienmnrmlrat:ddt-Lrat_EUtranCellFDD_validDlBrSubframes;
    }
    leaf hoOptStatNum {
      description "The minimal number of handovers required by the handover optimization function before adjusting  handover parameters.";
      type erienmnrmlrat:ddt-Lrat_EUtranCellFDD_hoOptStatNum;
      default 200;
    }
    leaf spifhoSetupBearerAtInitialCtxtSetup {
      description "Decides if a bearer handled by the feature Service or Priority Triggered Inter-Frequency Handover (SPIFHO) is set up at Initial Context Setup even when attribute servOrPrioIFHoSetupBearer is false.";
      yexte:takes-effect "New connection";
      yexte:dependencies "The value of this attribute is only considered when the value of servOrPrioIFHoSetupBearer=false.";
      type boolean;
      default false;
    }
    leaf tReorderingAutoConfiguration {
      description "Enable automatic configuration of tReorderingDl and tReorderingUl. Configuration is based on HARQ-interval together with an offset defined by harqOffsetDl/harqOffsetUl.tReordering >= 'Max number of HARQ' * HARQ-interval + harqOffset, where closest higher or equal allowed value is used.\nThis configuration is only applied to UM bearers. AM bearers will still use tReorderingUl and tReorderingDl from QciProfilePredefined or QciProfileOperatorDefined.";
      yexte:takes-effect "New connection";
      type boolean;
      default false;
    }
    leaf bcCdma2000SysTimeType {
      config false;
      description "The actual type of CDMA2000 system time that is broadcast in SIB8.";
      notife:notifiable-state-data true;
      type erienmnrmlrat:enum-Cdma2000SysTimeVals;
    }
    leaf ns05FullBandSchedEnabled {
      description "Enables PUSCH 100 PRBs scheduling.";
      yexte:dependencies "Only takes effect if:\n- license for NS 05 Additional Maximum Power Reduction Support is present and the feature is active, and\n- attribute networkSignallingValue in MOC EUtranCellFDD/TDD is NS_05.";
      type boolean;
      default false;
    }
    leaf pdcchOuterLoopUpStepPCell {
      description "PDCCH outer loop up step size for primary cells in case of carrier aggregation. This applies to UEs that have at least one secondary cell configured and do not have any bearer mapped to a QCI with serviceType of VoIP. In TDD, this parameter is not used.";
      yexte:takes-effect "Object unlocked";
      type erienmnrmlrat:ddt-Lrat_EUtranCellFDD_pdcchOuterLoopUpStepPCell;
      default 6;
    }
    leaf primaryPsdOffset {
      description "Offset value that controls the maximum allowed difference between pZeroNominalPusch and the received power below pZeroNominalPusch in the primary sector when UL CoMP is used.";
      type erienmnrmlrat:ddt-Lrat_EUtranCellFDD_primaryPsdOffset;
      default 0;
    }
    leaf noOfPucchFormat3PrbPairsPerFrame {
      erienmyext:no-notification;
      config false;
      description "PRB usage for PUCCH Format3. Based on 3CC Carrier Aggregation user configuration.";
      type erienmnrmlrat:ddt-Lrat_EUtranCellFDD_noOfPucchFormat3PrbPairsPerFrame;
    }
    leaf ulImprovedUeAdapRetransEnabled {
      status deprecated {
        yexte:status-information "Since 17.Q3. Has no functional behavior. Planned to be removed.";
      }
      description "Whether or not UL-scheduler is enabled that uses adaptive re-transmission more frequently for data-aware UL-scheduling UEs, to reduce fragments in UL spectrum.";
      type boolean;
      default true;
    }
    leaf prsPowerBoosting {
      description "Used for selecting the different power boosting alternatives for PRS transmissions. If set to 0, a default table based on the number of PBCH antennas and transmission scheme is shown. If set to 1, 2, or 3, it results in a power boosting of 0 dB, 3 dB, or 6 dB respectively.";
      yexte:takes-effect "Object unlocked";
      type erienmnrmlrat:ddt-Lrat_EUtranCellFDD_prsPowerBoosting;
      default 0;
    }
    leaf ulPsdLoadThresholdSinrClpc {
      description "Threshold of UL transmission power per PRB. If averaged UL transmission power measurement per PRB is lower than ulPsdLoadThresholdSinrClpc over a set percentage of UL bandwidth, then SINR-based UL closed-loop power control can be considered.";
      yexte:dependencies "Threshold only has effect if attribute enableSinrUplinkClpc is true.";
      type erienmnrmlrat:ddt-Lrat_EUtranCellFDD_ulPsdLoadThresholdSinrClpc;
      default 2;
    }
    leaf prsMutingPatternLen {
      description "Used for selecting the length of the PRS muting pattern. Setting the pattern length to 1 results in deactivation of PRS muting. The muting pattern is set to \"1111111111111\" in this case. Other recommended muting pattern lengths are: 2, 4, 8, and 16 bits.";
      yexte:takes-effect "Object unlocked";
      type erienmnrmlrat:ddt-Lrat_EUtranCellFDD_prsMutingPatternLen;
      default 1;
    }
    leaf noOfEnhAdptReTxCand {
      description "Threshold used in restrict SE number that enhanced adaptive Retransmission candidates, if there are too many non-adaptive retransmission candidates, only \"noOfEnhAdptReTxCand\" numbers SE can be the enhanced adaptive retransmission queue.\nMaximum number of SEs added to the enhanced adaptive retransmission queue as candidates.\nIf set to -1, number of candidates is automatically decided by eNodeB.\nIf set to 0, no UEs added to queue and thus feature has no effect.";
      type erienmnrmlrat:ddt-Lrat_EUtranCellFDD_noOfEnhAdptReTxCand;
      default 0;
    }
    leaf enableUeAssistedAdaptiveDrx {
      description "Enable or disable the UE-Assisted Adaptive DRX feature.";
      yexte:takes-effect "Object unlocked";
      type boolean;
      default true;
    }
    leaf isDlOnly {
      description "Indicates if the cell is operated with downlink only and with no uplink.";
      yexte:disturbances "Changes may affect traffic.";
      yexte:takes-effect "Object unlocked";
      yexte:dependencies "Must be false if catm1SupportEnabled is true.";
      type boolean;
      default false;
    }
    leaf tTimeAlignmentTimer {
      description "A timer used for supervision and control of uplink synchronization. Special value: 0 means infinity.";
      yexte:takes-effect "Cell lock/unlock";
      type erienmnrmlrat:ddt-Lrat_EUtranCellFDD_tTimeAlignmentTimer;
      default 0;
    }
    leaf dlInterferenceManagementActive {
      description "Specifies if the downlink interference management is enabled or disabled.";
      yexte:takes-effect "Object unlocked";
      type boolean;
      default false;
    }
    leaf prsTransmisScheme {
      description "Used for selecting whether the PRS transmission must use antenna switching or pre-coder switching.";
      yexte:takes-effect "Object unlocked";
      type erienmnrmlrat:enum-TransmissionScheme;
      default ANTENNA_SWITCHING;
    }
    container ssacBarringForMMTELVideo {
      description "Service specific access class barring parameters for MMTEL video originating calls.\nInformation broadcasted in SIB2.";
      erienmyext:enm-type STRUCT;
      uses erienmnrmlrat:struct-AcBarringConfig;
    } // end 'container ssacBarringForMMTELVideo'
    leaf acBarringForEmergency {
      description "Access class barring for  Emergency, which corresponds to access class 10.";
      yexte:disturbances "Changing this attribute can block emergency calls.";
      yexte:dependencies "ac-BarringForEmergency value in SIB2 can be automatically overridden by Progressive Barring of Special Access Classes algorithm regardless of value in this attribute when its corresponding AcBarringModeEm is set to AUTO.";
      type boolean;
      default false;
    }
    leaf lbabMinBarringFactor {
      description "Minimum barring factor for Load-Based Access Barring algorithm or priority level 0 for one of the following algorithms:\n- Progressive Access Barring\n- Progressive Barring of Special Access Classes\n- PLMN-Specific Access Barring";
      yexte:dependencies "Only takes effect when feature Load-Based Access Barring or feature Progressive Access Barring is activated.";
      type erienmnrmlrat:ddt-Lrat_EUtranCellFDD_lbabMinBarringFactor;
      default 0;
    }
    leaf-list prioAdditionalFreqBandList {
      min-elements 0;
      max-elements 8;
      description "List of additional frequency bands the cell belongs to. Primary frequency band, EARFCN value of the cell, is not included. Secondary cell evaluation is done according to list order, and/or the list is broadcasted in SIB1. Highest priority band is position 0 in the list.";
      yexte:precondition "ENodeBFunction::useBandPrioritiesInSCellEval and/or ENodeBFunction::useBandPrioritiesInSib1 must be enabled.";
      yexte:dependencies "List only contains frequency bands from additionalFreqBandList.";
      type erienmnrmlrat:ddt-Lrat_EUtranCellFDD_prioAdditionalFreqBandList;
    }
    leaf-list emergencyAreaId {
      min-elements 0;
      max-elements 15;
      description "A cell that supports  broadcast of warning messages can belong to one to 15 Emergency Areas, identified by an Emergency Area Id, set by the operator.  Value -1 means identity not set.";
      type erienmnrmlrat:ddt-Lrat_EUtranCellFDD_emergencyAreaId;
      default -1;
      default -1;
      default -1;
      default -1;
      default -1;
      default -1;
      default -1;
      default -1;
      default -1;
      default -1;
      default -1;
      default -1;
      default -1;
      default -1;
      default -1;
    }
    leaf ttiBundlingSwitchThresHyst {
      description "Hysteresis of SINR threshold for triggering a switch to TTI bundling.";
      yexte:takes-effect "Cell lock/unlock";
      type erienmnrmlrat:ddt-Lrat_EUtranCellFDD_ttiBundlingSwitchThresHyst;
      default 10;
    }
    leaf dlDynUeAdmCtrlOverloadThr {
      description "Highest allowed DL radio resource utilization ratio for admission of a non-privileged UE. Applies to each DL resource considered by Dynamic UE Admission Control. Resource utilization is checked against this threshold for all new, re-established, or incoming handover RRC connections.";
      yexte:disturbances "Changing this attribute can affect the following:\n- the number of RRC-connected users\n- cell throughput and the number of rejected non-privileged RRC connection requests\n- rejected non-privileged RRC connection re-establishment requests and rejected\n  non-privileged incoming handover requests.";
      yexte:dependencies "dlDynUeAdmCtrlOverloadThr >= dlDynUeAdmCtrlRetDiffThr";
      type erienmnrmlrat:ddt-Lrat_EUtranCellFDD_dlDynUeAdmCtrlOverloadThr;
      default 600;
    }
    leaf rxSinrTargetClpc {
      description "SINR target value for SINR-based UL closed-loop power control.";
      yexte:disturbances "Changing this attribute can cause loss of traffic.";
      yexte:dependencies "SINR target only has effect if attribute enableSinrUplinkClpc is true.";
      type erienmnrmlrat:ddt-Lrat_EUtranCellFDD_rxSinrTargetClpc;
      default 25;
    }
    leaf nrOfPreallocatedSrRes {
      config false;
      description "Number of successfully preallocated Scheduling Request resources at cell setup.\nUndefined value: -1";
      yexte:dependencies "Relation to AdmissionControl::nrOfPaConnReservationsPerCell.\nSuccessful preallocation: nrOfPreallocatedSrRes = nrOfPaConnReservationsPerCell\nPartially successful preallocation: nrOfPreallocatedSrRes < nrOfPaConnReservationsPerCell\nFailed preallocation: nrOfPreallocatedSrRes = 0\nNo preallocation attempt (default): nrOfPreallocatedSrRes = -1";
      notife:notifiable-state-data true;
      type erienmnrmlrat:ddt-Lrat_EUtranCellFDD_nrOfPreallocatedSrRes;
    }
    leaf threshServingLow {
      description "Specifies the threshold that the signal strength of the serving cell must be below for cell reselection towards a lower priority Inter-Frequency or Inter-RAT frequency.\nCorresponds to ThreshServingLowP in TS 36.304.";
      type erienmnrmlrat:ddt-Lrat_EUtranCellFDD_threshServingLow;
      default 0;
    }
    leaf dynUlResourceAllocEnabled {
      description "Enables Dynamic uplink resource allocation on cell level.";
      yexte:takes-effect "Cell lock/unlock";
      yexte:dependencies "Only relevant if license UlDynamicResourceAllocation is present and feature is active.";
      type boolean;
      default false;
    }
    container mappingInfo {
      description "The System Information (SI) message to which each System Information Block (SIB) is mapped.\n\nNote: SIB2 is always mapped to the SI message 1 according to 3GPP TS 36.331.";
      erienmyext:enm-type STRUCT;
      uses erienmnrmlrat:struct-MappingInfoSIBs;
    } // end 'container mappingInfo'
    leaf-list pciConflict {
      min-elements 0;
      max-elements 5;
      description "A PCI confusion exists if a source cell has relations to two neighbor cells where both neighbor cells have the same PCI and frequency. A PCI collision exists if a source cell has a relation to a neighbor cell where both the source cell and neighbor cell have the same PCI and frequency.";
      type erienmnrmlrat:enum-PciConflict;
    }
    leaf networkSignallingValueCa {
      description "Enables additional spectrum emission requirements for CA according to 3GPP TS 36.101, table 6.2.4A-1.";
      yexte:takes-effect "Object disabled/enabled";
      type erienmnrmlrat:enum-NetworkSignallingValueCa;
      default CA_NS_31;
    }
    leaf ns05FullBandUsersInCellThres {
      description "Value of threshold to enable the PUSCH 100 PRBs scheduling. PUSCH 100 PRBs scheduling is triggered when the number of UE in RRC_CONNECTED mode in the cell is less than or equal to ns05FullBandUsersInCellThres.";
      yexte:dependencies "Only takes effect if:\n- license for NS 05 Additional Maximum Power Reduction Support is present and the feature is active, and\n- attribute networkSignallingValue in MOC EUtranCellFDD/TDD is NS_05, and\n- attribute ns05FullBandSchedEnabled in MOC EUtranCellFDD/TDD is true.";
      type erienmnrmlrat:ddt-Lrat_EUtranCellFDD_ns05FullBandUsersInCellThres;
      default 10;
    }
    leaf ttiBundlingAfterReest {
      description "Controls if UE remains in TTI bundling mode after reestablishment.";
      type erienmnrmlrat:enum-TtiBundlingModeAfterReestablishment;
      default TTI_BUNDLING_SOURCE_REEST_ONLY;
    }
    leaf caPrioThreshold {
      description "The threshold number of SCells configured using prioritized SCell selection. When the number of SCells configured for UEs connected in this PCell is higher than caPrioThreshold, all frequency carriers configured for carrier aggregation are assumed to have equal priority regardless of the configured values.";
      yexte:takes-effect "Next cell unlock";
      yexte:dependencies "Only applicable when CarrierAggregationFunction::dynamicSCellSelectionMethod == PRIORITIZED.";
      type erienmnrmlrat:ddt-Lrat_EUtranCellFDD_caPrioThreshold;
      default 300;
    }
    leaf noOfUlImprovedUe {
      description "Number of data-aware UL-scheduling UEs that can be improved at allocation of PDCCH and PUSCH.";
      type erienmnrmlrat:ddt-Lrat_EUtranCellFDD_noOfUlImprovedUe;
      default 1;
    }
    leaf lbabMinBarringFactorPrio3 {
      description "Priority level 3 minimum barring factor for one of the following algorithms:\n- Progressive Access Barring\n- Progressive Barring of Special Access Classes\n- PLMN-Specific Access Barring";
      yexte:dependencies "Only takes effect when Progressive Access Barring is activated.";
      type erienmnrmlrat:ddt-Lrat_EUtranCellFDD_lbabMinBarringFactorPrio3;
      default 0;
    }
    leaf lbabMinBarringFactorPrio4 {
      description "Priority level 4 minimum barring factor for one of the following algorithms:\n- Progressive Access Barring\n- Progressive Barring of Special Access Classes\n- PLMN-Specific Access Barring";
      yexte:dependencies "Only takes effect when Progressive Access Barring is activated.";
      type erienmnrmlrat:ddt-Lrat_EUtranCellFDD_lbabMinBarringFactorPrio4;
      default 0;
    }
    leaf cellDownlinkCaCapacity {
      description "Normalized downlink cell capacity available for use by carrier aggregation. The value is used to calculate the aggregated capacity of a UE:s possible aggregation possibilities, for example by the CA Aware IFLB feature.";
      type erienmnrmlrat:ddt-Lrat_EUtranCellFDD_cellDownlinkCaCapacity;
      default 0;
    }
    leaf harqOffsetDl {
      description "Offset used when tReorderingDl is calculated by automatic configuration. tReorderingDl = 'Max number of HARQ for DL' * HARQ-interval + harqOffsetDl.";
      yexte:takes-effect "New connection";
      type erienmnrmlrat:ddt-Lrat_EUtranCellFDD_harqOffsetDl;
      default 3;
    }
    leaf advCellSupSensitivity {
      description "Indicates the sensitivity of the Advanced Cell Supervision function. A higher value will make ACS detect a sleeping cell faster, but with higher risk for false detection. A lower value will make ACS detect a sleeping cell slower, but with lower risk for false detection.";
      yexte:disturbances "Changing this attribute can cause loss of traffic.";
      type erienmnrmlrat:ddt-Lrat_EUtranCellFDD_advCellSupSensitivity;
      default 0;
    }
    leaf initialBufferSizeDefault {
      description "The number of bytes that is assumed to be in the UE buffer when an SR is received through PUCCH.";
      yexte:takes-effect "Cell lock/unlock";
      type erienmnrmlrat:ddt-Lrat_EUtranCellFDD_initialBufferSizeDefault;
      default 86;
    }
    leaf lbabMinBarringFactorPrio1 {
      description "Priority level 1 minimum barring factor for one of the following algorithms:\n- Progressive Access Barring\n- Progressive Barring of Special Access Classes\n- PLMN-Specific Access Barring";
      yexte:dependencies "Only takes effect when feature Progressive Access Barring is activated.";
      type erienmnrmlrat:ddt-Lrat_EUtranCellFDD_lbabMinBarringFactorPrio1;
      default 0;
    }
    leaf puschNcpChannelEstWindowSize {
      description "Normal or Large Window Size for PUSCH filter channel estimation for normal CP.";
      yexte:takes-effect "Next cell unlock";
      type erienmnrmlrat:enum-PuschChannelEstWindowSize;
      default NORMAL_SIZE;
    }
    leaf noOfPucchFormat3PrbPairs {
      description "Number of PUCCH Format 3 PRB pairs.";
      yexte:takes-effect "Cell lock/unlock";
      yexte:dependencies "Only takes effect when 3CC Carrier aggregation Extension Feature (FAJ 121 3084) is enabled.";
      type erienmnrmlrat:ddt-Lrat_EUtranCellFDD_noOfPucchFormat3PrbPairs;
      default 1;
    }
    leaf lbabMinBarringFactorPrio2 {
      description "Priority level 2 minimum barring factor for one of the following algorithms:\n- Progressive Access Barring\n- Progressive Barring of Special Access Classes\n- PLMN-Specific Access Barring";
      yexte:dependencies "Only takes effect when feature Progressive Access Barring is activated.";
      type erienmnrmlrat:ddt-Lrat_EUtranCellFDD_lbabMinBarringFactorPrio2;
      default 0;
    }
    leaf allocThrPucchFormat1 {
      description "Threshold in terms of number of remaining SR resources available for the cell. Below this threshold, allocTimerPucchFormat1 for allocation of an additional PUCCH format 1 PRB pair is triggered. Occurs if  feature Dynamic PUCCH  is activated. Value 0 means the dynamic PUCCH allocation/deallocation operation for this cell is disabled.";
      yexte:dependencies "If Scheduling Request resources limitation pool for privileged access connections is activated in eNodeB, threshold for allocation of an additional PUCCH format 1 PRB pair by dynamic PUCCH must be higher than number of resources in limitation pool.\n(allocThrPucchFormat1 > AdmissionControl::limitSrNonPa)";
      type erienmnrmlrat:ddt-Lrat_EUtranCellFDD_allocThrPucchFormat1;
      default 50;
    }
    leaf primaryUpperLayerInd {
      description "Whether upperLayerIndication is set for PLMN identified by ENodeBFunction::eNodeBPlmnId.\nThe upperLayerIndication is broadcast in SIB2.";
      yexte:dependencies "Valid for Baseband Radio Node only.";
      type erienmnrmlrat:enum-LayerState;
      default OFF;
    }
    leaf puschFrequencyAllocationBr {
      description "Controls allocation of PUSCH for BR UEs to upper or lower part of band.\nControls PUSCH from BR UEs, except msg3.\nFor example, it can be used for the following:\n- To avoid interfered part of band.\n- To be used in combination with Flexible Channel Bandwidth.\n0: Allocate PUSCH from BR UEs, except msg3, to lower part of band.\n1: Allocate PUSCH from BR UEs, except msg3, to upper part of band.";
      yexte:takes-effect "Next cell unlock";
      type erienmnrmlrat:ddt-Lrat_EUtranCellFDD_puschFrequencyAllocationBr;
      default 0;
    }
    container acBarringForMoSignalling {
      description "Access class barring parameters for mobile originating signaling.\nInformation broadcasted in SIB2.";
      erienmyext:enm-type STRUCT;
      uses erienmnrmlrat:struct-AcBarringConfig;
    } // end 'container acBarringForMoSignalling'
    leaf cellCapMinMaxWriProt {
      description "Write protection that prevents feature Automated Cell Capacity Estimation from changing the value on parameters cellCapMinCellSubCap and cellCapMaxCellSubCap.\nIf set to true, feature Automated Cell Capacity Estimation cannot reset cellCapMinCellSubCap and cellCapMaxCellSubCap at cell unlock.\nIf set to false, feature Automated Cell Capacity Estimation can change cellCapMinCellSubCap and cellCapMaxCellSubCap at cell unlock.";
      type boolean;
      default false;
    }
    leaf msg3FrequencyAllocationBr {
      description "Controls allocation of msg3 for BR UEs to upper or lower part of band.\nControls msg3 from BR UEs.\nFor example, it can be used for the following:\n- To avoid interfered part of band.\n- To be used in combination with Flexible Channel Bandwidth.\n0: Allocate msg3 from BR UEs to lower part of band.\n1: Allocate msg3 from BR UEs to upper part of band.";
      yexte:takes-effect "Next cell unlock";
      type erienmnrmlrat:ddt-Lrat_EUtranCellFDD_msg3FrequencyAllocationBr;
      default 1;
    }
    leaf lbTpRankThreshMin {
      description "The minimum threshold for the relative gain at throughput aware load balancing. A negative value may allow for some throughput loss for the individual UE, if the load balancing criteria requires so. Higher values may increase the fraction of non-qualified UEs at UE selection for throughput aware load balancing and may cause the load balancing to stall.\nSpecial value -100 means the lower boundary for the threshold is disabled.";
      yexte:disturbances "Changing this attribute can cause loss of traffic.";
      type erienmnrmlrat:ddt-Lrat_EUtranCellFDD_lbTpRankThreshMin;
      default -20;
    }
    leaf physicalLayerSubCellId {
      description "Subidentity within the physical layer cell ID group.\nPhysical layer cell IDs are grouped into 168 unique physical layer cell ID groups. Each group contains 3 unique subidentities.\nUsed with physicalLayerCellIdGroup to calculate physical layer cell ID.";
      mandatory true;
      yexte:disturbances "Changes may affect traffic.";
      type erienmnrmlrat:ddt-Lrat_EUtranCellFDD_physicalLayerSubCellId;
    }
    leaf lbabIncr {
      description "How fast the Access Class Barring probability is increased, that is how fast acBarringFactor in SIB2 is decreased when the cell load is increased.";
      yexte:dependencies "Only takes effect when Load-Based Access Barring is activated.";
      type erienmnrmlrat:ddt-Lrat_EUtranCellFDD_lbabIncr;
      default 5;
    }
    leaf harqOffsetUl {
      description "Offset used when tReorderingUl is calculated by automatic configuration. tReorderingUl = 'Max number of HARQ for UL' * HARQ-interval + harqOffsetUl.";
      yexte:takes-effect "New connection";
      type erienmnrmlrat:ddt-Lrat_EUtranCellFDD_harqOffsetUl;
      default 3;
    }
    container acBarringPresence {
      description "Specifies how access class barring IE for each traffic class is present in SIB2 and priority level assigned to it.";
      erienmyext:enm-type STRUCT;
      uses erienmnrmlrat:struct-AcBarringPresence;
    } // end 'container acBarringPresence'
    leaf sdmActive {
      description "Specifies if SDM (Spatial Division Multiplexing) for CombinedCell configuration is activated or not. If SDM is activated, it is possible to multiplex multiple Ues in different sectors in the same time and same frequency resource.";
      yexte:disturbances "Change can affect traffic";
      yexte:takes-effect "Object disabled/enabled";
      type boolean;
      default false;
    }
    leaf ttiBundlingSwitchThres {
      description "SINR threshold for triggering a switch to TTI bundling.";
      yexte:takes-effect "Cell lock/unlock";
      type erienmnrmlrat:ddt-Lrat_EUtranCellFDD_ttiBundlingSwitchThres;
      default 90;
    }
    leaf pdschMaxNrOfPrbsPerUe {
      description "Maximum number of physical resource blocks (PRBs) allowed on PDSCH for each UE.\nNote: If the set value is larger than the system bandwidth, then the system bandwidth value will be used instead.\nFor PDSCH resource allocation type 0, the actual maximum number of PRBs that is allocated will be a multiple of RBGs (Resource Block Groups) that is nearest to the set value but without exceeding it.";
      yexte:takes-effect "Object unlocked";
      type erienmnrmlrat:ddt-Lrat_EUtranCellFDD_pdschMaxNrOfPrbsPerUe;
      default 100;
    }
    leaf-list arpPriorityLevelForSPIFHo {
      min-elements 16;
      max-elements 16;
      description "ARP Priority Level list used in the feature Service or Priority-Triggered Inter-Frequency Handover.\nThe first instance in the list is for ARP Priority Level 0, second for 1, and so on. Value \"false\" means the UE with this bearer is not intended to be moved to other frequency.";
      yexte:takes-effect "New connection";
      type boolean;
      default false;
      default false;
      default false;
      default false;
      default false;
      default false;
      default false;
      default false;
      default false;
      default false;
      default false;
      default false;
      default false;
      default false;
      default false;
      default false;
    }
    leaf lbabThreshTimeLow {
      description "Time period to measure RRC Connection Reject Ratio against threshold lbabThreshRejectRateLow.";
      yexte:dependencies "Only takes effect when Load-Based Access Barring is activated.";
      type erienmnrmlrat:ddt-Lrat_EUtranCellFDD_lbabThreshTimeLow;
      default 30;
    }
    leaf maxQciLatencyMeas {
      status deprecated {
        yexte:status-information "Since L16A. Planned to be removed.";
      }
      description "Largest numerical value corresponding to the lowest priority of the QCIs included into MAC latency measurements.";
      yexte:dependencies "maxQciLatencyMeas >= minQciLatencyMeas";
      type erienmnrmlrat:ddt-Lrat_EUtranCellFDD_maxQciLatencyMeas;
      default 255;
    }
    leaf prioHpueCapability {
      description "Priority of high power UE capability.";
      type erienmnrmlrat:enum-PrioHpueCapability;
      default NO_PRIORITIZATION;
    }
    leaf lbEUtranTriggerOffloadThreshold {
      description "This attribute is a threshold for eNodeB. The value applies for offload towards EUTRAN target cells. The eNodeB attempts to offload traffic from the source cell to Inter-Frequency LTE neighbors corresponding to the subscription ratio above the threshold.";
      yexte:disturbances "Changing this attribute can cause loss of traffic.";
      type erienmnrmlrat:ddt-Lrat_EUtranCellFDD_lbEUtranTriggerOffloadThreshold;
      default 100;
    }
    leaf allocTimerPucchFormat1 {
      description "A guard time. After this time, a PUCCH format 1 PRB pair is allocated if threshold allocThrPucchFormat1 is still passed.";
      type erienmnrmlrat:ddt-Lrat_EUtranCellFDD_allocTimerPucchFormat1;
      default 50;
    }
    leaf diffAdmCtrlFilteringProfRef {
      description "Reference to an instance of DiffAdmCtrlFilteringProfile MO.";
      yexte:disturbances "Changing this attribute can cause loss of traffic.";
      erienmyext:enm-type MOREF;
      type string;
    }
    leaf pdcchCovImproveDtx {
      description "PDCCH DCI format 1A for first re-transmission due to DTX of SRB and QCI1.";
      yexte:takes-effect "Cell lock/unlock";
      type boolean;
      default false;
    }
    leaf cioUpperLimitAdjBySon {
      description "Indicates the upper limit value of cellIndividualOffsetEUtran range that the SON function is allowed to adjust.";
      yexte:disturbances "Changing this attribute can stop outgoing HO.";
      type erienmnrmlrat:ddt-Lrat_EUtranCellFDD_cioUpperLimitAdjBySon;
      default 4;
    }
    leaf pdcchCovImproveSrb {
      description "PDCCH DCI format 1A is used for SRB to increase transmission success rate and to minimize interruption time.";
      yexte:takes-effect "Cell lock/unlock";
      type boolean;
      default false;
    }
    leaf-list additionalUpperLayerIndList {
      min-elements 0;
      max-elements 5;
      description "Whether upperLayerIndication is set for additional PLMN identities. Indication in additionalUpperLayerIndList[x] refers to PLMN ID in additionalPlmnList[x].\nThe upperLayerIndication is broadcast in SIB2.";
      yexte:dependencies "Must have the same length as additionalPlmnList. Valid for Baseband Radio Node only.";
      type erienmnrmlrat:enum-LayerState;
      default OFF;
      default OFF;
      default OFF;
      default OFF;
      default OFF;
    }
    leaf-list activeServiceAreaId {
      min-elements 0;
      max-elements 64;
      config false;
      description "The active MBMS Service Area Identity. The content of this attribute is either empty or has the value of the attribute MbsfnArea::serviceAreaId for one or more MbsfnArea MOs. Purpose of this attribute is to support OSS SNAD functionality. This attribute is mirrored by OSS to ExternalEUtranCellFDD/TDD.";
      yexte:dependencies "A (configured) MbsfnArea::serviceAreaId becomes Active ServiceAreaId if:\n- the MBMS Multicarrier feature is activated\n- the cell has an unreserved MBSFNAreaCellRelation to an UNLOCKED MBSFNArea\n- time and phase synchronization accuracy fulfills requirements for LTE Broadcast";
      notife:notifiable-state-data true;
      type erienmnrmlrat:ddt-Lrat_EUtranCellFDD_activeServiceAreaId;
    }
    leaf estCellCapUsableFraction {
      description "Scaling factor for the estimated cell subscription capacity. Can be used to reduce the traffic load balancing attraction of the cell. Used if traffic handling capacity of the cell is constrained by circumstances the ACCE feature is unable to capture. An example of such a circumstance is at limited UL capacity in a TDD cell.\nWhen the attribute is value is set to 0, the corresponding cell uses the value cellSubscriptionCapacity as the Cell Subscription Capacity value for the cell. This bypasses the automatically estimated Cell Subscription Capacity value for the cell.";
      yexte:disturbances "Changing this attribute can cause loss of traffic.";
      type erienmnrmlrat:ddt-Lrat_EUtranCellFDD_estCellCapUsableFraction;
      default 100;
    }
    leaf hoOptAdjThresholdAbs {
      description "The absolute threshold value for adjusted handover failure rate required to adjust handover parameters.";
      yexte:disturbances "Changing this attribute can stop outgoing HO.";
      type erienmnrmlrat:ddt-Lrat_EUtranCellFDD_hoOptAdjThresholdAbs;
      default 5;
    }
    leaf cellCapMinCellSubCap {
      description "Minimum value for the estimated cell capacity.";
      yexte:dependencies "cellCapMinCellSubCap < cellCapMaxCellSubCap";
      type erienmnrmlrat:ddt-Lrat_EUtranCellFDD_cellCapMinCellSubCap;
      default 500;
    }
    leaf lbabDecr {
      description "How fast the Access Class Barring probability is decreased, that is how fast acBarringFactor in SIB2 is increased when the cell load is decreased.";
      yexte:dependencies "Only takes effect when Load-Based Access Barring is activated.";
      type erienmnrmlrat:ddt-Lrat_EUtranCellFDD_lbabDecr;
      default 5;
    }
    leaf-list additionalPlmnAlarmSupprList {
      min-elements 0;
      max-elements 5;
      description "The list of PLMN IDs in the cell indicates if they are suppressed for alarms PLMN Service Degraded and PLMN Service Unavailable when PLMN  is not available in the cell.\nThe PLMN ID appearing in additionalPlmnList[x] is suppressed when additionalPlmnAlarmSupprList[x] is true.\nIf the configured PLMN ID is not a served PLMN ID, then the alarm is suppressed independent of the configured settings.";
      yexte:dependencies "The length of this list must be the same as the list in addtionalPlmnList.";
      type boolean;
      default false;
      default false;
      default false;
      default false;
      default false;
    }
    leaf measuredMaxNoOfUsersInCell {
      erienmyext:no-notification;
      config false;
      description "Peak number of UE in RRC_CONNECTED mode measured in the cell. This attribute will be updated during operation of the eNB and used at unlock of the cell to distribute cells to different cores in Digital Units and Baseband Units with a multicore Main Processor. If attribute expectedMaxNoOfUsersInCell is changed from -1 to zero or higher, attribute measuredMaxNoOfUsersInCell will be reset to zero and not used to control the cell distribution.";
      yexte:takes-effect "Object unlocked";
      type erienmnrmlrat:ddt-Lrat_EUtranCellFDD_measuredMaxNoOfUsersInCell;
    }
    leaf pdcchLaGinrMargin {
      description "GINR back-off parameter for PDCCH link adaptation. Applies to all UEs when the feature Enhanced PDCCH Link Adaptation is disabled. In FDD, if the licenses for both Enhanced PDCCH Link Adaptation and Carrier Aggregation are enabled, this parameter applies to secondary cell PDCCH for UEs capable of carrier aggregation. In TDD, if the license for Enhanced PDCCH Link Adaptation is enabled, this parameter applies to:\n- UEs configured with carrier aggregation, and\n- UEs configured with HARQ-ACK PUCCH format 3 or HARQ-ACK multiplexing.";
      yexte:takes-effect "Object unlocked";
      type erienmnrmlrat:ddt-Lrat_EUtranCellFDD_pdcchLaGinrMargin;
      default 100;
    }
    leaf plmn2AbConfProfileRef {
      description "Reference to an instance of PlmnAbConfProfile. Points to the PLMN Access Barring configuration profile.";
      yexte:disturbances "Changing this attribute can cause loss of traffic.";
      yexte:dependencies "References plmn1AbConfProfileRef, plmn2AbConfProfileRef and plmn3AbConfProfileRef must point to unique PlmnAbConfProfile MO instance.";
      erienmyext:enm-type MOREF;
      type string;
    }
    leaf outOfCoverageSrTimerPeriodicity {
      description "Repetition rate of UL sparse grants that are eNodeB-triggered to Out Of Coverage (OOC) UEs.";
      yexte:takes-effect "Cell lock/unlock";
      type erienmnrmlrat:ddt-Lrat_EUtranCellFDD_outOfCoverageSrTimerPeriodicity;
      default 320;
    }
    list multipleNSPmaxReqMapping {
      min-elements 0;
      max-elements 64;
      key auto-generated-struct-key;
      leaf auto-generated-struct-key {
        type uint16;
        description "This leaf has been injected to allow for struct instances in a sequence to be ordered.";
        mandatory true;
      }
      description "A list which maps frequency bands to additional Pmax value, and additional spectrum emissions as described by 3GPP TS 36.101, table 6.2.4-1. This list is used to generate the value of additionalMultipleNSPmax.";
      erienmyext:enm-type STRUCT;
      uses erienmnrmlrat:struct-MultipleNSPmaxReqMapping;
    } // end 'list multipleNSPmaxReqMapping'
    leaf lbabPeriod {
      description "Minimum time for how often the acBarringFactor in SIB2 can be changed.";
      yexte:dependencies "Only takes effect when Load-Based Access Barring is activated.";
      type erienmnrmlrat:ddt-Lrat_EUtranCellFDD_lbabPeriod;
      default 120;
    }
    leaf dlBlerTargetEnabled {
      description "Turns on/off Configurable DL BLER Target.";
      yexte:takes-effect "Next cell unlock";
      type boolean;
      default false;
    }
    leaf mfbiFreqBandIndPrio {
      description "Changes priorities of bands for Multiple Frequency Band Indicators.\nIf true:\nCell broadcasts freqBandIndicatorPriority in SIB1, and FreqBandIndicatorPriority=broadcasted is sent over X2 interface to neighbor eNB.\nPrioritized additional frequency band list (prioAdditionalFreqBandList) is broadcasted in SIB1 and is also used for handovers (including S1 and X2 handovers) instead of additionalFreqBandList.\nIf UE indicates freqBandPriorityAdjustment capability (support of freqBandIndicatorPriority), primary band has the lowest priority, otherwise primary band has the highest priority.\nmfbiFreqBandIndPrio is not used for handovers between Ericsson eNBs if ENodeBFunction::caAwareMfbiIntraCellHo = true.\nIf false:\nCell doesn't broadcast freqBandIndicatorPriority in SIB1, and FreqBandIndicatorPriority=not-broadcasted is sent over X2 interface to neighbor eNB.\nadditionalFreqBandList is broadcasted in SIB1 and is also used for handovers (including S1 and X2 handovers).\nPrimary band always has the highest priority.";
      yexte:disturbances "Changing this attribute can cause loss of traffic. X2 handover and Connection Setup for MFBI capable UE can fail during a few seconds, leading to dropped calls.";
      yexte:takes-effect "New connection";
      yexte:dependencies "Only takes effect if Multiple Frequency Band Indicators is active.";
      type boolean;
      default false;
    }
    leaf upperLayerIndR15Usage {
      description "Proprietary market adaptation parameter.";
      yexte:dependencies "Valid for Baseband Radio Node only.";
      type boolean;
      default false;
    }
    leaf pdcchCfiMode {
      description "Controls the CFI (Control Format Indicator) used for the control region. cfiMode maps to CFI as described under enumerations. For DL BW of 1400 kHz, values of CFI = 1, 2 and 3 map to 2, 3, and 4 control region symbols respectively. Other BW, CFI maps directly to number of control region symbols.";
      yexte:takes-effect "Object unlocked";
      yexte:dependencies "pdcchCfiMode cannot equal CFI_STATIC_1 while dlChannelBandwidth = 1400, 3000, or 5000 kHz since there would be insufficient CCEs to transmit a PDCCH for common channel messages such as SIB1 or SI. Certain values of pdcchCfiMode that allow high CFI values may be disallowed when the combination of attributes pdcchCfiMode, dlChannelBandwidth, noOfPucchCqiUsers, and noOfPucchSrUsers require too many corresponding PUCCH HARQ-ARQ resources.";
      type erienmnrmlrat:enum-CfiMode;
      default CFI_STATIC_BY_BW;
    }
    leaf otdoaSuplActive {
      description "Indicates if the feature OTDOA Support in SUPL Environment is ACTIVATED  or DEACTIVATED in the cell.";
      yexte:takes-effect "Object unlocked.";
      type boolean;
      default false;
    }
    leaf hoOptAdjThresholdAbsQci1 {
      description "Absolute threshold for adjusted handover failure rate required to adjust cellIndividualOffsetEUtranQci1.";
      yexte:disturbances "Changing this attribute can stop outgoing HO.";
      type erienmnrmlrat:ddt-Lrat_EUtranCellFDD_hoOptAdjThresholdAbsQci1;
      default 5;
    }
    leaf lbabThreshRejectRateLow {
      description "RRC Connection Reject Ratio threshold below which Load-Based Access Barring decreases access class barring probability or Progressive Access Barring, or PLMN-Specific Access Barring recedes to lower priority.";
      yexte:dependencies "Only takes effect when Load-Based Access Barring is activated.";
      type erienmnrmlrat:ddt-Lrat_EUtranCellFDD_lbabThreshRejectRateLow;
      default 20;
    }
    leaf adaptiveCfiHoProhibit {
      description "Controls adaptive CFI to avoid using CFI=1 or CFI=1,2, when scheduling UEs that are in handover. The highest CFI value in available CFI values determined by pdcchCfiMode is not prohibited.";
      yexte:takes-effect "Cell lock/unlock";
      yexte:dependencies "Applicable only when attribute pdcchCfiMode is set to CFI_AUTO_MAXIMUM_2 or CFI_AUTO_MAXIMUM_3.";
      type erienmnrmlrat:enum-AdaptiveCfiHoProhibitMode;
      default NO_HO_PROHIBIT_CFI;
    }
    leaf lbEUtranAcceptOffloadThreshold {
      description "This attribute is a threshold for eNodeB. The value applies in the target cell for incoming offload. The eNodeB accepts incoming offload traffic in the target cell as long as the subscription ratio is below the threshold.";
      yexte:disturbances "Changing this attribute can cause loss of traffic.";
      type erienmnrmlrat:ddt-Lrat_EUtranCellFDD_lbEUtranAcceptOffloadThreshold;
      default 50;
    }
    list spectrumEmissionReqMapping {
      min-elements 0;
      max-elements 64;
      key auto-generated-struct-key;
      leaf auto-generated-struct-key {
        type uint16;
        description "This leaf has been injected to allow for struct instances in a sequence to be ordered.";
        mandatory true;
      }
      description "A list which maps frequency bands to network signaling values specifying additional spectrum emissions, as described by 3GPP TS 36.101, table 6.2.4-1. A band which is not explicitly mapped to a network signaling value by this list, will use the value NS_01. This list is used to generate the value of additionalSpectrumEmissionValues.";
      erienmyext:enm-type STRUCT;
      uses erienmnrmlrat:struct-SpectrumEmissionReqMapping;
    } // end 'list spectrumEmissionReqMapping'
    leaf earfcndl {
      yexte:restricted;
      description "The channel number for the central downlink frequency. The mapping from channel number to physical frequency for specified EUTRA bands is described in 3GPP TS 36.104. The values that can be used depend on national, operator-specific frequency allocation as well as on the supported frequency bands in the RBS.\nNote: Use the MO action changeFrequency if the DL frequency must be changed after the cell is initially setup.";
      mandatory true;
      yexte:disturbances "Changes may affect traffic.";
      yexte:takes-effect "Object disabled/enabled.";
      yexte:dependencies "This attribute is dependent on and set together with earfcnul. The earfcnul and earfcndl values are dependent and relate according to default EUTRA TX channel to RX channel separation as specified in 3GPP TS 36.101 for the  EUTRA operating band and channel bandwidth of the cell.";
      type erienmnrmlrat:ddt-Lrat_EUtranCellFDD_earfcndl;
    }
    leaf dlPowerState {
      config false;
      description "State of downlink output power.";
      notife:notifiable-state-data true;
      type erienmnrmlrat:enum-DlPowerState;
    }
    leaf commonSrPeriodicity {
      description "Common SR periodicity, used for all UEs.";
      yexte:takes-effect "Cell lock/unlock";
      yexte:dependencies "For 1.4 MHz: Only valid inputs are 10 and 20.";
      type erienmnrmlrat:ddt-Lrat_EUtranCellFDD_commonSrPeriodicity;
      default 10;
    }
    leaf orientMajorAxis {
      description "Orientation of the major axis of uncertainty, in degrees clockwise from north.  Orientation value (N) is derived by the formula:\nN <= X < (N + 1)\nwhere X is the orientation in degrees (0 - 180).";
      yexte:dependencies None;
      type erienmnrmlrat:ddt-Lrat_EUtranCellFDD_orientMajorAxis;
      default 0;
    }
    leaf ulDynUeAdmCtrlOverloadThr {
      description "Highest allowed UL radio resource utilization ratio for admission of a non-privileged UE. Applies to each UL resource considered by Dynamic UE Admission Control. Resource utilization is checked against this threshold for all new, re-established, or incoming handover RRC connections.";
      yexte:disturbances "Changing this attribute can affect the following:\n- the number of RRC-connected users\n- cell throughput and the number of rejected non-privileged RRC connection requests       - rejected non-privileged RRC connection re-establishment requests and rejected\n  non- privileged incoming handover requests.";
      yexte:dependencies "ulDynUeAdmCtrlOverloadThr >= ulDynUeAdmCtrlRetDiffThr";
      type erienmnrmlrat:ddt-Lrat_EUtranCellFDD_ulDynUeAdmCtrlOverloadThr;
      default 600;
    }
    leaf csiRsConfigType {
      description "Configuration type of 8 port CSI-RS (Channel State Information Reference Signal).";
      yexte:takes-effect "Next cell unlock";
      type erienmnrmlrat:enum-CsiRsConfigTypeFDD;
      default NZP_CSIRS;
    }
    leaf ul64qamEnabled {
      description "Enables UL 64-QAM at cell level.";
      yexte:takes-effect "Cell lock/unlock";
      yexte:dependencies "Only relevant if the license for UL 64-QAM is present and the\nfeature is active.";
      type boolean;
      default true;
    }
    leaf lessPrbUsageThreshold {
      description "Maximum downlink PRB usage that scheduling stays on-hold for Low Energy Scheduler Solution.";
      type erienmnrmlrat:ddt-Lrat_EUtranCellFDD_lessPrbUsageThreshold;
      default 90;
    }
    leaf-list includeLcgInMacUeThp {
      min-elements 4;
      max-elements 4;
      description "Controls the LCGs that are included in pmMacUeThpVolUl, pmMacUeThpTimeUl, and pmMacUeThpUlDistr. To include the n:th LCG, set includeLcgInMacUeThp[n]=true.\n";
      type boolean;
      default false;
      default false;
      default true;
      default true;
    }
    list endcAllowedPlmnList {
      min-elements 0;
      max-elements 6;
      key auto-generated-struct-key;
      leaf auto-generated-struct-key {
        type uint16;
        description "This leaf has been injected to allow for struct instances in a sequence to be ordered.";
        mandatory true;
      }
      description "PLMN ID allowed to use EN-DC. If empty, EN-DC not allowed in cell.\n";
      erienmyext:enm-type STRUCT;
      uses erienmnrmlrat:struct-PlmnIdentity;
    } // end 'list endcAllowedPlmnList'
    leaf schedulingInfoSib1BrMod {
      description "Whether or not to modify the transmission of IE SchedulingInfoSIB1-BR-r13 in the MIB to improve accessibility of faulty legacy LTE UEs (not compliant with Release 13 of 3GPP). If modification is on, also UEs which require zero schedulingInfoSIB1-BR-r13 are supported.";
      yexte:takes-effect "Next cell unlock";
      yexte:dependencies "Only valid if catm1SupportEnabled = true.";
      type erienmnrmlrat:enum-MibContentScheduling;
      default OFF;
    }
    leaf eranUlCompUserSelSinrHys {
      description "Hysteresis of SINR threshold for Elastic RAN UL CoMP user selection.";
      yexte:dependencies "Must be used together with eranUlCompUserSelSinrThr.";
      type erienmnrmlrat:ddt-Lrat_EUtranCellFDD_eranUlCompUserSelSinrHys;
      default 10;
    }
    leaf hostingDigitalUnit {
      config false;
      description "Shows the DU or Baseband on which baseband processing for the cell is located";
      notife:notifiable-state-data true;
      erienmyext:enm-type MOREF;
      type string;
    }
    leaf initCdma2000SysTimeType {
      description "Intended type of CDMA2000 system time to broadcast in SIB8, if applicable.";
      type erienmnrmlrat:enum-Cdma2000SysTimeVals;
      default NONE;
    }
    leaf-list cellResourceRef {
      min-elements 0;
      max-elements 6;
      status deprecated {
        yexte:status-information "Since 18.Q2. Has no functional behavior. Planned to be removed.";
      }
      description "References to an instance of CellResource MO.";
      yexte:takes-effect "Next cell unlock";
      yexte:dependencies "CellResource MO having non empty plmnList and CellResource MO having non empty spidList shouldn't be referred together(CellResource MO having empty plmnList and empty spidList is considered as configuring spidList(non empty spidList)). Duplication of PLMN or SPID within referred CellResouce MOs is not allowed.";
      erienmyext:enm-type MOREF;
      type string;
    }
    leaf measCellGroupCellRef {
      description "References to an instance of MeasCellGroup MO for grouping on a cell basis.";
      yexte:dependencies "MeasCellGroup with 0 groupId can not be referred.\nOnly MeasCellGroup having empty spidList and empty plmnList can be referred.";
      erienmyext:enm-type MOREF;
      type string;
    }
    leaf earfcnul {
      description "Channel number for the central UL frequency. The mapping from channel number to physical frequency for specified EUTRA bands is described in 3GPP TS 36.104. Values that can be used depend on national, operator-specific frequency allocation, as well as on the supported frequency bands of the RBS. Value 0 means that the UL channel number is N/A for the DL-only bands.";
      mandatory true;
      yexte:disturbances "Changes may affect traffic.";
      yexte:takes-effect "Object disabled/enabled";
      yexte:dependencies "This attribute is dependent on and set together with earfcndl. The earfcnul and earfcndl values are dependent and relate according to default EUTRA TX channel to RX channel separation as specified in 3GPP TS 36.101 for the  EUTRA operating band and channel bandwidth of the cell.";
      type erienmnrmlrat:ddt-Lrat_EUtranCellFDD_earfcnul;
    }
    leaf servOrPrioRedirectEnabled {
      description "Indicates if release with redirection is allowed in the feature Service or Priority-Triggered Inter-Frequency Handover.";
      yexte:takes-effect "New connection";
      type boolean;
      default true;
    }
    leaf dl256QamEnabled {
      description "Enable or disable 256 QAM support in DL.";
      yexte:takes-effect "Cell lock/unlock";
      type boolean;
      default true;
    }
    leaf ailgRef {
      description "Refers to an instance of AirIfLoadProfile. Assigns a AirIfLoadProfile to a cell.";
      erienmyext:enm-type MOREF;
      type string;
    }
    leaf elcLongDrxCycle {
      description "Long DRX cycle for ELC. Value of elcLongDrxCycle is in number of sub-frames.";
      yexte:takes-effect "New connection";
      yexte:dependencies "Feature Ericsson Lean Carrier is present active.";
      type erienmnrmlrat:enum-ElcLongDrxCycle;
      default SF40;
    }
    leaf resourcePartitionGroupRef {
      description "Reference to an instance of ResourcePartitionGroup MO.";
      yexte:disturbances "Changing this attribute can affect traffic.";
      yexte:takes-effect "Cell lock/unlock";
      erienmyext:enm-type MOREF;
      type string;
    }
    leaf dl256QamStatus {
      erienmyext:no-notification;
      config false;
      description "Indication if 256 QAM in DL is supported in the cell.";
      type erienmnrmlrat:enum-Dl256QamSupport;
    }
    leaf crsGain {
      description "Sets the DL power of the Cell specific Reference Signal (CRS) relatively a reference level defined by the power of the PDSCH type A resource elements. If crsGain is +3dB, the CRS power is 3dB higher than that of a PDSCH type A resource element.\nThe settings crsGain=4.77db and 6dB are mapped to 3dB. These settings are not supported.\nPDSCH type A resource elements are located in symbols that do not contain CRS.";
      yexte:takes-effect "Cell lock/unlock";
      yexte:dependencies "The crsGain only takes effect if the configured number of antenna ports used in a sector is 2, 4, or 8.  In the one port case, crsGain is hardcoded to 0dB.";
      type erienmnrmlrat:ddt-Lrat_EUtranCellFDD_crsGain;
      default 0;
    }
    leaf measBasedElcControl {
      description "Enables or disables measurement-based Ericsson Lean Carrier Control.";
      yexte:takes-effect "New connection";
      yexte:dependencies "Only relevant if license Ericsson Lean Carrier is present and feature is active.";
      type boolean;
      default false;
    }
    leaf prachFrequencyAllocation {
      description "Controls allocation of PRACH to upper or lower part of band.\nControls both LTE PRACH and PRACH for Bandwidth Reduced (BR) UEs together.\nFor example, it can be used for avoiding interfered part of band.\n0: Allocate PRACH from lower part of band.\n1: Allocate PRACH from upper part of band.";
      yexte:takes-effect "Next cell unlock";
      type erienmnrmlrat:ddt-Lrat_EUtranCellFDD_prachFrequencyAllocation;
      default 0;
    }
    leaf dlChannelBandwidth {
      description "The downlink channel bandwidth in the cell.\nValid values: 1400, 3000, 5000, 10000, 15000, 20000";
      yexte:disturbances "Changes may affect traffic.";
      yexte:takes-effect "Object disabled/enabled.";
      yexte:dependencies "This attribute is dependent on and shall be set to the same as ulChannelBandwidth.";
      type erienmnrmlrat:ddt-Lrat_EUtranCellFDD_dlChannelBandwidth;
      default 10000;
    }
    leaf pZeroNominalPusch {
      description "The nominal component of the UE transmit power for Physical Uplink Shared Channel (PUSCH).";
      yexte:disturbances "Changes may affect traffic.";
      yexte:dependencies "Changing the value of pZeroNominalPusch, might have impact on the setting of puschPwrOffset64Qam.\nSee puschPwrOffset64Qam for how that attribute depends on pZeroNominalPusch.";
      type erienmnrmlrat:ddt-Lrat_EUtranCellFDD_pZeroNominalPusch;
      default -103;
    }
    leaf acBarringSkipForSms {
      description "Indicates whether or not access attempts for SMS over SGs or SMS over IP from UEs are to skip Access Class Barring functionality.";
      yexte:disturbances "Changing this attribute can block sms.";
      type boolean;
      default false;
    }
    list eutranCellPolygon {
      min-elements 0;
      max-elements 15;
      key auto-generated-struct-key;
      leaf auto-generated-struct-key {
        type uint16;
        description "This leaf has been injected to allow for struct instances in a sequence to be ordered.";
        mandatory true;
      }
      description "Models the manageable characteristics for the cell polygon used for UE positioning. Each polygon corner is described by a latitude and longitude pair. Each polygon corner is represented with one position in the sequence. The other configured polygon corners follow in sequence. There must at least be three corners configured in a polygon when the function is active/used. The points shall be connected in the order that they are given. The last point is connected to the first point.";
      erienmyext:enm-type STRUCT;
      uses erienmnrmlrat:struct-EutranCellCorner;
    } // end 'list eutranCellPolygon'
    leaf noOfPucchFormat2PrbPairsPerFrame {
      erienmyext:no-notification;
      config false;
      description "PRB usage for PUCCH Format2. Based on PUCCH CQI user configuration.";
      type erienmnrmlrat:ddt-Lrat_EUtranCellFDD_noOfPucchFormat2PrbPairsPerFrame;
    }
    leaf covTriggerdBlindHoAllowedBr {
      description "Enables blind handover initiation when CAT-M UE reports bad coverage.\nEven if value is true, eNodeB only initiates blind handover if it finds suitable cell.";
      yexte:takes-effect "New connection";
      type boolean;
      default true;
    }
    leaf latencyLongThreshold {
      description "Signaling latency threshold.\nDynamic Load Control considers procedure latency as long, if above latencyLongThreshold.";
      yexte:takes-effect "Next cell unlock";
      yexte:dependencies "Applicable only when serviceState = OPERABLE for Dynamic Load Control.";
      type erienmnrmlrat:ddt-Lrat_EUtranCellFDD_latencyLongThreshold;
      default 135;
    }
    leaf hpueCaSwitchTimeToTrigger {
      description "Time-to-trigger value for UL measurement in switching between High Power UE to Carrier Aggregation.";
      type erienmnrmlrat:ddt-Lrat_EUtranCellFDD_hpueCaSwitchTimeToTrigger;
      default 40;
    }
    leaf idleModePrioAtReleaseRef {
      description "Reference to an IdleModePrioAtRelease MO. Assigns an IdleModePrioAtRelease to a cell.";
      yexte:disturbances "Changing this attribute can affect traffic.";
      erienmyext:enm-type MOREF;
      type string;
    }
    container changeNotification {
      description "For each System Information Block (SIB), indicates when the SIB content is changed, if system information change notification is broadcast prior to broadcast of updated system information.";
      erienmyext:enm-type STRUCT;
      uses erienmnrmlrat:struct-ChangeNotificationSIBs;
    } // end 'container changeNotification'
    leaf tac {
      description "Tracking Area Code for the EUtran Cell.";
      mandatory true;
      yexte:disturbances "Changes may affect traffic";
      type erienmnrmlrat:ddt-Lrat_EUtranCellFDD_tac;
    }
    leaf ns05PathlossOffsetThres {
      description "Value of threshold to detect if the NS_05 UE is in repeater zone. If the NS_05 UE's pathloss measured on low band is bigger than or equal to the value of other band plus ns05PathlossOffsetThres, the NS_05 UE is detected as in repeater zone.";
      yexte:dependencies "Only takes effect if:\n- license for NS 05 Additional Maximum Power Reduction Support is present and the feature is active, and\n- attribute networkSignallingValue in MOC EUtranCellFDD/TDD is NS_05, and\n- attribute ns05LowBandSchedMode is ADAPTIVE_AVAILABLE_BY_REPEATER_DETECTION.";
      type erienmnrmlrat:ddt-Lrat_EUtranCellFDD_ns05PathlossOffsetThres;
      default 50;
    }
    leaf minBestCellHoAttempts {
      description "Number of attempts for handover to a cell better than the serving cell, before handover is attempted to the next best cell. If there is no next best cell in the UE report, handover to the best cell is attempted repeatedly.";
      type erienmnrmlrat:ddt-Lrat_EUtranCellFDD_minBestCellHoAttempts;
      default 1;
    }
    leaf noConsecutiveSubframes {
      description "The number of consecutive downlink sub-frames with positioning reference signals as defined in 3GPP TS 36.211. Values define 1, 2, 4, or 6 consecutive sub-frames.";
      yexte:takes-effect "Object unlocked";
      yexte:dependencies None;
      type erienmnrmlrat:enum-NoOfSubframesVals;
      default SF1;
    }
    leaf-list serviceAreaId {
      min-elements 0;
      max-elements 64;
      status deprecated {
        yexte:status-information "Since L16B. Replaced by MbsfnArea::serviceAreaId. Planned to be removed.";
      }
      description "The MBMS Service Area Identity.";
      yexte:dependencies "At least one defined serviceAreaId needs to be configured in the eNB to ENABLE a TermPointToMmeM3";
      type erienmnrmlrat:ddt-Lrat_EUtranCellFDD_serviceAreaId;
    }
    leaf longitude {
      description "The degree of longitude of the transmitter antenna position.\nIn case of Combined Cell (multi-sector cell):\n   For indoor system, antenna of any sector.\n   For outdoor system,antenna of macro sector.";
      type erienmnrmlrat:ddt-Lrat_EUtranCellFDD_longitude;
      default 0;
    }
    leaf clusteredPuschMprFactor {
      description "Multiplication factor applied to the 3GPP-defined Maximum Power Reduction values for Clustered PUSCH. Low settings imply high usage of Clustered PUSCH, high settings imply the opposite.";
      yexte:takes-effect "Object unlocked";
      type erienmnrmlrat:ddt-Lrat_EUtranCellFDD_clusteredPuschMprFactor;
      default 100;
    }
    leaf pdcchOuterLoopUpStepVolte {
      description "PDCCH outer loop up step size for UEs with any bearer mapped to a QCI with serviceType of VoIP. In TDD, this parameter applies only to UEs which are configured with HARQ-ACK bundling.";
      yexte:takes-effect "Object unlocked";
      type erienmnrmlrat:ddt-Lrat_EUtranCellFDD_pdcchOuterLoopUpStepVolte;
      default 6;
    }
    leaf srvccDelayTimer {
      description "The length of time the eNodeB delays Single Radio Voice Call Continuity (SRVCC) handover.\nValue 0 means no delay.";
      yexte:takes-effect "New connection";
      type erienmnrmlrat:ddt-Lrat_EUtranCellFDD_srvccDelayTimer;
      default 0;
    }
    leaf hoOptStatNumQci1 {
      description "Minimal number of handovers required by AMO function before adjusting cellIndividualOffsetEUtranQci1.";
      type erienmnrmlrat:ddt-Lrat_EUtranCellFDD_hoOptStatNumQci1;
      default 200;
    }
    leaf minQciLatencyMeas {
      status deprecated {
        yexte:status-information "Since L16A. Planned to be removed.";
      }
      description "Smallest numerical value corresponding to the highest priority of the QCIs included into MAC latency measurements.";
      yexte:dependencies "minQciLatencyMeas  =< maxQciLatencyMeas";
      type erienmnrmlrat:ddt-Lrat_EUtranCellFDD_minQciLatencyMeas;
      default 5;
    }
    leaf lbTpNonQualFraction {
      description "The fraction of non-qualified UEs at UE selection for throughput aware load balancing. In case throughput aware UE selection is enabled, this parameter sets a target size for the fraction of UE to be disqualified for load balancing due to insufficient relative gain when moving UE from source to target cell.\nSpecial value 0 means that the throughput aware UE selection for this cell is disabled.";
      type erienmnrmlrat:ddt-Lrat_EUtranCellFDD_lbTpNonQualFraction;
      default 35;
    }
    list pciDetectingCell {
      min-elements 0;
      max-elements 5;
      key auto-generated-struct-key;
      leaf auto-generated-struct-key {
        type uint16;
        description "This leaf has been injected to allow for struct instances in a sequence to be ordered.";
        mandatory true;
      }
      description "Indicates the CGI of the cell that detected the PCI collision/confusion. This value is only valid if the corresponding attribute pciConflict is \"YES\" or \"YES_CONFLICTING_CELL\". The first cell in the pciDetectingCell list corresponds to the first cell in the pciConflictCell list and the first value of pciConflict. The second cell in the pciDetectingCell list corresponds to the second cell in the pciConflictCell list and the first value of pciConflict.";
      erienmyext:enm-type STRUCT;
      uses erienmnrmlrat:struct-Cgi;
    } // end 'list pciDetectingCell'
    container frameStartOffset {
      description "The frame start offset of the cell.\n";
      erienmyext:enm-type STRUCT;
      uses erienmnrmlrat:struct-FrameStartOffset;
    } // end 'container frameStartOffset'
    container siPeriodicityBr {
      description "SI message periodicity for Bandwidth reduced UEs. If SIB is not mapped to SI message, SI message is not transmitted.";
      erienmyext:enm-type STRUCT;
      uses erienmnrmlrat:struct-PeriodicitySI;
    } // end 'container siPeriodicityBr'
    leaf pdcchPowerBoostMax {
      description "Maximum power boost applied to UE-specific PDCCHs that require more CCEs than the maximum available CCE aggregation level. If UE-specific PDCCHs  require equal or less, an automatic power boost algorithm is applied. Attribute pdcchPowerBoostMax does not affect those PDCCHs.\nIf set to 0, there is no PDCCH power boost of the maximum CCE aggregation level. PDCCH coverage is not increased but the feature still optimizes the PDCCH power setting for PDCCHs that require equal or less CCEs than the maximum CCE aggregation level. This still allows for higher PDCCH capacity.";
      yexte:takes-effect "Cell lock/unlock";
      type erienmnrmlrat:ddt-Lrat_EUtranCellFDD_pdcchPowerBoostMax;
      default 0;
    }
    leaf prsConfigIndexMapped {
      config false;
      description "This parameter holds the resulting prsConfigIndex value. If prsPeriod is used by the operator then prsConfigIndexMapped will be set by the system. If prsConfigIndex is used by the operator then prsConfigIndexMapped will be a copy of the entered value.";
      notife:notifiable-state-data true;
      type erienmnrmlrat:ddt-Lrat_EUtranCellFDD_prsConfigIndexMapped;
    }
    leaf qQualMinOffset {
      description "The offset applied to the signaled qQualMin.\nCorresponds to Qqualminoffset in TS 36.304.\nValue 0 means that it is not sent in SIB1 and UE applies in such case the (default) value of 0 dB for Qqualminoffset.";
      yexte:dependencies "If the value of qQualMin is set to 0 the parameter qQualMinOffset will not be broadcasted.";
      type erienmnrmlrat:ddt-Lrat_EUtranCellFDD_qQualMinOffset;
      default 0;
    }
    leaf servOrPrioTriggeredIFHo {
      description "Specifies the trigger used in the feature Service or Priority-Triggered Inter-Frequency Handover.";
      yexte:takes-effect "New connection";
      type erienmnrmlrat:enum-ServOrPrioTriggeredIFHoType;
      default QCI;
    }
    leaf networkSignallingValue {
      description "Enables additional spectrum emission requirements according to 3GPP TS 36.101, table 6.2.4-1.";
      yexte:takes-effect "Object disabled/enabled";
      type erienmnrmlrat:enum-NetworkSignallingValue;
      default NS_01;
    }
    leaf qQualMinRsrqCe {
      description "Min quality level (RSRQ) in cell for UE in enhanced coverage mode.\nCorresponds to Qqualmin_CE in TS 36.304, sent in SIB1-BR. If 0, it is not sent and UE applies default value of negative infinity for Qqualmin_CE.";
      type erienmnrmlrat:ddt-Lrat_EUtranCellFDD_qQualMinRsrqCe;
      default 0;
    }
    leaf highBasebandPriority {
      description "Cell prioritization status for Baseband resources. Cells set to true get Baseband resources before cells set to false.";
      yexte:takes-effect "Next cell unlock";
      yexte:dependencies "Only has effect if Baseband Resource Cell Prioritization is enabled.";
      type boolean;
      default false;
    }
    leaf-list additionalFreqBandList {
      min-elements 0;
      max-elements 8;
      config false;
      description "A list of additional frequency bands the cell belongs to, not including the frequency band indicated by the EARFCN value of the cell (primary frequency band). The list is automatically set by the eNB. These additional frequency bands are broadcasted to the UEs in SystemInformationBlockType1 in case the feature Multiple Frequency Band Indicators is enabled in the cell.";
      notife:notifiable-state-data true;
      type erienmnrmlrat:ddt-Lrat_EUtranCellFDD_additionalFreqBandList;
    }
    leaf lastSchedLinkAdaptEnabled {
      description "Controls if link adaptation function allocates largest possible resource to last scheduled UE in the DL. Used to improve UE decoding success rate with reduced code rate.";
      yexte:takes-effect "Cell lock/unlock";
      type boolean;
      default true;
    }
    leaf ulConfigurableFrequencyStart {
      description "Specifies the start frequency offset for the allocation of resources when the uplink interference management is disabled expressed as a percentage of the configured bandwidth.";
      yexte:takes-effect "Object unlocked";
      yexte:dependencies "ulInterferenceManagementActive shall be disabled before this parameter takes effect.";
      type erienmnrmlrat:ddt-Lrat_EUtranCellFDD_ulConfigurableFrequencyStart;
      default 0;
    }
    leaf ssacBarringForMMTELVoicePresent {
      status deprecated {
        yexte:status-information "Since 17.Q3. Replaced by AcBarringPresence.acBarringForMmtelVoicePresence in EUtranCellFDD/EUtranCellTDD::acBarringPresence. Planned to be removed.";
      }
      description "Specifies presence of Information Element ssac-BarringForMMTEL-Voice-r9 in SIB2.";
      yexte:disturbances "Changing this attribute can block VoLTE calls in the cell.";
      type boolean;
      default false;
    }
    leaf ulFrequencyAllocationProportion {
      description "Specifies the amount of frequency resources that is allocated in UL expressed as a percentage of the configured bandwidth.";
      yexte:takes-effect "Object unlocked";
      type erienmnrmlrat:ddt-Lrat_EUtranCellFDD_ulFrequencyAllocationProportion;
      default 100;
    }
    leaf highSpeedUEActive {
      description "Indicates if the feature High Speed UE is activated in the cell";
      yexte:takes-effect "Object unlocked";
      type boolean;
      default false;
    }
    leaf pdcchAdmThreshold {
      status deprecated {
        yexte:status-information "Since L16A. Has no functional behavior. Planned to be removed.";
      }
      description "Sets the threshold for the CCE usage when ue starts to be rejected. This will only cause real rejects if pdcchAdmEnabled = true. Otherwise we will only step pmCellAdmControlPdcchRejMeas both no rejects will take place.";
      yexte:takes-effect "Cell lock/unlock";
      type erienmnrmlrat:ddt-Lrat_EUtranCellFDD_pdcchAdmThreshold;
      default 1000;
    }
    leaf catm1SupportEnabled {
      description "Whether or not support for Category M device is enabled in the cell.\nNote: Feature is optional and under license control.";
      yexte:takes-effect "Cell lock/unlock";
      yexte:dependencies "Must be false if isDlOnly is true.";
      type boolean;
      default false;
    }
    leaf iuaInterval {
      status deprecated {
        yexte:status-information "Since 18.Q3. Replaced by InstantUplinkAccess::iuaInterval. Planned to be removed.";
      }
      description "Time interval between UL short-SPS (semi-persistent scheduling) instances. Value 0 means load based selection of IUA interval.";
      yexte:dependencies "In MO EUtranCellFDD, only values 0,1,2,4 are allowed. In MO EUtranCellTDD, only values 0,1,5 are allowed.";
      type erienmnrmlrat:ddt-Lrat_EUtranCellFDD_iuaInterval;
      default 1;
    }
    leaf altitude {
      description "Transmitter antenna altitude (meters). Use +/- values to denote height/depth.\nIn case of Combined Cell (multi-sector cell):\nFor indoor system, antenna of any sector.\nFor outdoor system, antenna of macro sector.";
      type erienmnrmlrat:ddt-Lrat_EUtranCellFDD_altitude;
      default 0;
    }
    leaf-list measCellGroupUeRef {
      min-elements 0;
      max-elements 6;
      description "Reference to a list of MeasCellGroup MOs for grouping on UE basis. Referenced Mos include measurements on differentiated UEs into a measurement group.";
      yexte:dependencies "MeasCellGroup with 0 groupId can not be referred.\nMeasCellGroup with empty spidList and empty plmnList can not be referred.\nMeasCellGroup with non-empty plmnList and MeasCellGroup having non null spidList can not be referred together.\nDuplication of plmn or spid within referred MeasCellGroups is not allowed.";
      erienmyext:enm-type MOREF;
      type string;
    }
    container systemInformationBlock7 {
      description "Contains cell re-selection information common for cell re-selection towards GERAN.\n";
      erienmyext:enm-type STRUCT;
      uses erienmnrmlrat:struct-SIB7;
    } // end 'container systemInformationBlock7'
    leaf prescheduling {
      description "Whether or not prescheduling is enabled.";
      type boolean;
      default true;
    }
    container systemInformationBlock6 {
      description "Contains cell re-selection information common for cell re-selection towards UTRAN.\n";
      erienmyext:enm-type STRUCT;
      uses erienmnrmlrat:struct-SIB6;
    } // end 'container systemInformationBlock6'
    leaf pdcchCovImproveQci1 {
      description "PDCCH DCI format 1A to increase MOS for QCI1 in high interference or high path loss scenarios.";
      yexte:takes-effect "Cell lock/unlock";
      type boolean;
      default false;
    }
    leaf enableDrxAwareRlcArq {
      description "Enables function to automatically adapt t-PollretransmitTimer to the time it takes to complete HARQ procedure + harqOffset (UL and DL).";
      yexte:takes-effect "New connection";
      type boolean;
      default false;
    }
    container systemInformationBlock3 {
      description "Contains cell re-selection information common for intra-frequency, inter-frequency and/ or inter-RAT cell re-selection.\n";
      erienmyext:enm-type STRUCT;
      uses erienmnrmlrat:struct-SIB3;
    } // end 'container systemInformationBlock3'
    leaf transmissionMode {
      description "Defines the Transmission Mode (e.g. Transmit Diversity and Closed-Loop Spatial Multiplexing) that shall be used for the UEs that are connected to the cell. See 3GPP TS 36.213 table 7.1-5 for a definition of Transmission Mode.";
      yexte:dependencies "If mbsfnSubframesForTm9 enabled, TM9-capable UEs are reconfigured to TM9.";
      type erienmnrmlrat:enum-TransmissionModeFDD;
      default TRANSMISSION_MODE_3;
    }
    leaf iuaEnabled {
      status deprecated {
        yexte:status-information "Since 18.Q3. Replaced by InstantUplinkAccess::iuaEnabled. Planned to be removed.";
      }
      description "Enables Instant Uplink Access (IUA) for a cell.";
      type boolean;
      default false;
    }
    container systemInformationBlock8 {
      description "Contains cell re-selection information common for cell re-selection towards CDMA2000. This is controlled by the licensing MO Cdma2000SessionContinuity. The SIB8 distribution and information are also controlled by other licenses.";
      erienmyext:enm-type STRUCT;
      uses erienmnrmlrat:struct-SIB8;
    } // end 'container systemInformationBlock8'
    leaf dlPowerRampUpInitRatio {
      description "Initial ratio for downlink output power to start power ramp up.\nValue 100 indicates full cell coverage.";
      yexte:takes-effect "Cell lock/unlock";
      type erienmnrmlrat:ddt-Lrat_EUtranCellFDD_dlPowerRampUpInitRatio;
      default 100;
    }
    leaf noOfChannelSelectionSets {
      description "The number of channel selection PUCCH resource sets (CS sets) to reserve in each cell for secondary cell HARQ feedback. To conserve PUCCH resource, this attribute can be set to 0 if the cell is not used as PCell for Carrier Aggregation.";
      yexte:takes-effect "Cell lock/unlock";
      type erienmnrmlrat:ddt-Lrat_EUtranCellFDD_noOfChannelSelectionSets;
      default 4;
    }
    leaf useBandPrioritiesInSib1 {
      status deprecated {
        yexte:status-information "Since 18.Q4. Replaced by mfbiFreqBandIndPrio. Planned to be removed.";
      }
      description "If enabled, prioritized additional frequency band list is broadcast in SIB1 according to priorities set in EUtranCellFDD::prioAdditionalFreqBandList or in EUtranCellTDD::prioAdditionalFreqBandList. The priorities must be valid.\nIf disabled, EUtranCellFDD::additionalFreqBandList or EUtranCellTDD::additionalFreqBandList is used.";
      yexte:takes-effect "New connection";
      yexte:precondition "eNodeB must support Multiple Frequency Band Indicators feature.";
      type boolean;
      default false;
    }
    leaf mobCtrlAtPoorCovActive {
      description "Specifies if the feature Mobility Control at Poor Coverage is enabled or disabled in the cell.";
      yexte:takes-effect "New connection";
      type boolean;
      default false;
    }
    leaf interEnbUlCompUserSelSinrThr {
      description "SINR threshold for inter-eNodeB UL CoMP user selection.";
      yexte:disturbances "If changed, system performance can be affected. As values go higher, more candidates are selected for Inter-eNodeB Uplink CoMP, but more user measurements are triggered. This impacts MP load and transport load over X2.";
      yexte:dependencies "Must be used together with interEnbUlCompUserSelSinrHys.";
      type erienmnrmlrat:ddt-Lrat_EUtranCellFDD_interEnbUlCompUserSelSinrThr;
      default 100;
    }
    leaf ulTxPsdDistrThr {
      description "Threshold for % of PRBs with \"UL Tx power per PRB >= ulPsdLoadThresholdSinrClpc\" during measSinrClpcPeriod. Below threshold means low cell power load and then SINR based UL closed-loop power control can be considered.";
      yexte:dependencies "Attribute enableSinrUplinkClpc must be true.";
      type erienmnrmlrat:ddt-Lrat_EUtranCellFDD_ulTxPsdDistrThr;
      default 40;
    }
    leaf ulSchedCtrlForOocUesEnabled {
      description "Enables feature UL Scheduling Control for Out Of Coverage (OOC) UEs.";
      yexte:takes-effect "Cell lock/unlock";
      type boolean;
      default true;
    }
    leaf dlInternalChannelBandwidth {
      description "Internal DL channel bandwidth in the cell with reduced channel bandwidth. Reduced bandwidth for an LTE carrier creates free space for carriers of other radio technologies to use within a standard spectrum 5 MHz or 10 MHz. Other spectrum will generate the undefined value 0. Reduced channel bandwidth is only supported on some radios.";
      yexte:disturbances "Changes may affect traffic";
      yexte:takes-effect "Object disabled/enabled";
      yexte:dependencies "Value must be the same as ulInternalChannelBandwidth value.\ndlInternalChannelBandwidth values 4200, 4400, 4600 and 4800 are only allowed when dlChannelBandwidth is 5000.\ndlInternalChannelBandwidth value 9000 is only allowed when dlChannelBandwidth is 10000.";
      type erienmnrmlrat:ddt-Lrat_EUtranCellFDD_dlInternalChannelBandwidth;
      default 0;
    }
    leaf qRxLevMin {
      description "The required minimum received Reference Symbol Received Power (RSRP) level in the E-UTRA frequency for cell reselection. Corresponds to parameter Qrxlevmin in 3GPP TS 36.304. This attribute is broadcast in SIB1.";
      type erienmnrmlrat:ddt-Lrat_EUtranCellFDD_qRxLevMin;
      default -140;
    }
    container acBarringForCsfb {
      description "Access class barring parameters for mobile originating CSFB calls.\nThe information is broadcasted in SIB2.";
      erienmyext:enm-type STRUCT;
      uses erienmnrmlrat:struct-AcBarringConfig;
    } // end 'container acBarringForCsfb'
    leaf voiceMeasAccEnabled {
      status deprecated {
        yexte:status-information "Since 18.Q2. Has no functional behavior. Planned to be removed.";
      }
      description "Enables voice IRAT measurement acceleration in the cell.";
      yexte:takes-effect "New connection";
      yexte:dependencies "Only relevant if mobCtrlAtPoorCovActive is set to true.";
      type boolean;
      default false;
    }
    leaf acBarringSkipForMmtelVoice {
      description "Indicates whether or not access attempts for MMTEL voice from UEs are to skip Access Class Barring functionality.";
      yexte:disturbances "Changing this attribute can block VoLTE calls.";
      type boolean;
      default false;
    }
    leaf confidence {
      description "Percentage of confidence that the target device is within the ellipsoid defined by the three axes of uncertainty: semi-major, semi-minor, and altitude.";
      yexte:dependencies None;
      type erienmnrmlrat:ddt-Lrat_EUtranCellFDD_confidence;
      default 100;
    }
    leaf loadBasedBarringFactor {
      config false;
      description "Current barring factor based on LBAB algorithm or PAB algorithm.";
      yexte:dependencies "Only takes effect when feature Load-Based Access Barring or feature Progressive Access Barring is activated.";
      notife:notifiable-state-data true;
      type erienmnrmlrat:ddt-Lrat_EUtranCellFDD_loadBasedBarringFactor;
    }
    leaf maxNoClusteredPuschAlloc {
      description "Maximum number of UEs with Clustered PUSCH allocations allowed in a TTI.";
      yexte:takes-effect "Object unlocked";
      type erienmnrmlrat:ddt-Lrat_EUtranCellFDD_maxNoClusteredPuschAlloc;
      default 0;
    }
    leaf qRxLevMinCe {
      description "Min received RSRP level in E-UTRA frequency for cell reselection for UE in enhanced coverage mode. Corresponds to parameter Qrxlevmin_CE in 3GPP TS 36.304. This attribute is broadcast in SIB1-BR.";
      type erienmnrmlrat:ddt-Lrat_EUtranCellFDD_qRxLevMinCe;
      default -140;
    }
    leaf ulTrigActive {
      description "Specifies if outgoing uplink-triggered mobility actions are enabled or disabled in the cell.\nUsed when Uplink-Triggered Inter-Frequency Mobility is enabled. The parameter has effect if Mobility Control in Poor Coverage is enabled and mobCtrlAtPoorCovActive is set to true in the cell.";
      type boolean;
      default true;
    }
    leaf hoOptAdjThresholdPerc {
      description "The permillage threshold value for adjusted handover failure rate required to adjust handover parameters.";
      yexte:disturbances "Changing this attribute can stop outgoing HO.";
      type erienmnrmlrat:ddt-Lrat_EUtranCellFDD_hoOptAdjThresholdPerc;
      default 50;
    }
    leaf pMaxServingCell {
      description "Limits UE uplink transmission power in the serving cell and calculates the parameter Pcompensation (defined in 3GPP TS 36.304) for cell selection.\nThe attribute is broadcast in SIB1.\nValue 1000 means the parameter is not included in system information.";
      yexte:disturbances "Changing this attribute can cause loss of traffic.";
      type erienmnrmlrat:ddt-Lrat_EUtranCellFDD_pMaxServingCell;
      default 1000;
    }
    leaf pdcchOuterLoopInitialAdjVolte {
      description "The initial value for PDCCH outer loop adjustment for UEs with any bearer mapped to a QCI with serviceType of VoIP. In TDD, this parameter applies only to UEs which are configured with HARQ-ACK bundling.";
      yexte:takes-effect "Object unlocked";
      type erienmnrmlrat:ddt-Lrat_EUtranCellFDD_pdcchOuterLoopInitialAdjVolte;
      default -70;
    }
    leaf dlPowerRampUpRate {
      description "Power ramp up rate per second for downlink output power to reach full cell coverage.";
      yexte:takes-effect "Cell lock/unlock";
      type erienmnrmlrat:ddt-Lrat_EUtranCellFDD_dlPowerRampUpRate;
      default 1;
    }
    leaf pdcchTargetBler {
      description "PDCCH target error rate for UEs that do not have any secondary cell configured and do not have any bearer mapped to a QCI with serviceType of VoIP. In TDD, this parameter applies only to UEs which are configured with HARQ-ACK bundling.";
      yexte:takes-effect "Object unlocked";
      type erienmnrmlrat:ddt-Lrat_EUtranCellFDD_pdcchTargetBler;
      default 24;
    }
    leaf bsrThreshold {
      description "Threshold used to help identify data-aware UL scheduling UEs. If BSR >= bsrThreshold, UE becomes candidate UE for UL improvement.";
      type erienmnrmlrat:ddt-Lrat_EUtranCellFDD_bsrThreshold;
      default 0;
    }
    leaf iuaMaxPrbsPerUe {
      status deprecated {
        yexte:status-information "Since 18.Q3. Replaced by InstantUplinkAccess::iuaUePrbLimit. Planned to be removed.";
      }
      description "Maximum UL PRBs that are used by an IUA UE. The actual number of PRBs per UE depends on iuaMaxResourcePerCell.";
      type erienmnrmlrat:ddt-Lrat_EUtranCellFDD_iuaMaxPrbsPerUe;
      default 20;
    }
    leaf dlPowerRampUpInitialRatio {
      status deprecated {
        yexte:status-information "Since 18.Q4. Planned to be removed.";
      }
      description "Initial ratio for downlink output power to start power ramp up.\nValue 100 indicates full cell coverage.";
      yexte:takes-effect "Cell lock/unlock";
      type erienmnrmlrat:ddt-Lrat_EUtranCellFDD_dlPowerRampUpInitialRatio;
      default 100;
    }
    leaf plmn3AbConfProfileRef {
      description "Reference to an instance of PlmnAbConfProfile. Points to the PLMN Access Barring configuration profile.";
      yexte:disturbances "Changing this attribute can cause loss of traffic.";
      yexte:dependencies "References plmn1AbConfProfileRef, plmn2AbConfProfileRef and plmn3AbConfProfileRef must point to unique PlmnAbConfProfile MO instance.";
      erienmyext:enm-type MOREF;
      type string;
    }
    leaf noOfPucchSrUsers {
      description "The number of Scheduling Request (SR) resources available on the PUCCH channel.\nFor 1.4 MHz system bandwidth the recommended value is 50.\n\n";
      yexte:disturbances "Cell runs new set-up procedure. All cell-connected UEs are released and connected again.";
      type erienmnrmlrat:ddt-Lrat_EUtranCellFDD_noOfPucchSrUsers;
      default 160;
    }
    leaf lastModification {
      description "Indicates whether the MO was last modified by the operator or if the MO has been modified by the PCI conflict detection application.";
      type erienmnrmlrat:enum-LastModificationSourceCell;
      default OPERATOR;
    }
    leaf pZeroNominalPucch {
      description "The nominal component of the UE transmit power for Physical Uplink Control Channel (PUCCH).";
      yexte:disturbances "Changes may affect traffic.";
      type erienmnrmlrat:ddt-Lrat_EUtranCellFDD_pZeroNominalPucch;
      default -117;
    }
    leaf rachRootSequence {
      description "The first root sequence number for Random Access Channel (RACH) preamble generation. RACH root sequence is broadcast as a part of system information distribution and used for preamble detection.\nSee definition for logical root sequence number in 3GPP TS 36.211.\nIf feature Automated Rach Root Sequence Allocation is not activated a parameter change triggers automatic cell lock/unlock.\nIf feature Automated Rach Root Sequence Allocation is activated the parameter is changed without the need to lock/unlock the cell.";
      yexte:disturbances "Changes may affect traffic.";
      type erienmnrmlrat:ddt-Lrat_EUtranCellFDD_rachRootSequence;
      default 386;
    }
    leaf dlFrequencyAllocationProportion {
      description "Specifies the amount of frequency resources that is allocated in DL expressed as a percentage of the configured bandwidth.";
      yexte:disturbances "Changing this attribute can cause loss of traffic.";
      yexte:takes-effect "Object unlocked";
      type erienmnrmlrat:ddt-Lrat_EUtranCellFDD_dlFrequencyAllocationProportion;
      default 100;
    }
    action stopAilg {
      description "Stops execution of the optional feature Air Interface Load Generator.";
    }
    action startAilg {
      description "Starts execution of the optional feature Air Interface Load Generator.";
    }
    action changeFrequency {
      description "Changes the frequency of the cell. The attribute earfcndl is changed. This MO action includes the following steps:\n\n- An instance of EUtranFrequency with correct frequency is created (if not already existing).\n\n\n- For neigbouring cells with existing cell relations to the cell, create new EUtranFreqRelation instances (if not already existing) and new EUtranCellRelation instances (with the same attribute values as the existing EUtranFreqRelation and EUtranCellRelation MOs).\n\n\n- For the changed cell an instance of EUtranFreqRelation with reference to the correct instance of EUtranFrequency is created, if not already existing (with the same attribute values as the existing EUtranFreqRelation MO).\n\nNote that changing frequency of a EUtranCellFDD will imply that all other eNBs that have this cell configured as an ExternaEUtranCellFDD will be updated with the new frequency. This means that new EUtranFreqRelation and corresponding EUtranFrequency MOs might be created.\n\n";
      input {
        leaf earfcn {
          mandatory true;
          description "The new DL frequency for this cell.";
          type erienmnrmlrat:ddt-EUtranCellFDD_changeFrequency_earfcn;
        }
      }
    }
  } // end 'grouping moc-EUtranCellFDD'
  grouping moc-Cdma2000Network-keys {
    description "Key(s) for MOC Cdma2000Network";
    leaf id {
      erienmyext:no-notification;
      description "The value component of the Relative Distinguished Name (RDN).\n";
      mandatory true;
      yexte:ecim-name cdma2000NetworkId;
      type string;
    }
  } // end 'grouping moc-Cdma2000Network-keys'
  grouping moc-Cdma2000Network {
    description "This Managed Object is a container for CDMA2000 related Managed Objects.\n";
    leaf userLabel {
      description "Label for free use.\n";
      type erienmnrmlrat:ddt-Lrat_Cdma2000Network_userLabel;
    }
  } // end 'grouping moc-Cdma2000Network'
  grouping moc-SecurityHandling-keys {
    description "Key(s) for MOC SecurityHandling";
    leaf id {
      erienmyext:no-notification;
      description "The value component of the RDN.\n";
      mandatory true;
      yexte:ecim-name securityHandlingId;
      type string;
    }
  } // end 'grouping moc-SecurityHandling-keys'
  grouping moc-SecurityHandling {
    description "Models manageable characteristics of security handling except security handling during X2 handover and S1 handover. These characteristics are then used by all instances of RRC dedicated protocol.\n\nThe RDN of this MO is SecurityHandling=1.";
    leaf-list integrityProtectAlgoPrio {
      min-elements 1;
      max-elements 3;
      description "An array specifying the integrity protection algorithms that should be allowed and their priority order. The array has a maximum length of 3 and a minimum length of 1. The algorithm in index zero has the highest priority. Each algorithm shall be written only once in the array.";
      yexte:takes-effect "New connection";
      type erienmnrmlrat:enum-IntegrityProtectionAlgorithmID;
      default EIA2;
      default EIA1;
    }
    leaf countWrapSupervisionActive {
      description "Parameter for controlling whether or not to supervise if COUNT-C is about to wrap.\n";
      yexte:takes-effect "Cell lock/unlock.";
      type boolean;
      default true;
    }
    leaf rbIdSupervisionActive {
      description "Controls supervision when the same radio bearer ID with the same set of parameters occurs in the ciphering algorithm.";
      type boolean;
      default true;
    }
    leaf-list cipheringAlgoPrio {
      min-elements 1;
      max-elements 4;
      description "An array specifying the ciphering algorithms that should be allowed and their priority order. The array has a maximum length of 4 and a minimum length of 1. The algorithm in index zero has the highest priority. Each algorithm shall be written only once in the array.";
      yexte:takes-effect "New connection";
      type erienmnrmlrat:enum-CipheringAlgorithmID;
      default EEA1;
      default EEA2;
      default EEA0;
    }
  } // end 'grouping moc-SecurityHandling'
  grouping moc-ResourcePartitionGroup-keys {
    description "Key(s) for MOC ResourcePartitionGroup";
    leaf id {
      erienmyext:no-notification;
      description "The value component of the RDN.";
      mandatory true;
      yexte:ecim-name resourcePartitionGroupId;
      type string;
    }
  } // end 'grouping moc-ResourcePartitionGroup-keys'
  grouping moc-ResourcePartitionGroup {
    description "Group of resource partitions used together in a cell. All partitions in a group must contain the same empty attribute (plmnList or spidList). Multiple partitions in the same group must not be applicable to the same UE.";
    leaf-list reservedBy {
      min-elements 0;
      config false;
      description "Contains a list of MO instances that reserve this MO instance.";
      yexte:dependencies "The MO may not be deleted if it is reserved.";
      notife:notifiable-state-data true;
      erienmyext:enm-type MOREF;
      type string;
    }
  } // end 'grouping moc-ResourcePartitionGroup'
  grouping moc-QciProfilePredefined-keys {
    description "Key(s) for MOC QciProfilePredefined";
    leaf id {
      erienmyext:no-notification;
      description "The value component of the RDN.\n";
      mandatory true;
      yexte:ecim-name qciProfilePredefinedId;
      type string;
    }
  } // end 'grouping moc-QciProfilePredefined-keys'
  grouping moc-QciProfilePredefined {
    description "Bearer-level QoS configuration.\nNot possible to create or remove instances of this MO.\nEach QciProfilePredefined corresponds to a standardized QCI as described in 3GPP TS 23.203. Except for a default QCI profile activated whenever a profile related to a specific QCI is not defined.\n\nRDNs of these MOs are QciProfilePredefined=qci1 to QciProfilePredefined=qci9, QciProfilePredefined=qci65, QciProfilePredefined=qci66, QciProfilePredefined=qci69, QciProfilePredefined=qci70, and QciProfilePredefined=default.";
    leaf serviceType {
      description "Indicates the service that the bearer is used for.";
      yexte:takes-effect "Cell lock/unlock";
      yexte:precondition "ServiceType PTT can only be set to QciProfilePredefined=qci65 and qci66. ServiceType MC_SIGNALING can only be set to QciProfilePredefined=qci69.";
      yexte:dependencies "Changes to this parameter take effect only if the license for QoS Aware Scheduler is present and the feature is active.";
      type erienmnrmlrat:enum-ServiceType;
      default UNDEFINED;
    }
    leaf userLabel {
      description "Label for free use.\n";
      type erienmnrmlrat:ddt-Lrat_QciProfilePredefined_userLabel;
    }
    leaf pdcpSNLength {
      description "Indicates the Packet Data Convergence Protocol (PDCP) Sequence Number length in bits as specified in TS 36.323.";
      yexte:takes-effect "Cell lock/unlock";
      yexte:dependencies "RLC UM must be configured (rlcMode = UM) to set this attribute to 7. RLC AM must be configured (rlcMode = AM) to set this attribute to 15. 15-bits PDCP SN is only applied if:\n - pdcp-SN-Extension capability is indicated by UE; And\n - UE is of category 11 or above; And\n - UE is capable of at least 3C Carrier Aggregation.\nOtherwise, default value of 12-bits PDCP SN is applied for RLC AM bearers.";
      type erienmnrmlrat:ddt-Lrat_QciProfilePredefined_pdcpSNLength;
      default 12;
    }
    leaf pdbOffset {
      description "An offset to the PDB used by Active Queue Management (AQM).\n";
      yexte:takes-effect "Cell lock/unlock";
      yexte:dependencies "pdb + pdbOffset >= 0";
      type erienmnrmlrat:ddt-Lrat_QciProfilePredefined_pdbOffset;
      default 0;
    }
    leaf rlcMode {
      description "RLC Mode";
      yexte:takes-effect "Cell lock/unlock";
      yexte:dependencies "Can only be set to AM if rlcSNLength is set to 10 or 16 and pdcpSNLength is set to 12 or 15. Must be set to UM if rlcSNLength is set to 5 or pdcpSNLength is set to 7.";
      type erienmnrmlrat:enum-RlcMode;
      default AM;
    }
    leaf dataFwdPerQciEnabled {
      description "Enables forwarding of data for this QCI. ";
      yexte:dependencies "The parameter is only valid if the IntraLTEHODataFwd or S1HODataFwd licence is installed and active.";
      type boolean;
      default false;
    }
    leaf pdbMeasurementDelta {
      description "Adds delay for links when calculating delay of VoIP UL packets.\nPrimarily for use in configuration with at least one vPP.";
      yexte:disturbances "Changing this attribute can cause VoIP counters to indicate worse performance.\nFollowing counters can be affected:\n- EUtranCellFDD/EUtranCellTDD::pmPdcpPktPdbUlOkVoip\n- EUtranCellFDD/EUtranCellTDD::pmVoipQualityRbUlOk\n- EUtranCellFDD/EUtranCellTDD::pmVoipQualityRbUlNok\n- EUtranCellFDD/EUtranCellTDD::pmVoipQualityUeUlOk\n- EUtranCellFDD/EUtranCellTDD::pmVoipQualityUeUlNok";
      yexte:takes-effect "New connection";
      type erienmnrmlrat:ddt-Lrat_QciProfilePredefined_pdbMeasurementDelta;
      default 0;
    }
    leaf endcProfileRef {
      description "Reference to an instance of EndcProfile or EndcProfilePredefined.\nEN-DC profile associated with this QCI.\nIf not set, defaults to EndcProfilePredefined with LDN = ManagementElement=1, ENodeBFunction=1, EndcProfilePredefined=1.";
      yexte:disturbances "Changing this attribute can cause loss of traffic.";
      yexte:takes-effect "New connection";
      yexte:dependencies "Only applicable in Baseband Radio Node.";
      erienmyext:enm-type MOREF;
      type string;
    }
    leaf rlfPriority {
      description "The relative priority among the RLF (Radio Link Failure) profiles, i.e. if the bearer that is setup with this QCI has a higher RLF priority than any of the existing bearers, the RLF configuration will be set to those selected by the rlfProfileId for this QCI. If more than one QCI has been configured with the same and highest value of rlfPriority the RLF configuration will be set by the lowest QCI. The instances that share the same rlfProfileId may have the same rlfPriority value. Also note that larger rlfPriority values indicate higher relative priority.";
      yexte:takes-effect "Object unlocked";
      type erienmnrmlrat:ddt-Lrat_QciProfilePredefined_rlfPriority;
      default 0;
    }
    leaf ulMaxHARQTxQci {
      description "Maximum number of transmissions for one HARQ process in UL when this QCI has the highest HARQ priority.";
      yexte:takes-effect "New connection";
      type erienmnrmlrat:ddt-Lrat_QciProfilePredefined_ulMaxHARQTxQci;
      default 5;
    }
    leaf dlResourceAllocationStrategy {
      description "Defines the downlink resource allocation strategy of the QoS Class Identifier (QCI).";
      yexte:takes-effect "New connection";
      yexte:dependencies "Changes to this parameter take effect only if the licenses for Downlink Frequency Selective Scheduling and QoS Aware Scheduler are present and the features are active.";
      type erienmnrmlrat:enum-ResourceAllocationStrategy;
      default RESOURCE_FAIR;
    }
    leaf counterActiveMode {
      description "Defines the interpretation of active for the QCI:\nFALSE (DEFAULT):\nActive time is measured in the case of:\nDRB: as the time when there is data in a buffer, DL and/or UL, with an added guard period of 100 ms thereafter\nUE: as the time when there is data in a buffer, DL and/or UL, with an added guard period of 100 ms thereafter in any of the DRBs connected to the UE\nThe pmCounters for active E-RABs are stepped in case of data in a buffer, DL and/or UL.\nTRUE:\nActive time is measured in the case of:\nDRB: from the first data occurrence in a buffer to the last data occurrence in a buffer for that DRB\nUE: from the first data occurrence in a buffer to the last data occurrence in a buffer for any DRB associated with the UE\nThe pmCounters for active E-RABs are always stepped since the DRB is considered always active";
      yexte:takes-effect "Cell lock/unlock";
      type boolean;
      default false;
    }
    leaf dscp {
      description "The Differentiated Services Code Point for a Quality of Service Class Indicator (QCI). This corresponds to mappings from RAN QoS to Transport Network QoS.";
      mandatory true;
      yexte:takes-effect "New connection.";
      type erienmnrmlrat:ddt-Lrat_QciProfilePredefined_dscp;
    }
    leaf srsAllocationStrategy {
      description "If the parameter srsAllocationStrategy in the QoS configuration for a Data radio Bearer assigned to a UE is set to ACTIVATED, then an attempt is made to allocate sounding for a UE. If several Data Radio Bearers are setup towards the UE with different QoS configurations, and the QoS configurations has different QCI parameter, an algorithm using the priority parameter in the QoS configuration, will resolve which QoS configuration that will define sounding.";
      yexte:takes-effect "New connection";
      yexte:dependencies "Only relevant if the licenses for QoS Aware Scheduler and frequency selective scheduling are present and the features are active.";
      type erienmnrmlrat:enum-SrsAllocationStrategy;
      default DEACTIVATED;
    }
    leaf relativePriority {
      description "The relative priority associated with a QCI.";
      yexte:takes-effect "New connection";
      yexte:dependencies "Changes to this parameter take effect only if the feature states of the  QoS Aware Scheduler , Proportional Fair Scheduler, and  the Rps are enabled.";
      type erienmnrmlrat:ddt-Lrat_QciProfilePredefined_relativePriority;
      default 1;
    }
    leaf ulMaxWaitingTime {
      description "The scheduler attempts to achieve ulMaxWaitingTime for UL bearers before giving any UL bearer a higher priority. Value 0 means that the higher priority is never applied. Must be set to a similar or slightly shorter value than the PDB. Setting too low a value can affect other services with higher priority. For more information about PDB refer to TS 23.203.";
      yexte:disturbances "Changing this attribute can affect performance of all data bearers. A value that is set too low can affect other services with higher priority. A value that is set too high can cause Dynamic UE Admission Control to fail in keeping the cell stable at overload.";
      yexte:takes-effect "New connection";
      yexte:dependencies "Only used for Resource Fair Scheduling algorithm. Only relevant if the license for Advanced Differentiation for Resource Fair Scheduler is present and the feature is active.";
      type erienmnrmlrat:ddt-Lrat_QciProfilePredefined_ulMaxWaitingTime;
      default 0;
    }
    leaf schedulingAlgorithm {
      description "Specifies which scheduling algorithm is to be used for a certain QCI.";
      yexte:disturbances "Changing this attribute can cause loss of traffic.";
      yexte:takes-effect "New connection";
      yexte:dependencies "Only relevant if the license for QoS Aware Scheduler is present and the feature is active. The value DELAY_BASED can only be used if the attribute serviceType has value VOIP.";
      type erienmnrmlrat:enum-SchedulingAlgorithm;
      default RESOURCE_FAIR;
    }
    leaf qci {
      yexte:restricted;
      description "Quality of Service Class Indicator (QCI) as defined in 3GPP TS 23.203  (Release 8). Each instance of this MO has a unique value for the QCI.\nSpecial value: 0 refers to a default QCI profile activated whenever a profile related to a specific QCI has not been defined.";
      mandatory true;
      yexte:dependencies "Each qci must be set to a unique value.";
      type erienmnrmlrat:ddt-Lrat_QciProfilePredefined_qci;
    }
    leaf dlMaxWaitingTime {
      description "The scheduler attempts to achieve dlMaxWaitingTime for DL bearers before giving any DL bearer a higher priority. Value 0 means that the higher priority is never applied. Must be set to a similar or slightly shorter value than the PDB. Setting too low a value can affect other services with higher priority. For more information about PDB refer to TS 23.203.";
      yexte:disturbances "Changing this attribute can affect performance of all data bearers. A value that is set too low can affect other services with higher priority. A value that is set too high can cause Dynamic UE Admission Control to fail in keeping the cell stable at overload.";
      yexte:takes-effect "New connection";
      yexte:dependencies "Only used for Resource Fair Scheduling algorithm. Only relevant if the license for Advanced Differentiation for Resource Fair Scheduler is present and the feature is active.";
      type erienmnrmlrat:ddt-Lrat_QciProfilePredefined_dlMaxWaitingTime;
      default 0;
    }
    leaf dlMinBitRate {
      description "The scheduler will attempt to achieve minbitrate for all bearers before giving any user a higher rate. Value 0 means that the minRate scheduler is not used.";
      yexte:disturbances "Changing this attribute can cause loss of traffic.";
      yexte:takes-effect "New connection";
      yexte:dependencies "This parameter will only be used if one of the following Proportional Fair scheduling algorithms, \"maximum_C_over_I\", \"proportional_fair_low\", \"proportional_fair_medium\", \"proportional_fair_high\" or \"equal_rate\", has been selected. Only relevant if the license for QoS Aware Scheduler is present and the feature is active.";
      type erienmnrmlrat:ddt-Lrat_QciProfilePredefined_dlMinBitRate;
      default 0;
    }
    leaf absPrioOverride {
      description "Indicates if the data radio bearer is subject to Absolute Priority Override.";
      yexte:disturbances "Changing this attribute can cause loss of traffic.";
      yexte:takes-effect "New connection";
      yexte:dependencies "Only relevant if the license for QoS Aware Scheduler is present and the feature is active.";
      type erienmnrmlrat:enum-AbsPrioOverride;
      default NO_OVERRIDE;
    }
    leaf priorityFraction {
      description "Fractional part of QCI-related priority.\nDecimal part of priority is defined by priority attribute.";
      yexte:disturbances "Changing this attribute can cause loss of traffic.";
      yexte:takes-effect "New connection";
      yexte:dependencies "(priority + priorityFraction) > 0 AND (priority * 10 + priorityFraction) <= 140";
      type erienmnrmlrat:ddt-Lrat_QciProfilePredefined_priorityFraction;
      default 0;
    }
    leaf logicalChannelGroupRef {
      description "Refers to an instance of LogicalChannelGroup. Assigns a Logical Channel Group to a Quality of Service Class Indicator (QCI).";
      mandatory true;
      yexte:takes-effect "New connection";
      erienmyext:enm-type MOREF;
      type string;
    }
    leaf qciACTuning {
      description "Tuning factor per QCI for admission control. Only valid for QCIs with resource type GBR.";
      yexte:disturbances "Setting values below one means overbooking of GBR resources and thus a risk of letting in more GBR traffic than can be supported. Setting values above one means underbooking of GBR resources and thus a risk of underutilization of the resources.";
      yexte:takes-effect "New connection";
      yexte:dependencies "Only relevant if the license for Dynamic GBR admission control is present and the feature is active.\n";
      type erienmnrmlrat:ddt-Lrat_QciProfilePredefined_qciACTuning;
      default 1000;
    }
    leaf inactivityTimerOffset {
      description "The offset time value that can be used to prolong the default inactivity timer.";
      yexte:takes-effect "New connection";
      type erienmnrmlrat:ddt-Lrat_QciProfilePredefined_inactivityTimerOffset;
      default 0;
    }
    leaf drxProfileRef {
      description "Points out the DRX profile associated with this QCI. If not set the default reference will be to the DrxProfile instance corresponding to Local Distinguished Name (LDN) = ManagementElement=1, ENodeBFunction=1, DRxProfile=0.";
      yexte:disturbances "Changing this attribute can cause loss of traffic. Possible mismatch between DRX setting used by network and UE for ongoing connections.";
      yexte:takes-effect "Object unlocked";
      yexte:dependencies "The DRX profile must exist, otherwise it will be interpreted as default DRX profile.";
      erienmyext:enm-type MOREF;
      type string;
    }
    leaf tReorderingDl {
      description "This timer is used by the receiving end of Acknowledged Mode (AM) or Unacknowledged Mode (UM) Radio Link Control (RLC) entity in UE, to detect loss of downlink RLC protocol data units at lower layers.";
      yexte:takes-effect "New connection";
      yexte:dependencies "Not applicable for RLC TM. Only relevant when rlcMode is UM or AM";
      type erienmnrmlrat:ddt-Lrat_QciProfilePredefined_tReorderingDl;
      default 35;
    }
    leaf harqPriority {
      description "Relative HARQ priority of this QCI. If a bearer that is setup with this QCI has highest HARQ priority, HARQ transmission number is set to ulMaxHARQTxQci and dlMaxHARQTxQci. HARQ priority must be unique for all configured MOC instances for QciProfilePredefined and QciProfileOperatorDefined. Does not apply when ulMaxHARQTxQci and dlMaxHARQTxQci are same. Note that larger harqPriority values indicate higher relative priority.";
      yexte:takes-effect "New connection";
      type erienmnrmlrat:ddt-Lrat_QciProfilePredefined_harqPriority;
      default 0;
    }
    container measReportConfigParams {
      description "Parameters for service-specific load management for a certain QCI profile.";
      erienmyext:enm-type STRUCT;
      uses erienmnrmlrat:struct-MeasReportConfigParams;
    } // end 'container measReportConfigParams'
    leaf qciSubscriptionQuanta {
      description "Normalized subscription quantity associated with the specific the QCI. Specifies the subscription cost of a bearer with this predefined profile.  The subscription cost is used for traffic load balancing purposes.";
      yexte:disturbances "Changing this attribute can cause loss of traffic.";
      type erienmnrmlrat:ddt-Lrat_QciProfilePredefined_qciSubscriptionQuanta;
      default 1;
    }
    leaf priority {
      description "Decimal part of QCI-related priority.\nFractional part of priority is defined by priorityFraction attribute.";
      mandatory true;
      yexte:disturbances "Changing this attribute can cause loss of traffic.";
      yexte:takes-effect "New connection";
      yexte:dependencies "(priority + priorityFraction) > 0 AND (priority * 10 + priorityFraction) <= 140";
      type erienmnrmlrat:ddt-Lrat_QciProfilePredefined_priority;
    }
    leaf pdb {
      description "The contribution from eNodeB to the Packet Delay Budget (PDB) for a QCI. Packet delays outside eNodeB e.g. in the transport network are excluded. For more information about PDB refer to TS 23.203.";
      yexte:takes-effect "Cell lock/unlock";
      yexte:dependencies "Only relevant if the license for QoS Aware Scheduler is present and active.";
      type erienmnrmlrat:ddt-Lrat_QciProfilePredefined_pdb;
      default 0;
    }
    leaf rlcSNLength {
      description "Radio Link Control (RLC) Sequence Number length in bits as specified in TS 36.322.";
      yexte:takes-effect "Cell lock/unlock";
      yexte:dependencies "RLC UM must be configured (rlcMode = UM) to set this attribute to 5. RLC AM must be configured (rlcMode = AM) to set this attribute to 16. 16-bit RLC SN is only applied if:\n- extendedRLC-SN-SO-Field-r13 is indicated by UE; and\n- 5CC DL Carrier Aggregation Extension license is enabled; and\n- UE is capable of at least 5CC DL Carrier Aggregation.\nOtherwise, default value of 10-bit RLC SN is applied for RLC AM bearers.";
      type erienmnrmlrat:ddt-Lrat_QciProfilePredefined_rlcSNLength;
      default 10;
    }
    leaf drxPriority {
      description "The relative priority among the DRX profiles, i.e. if the bearer that is setup with this QCI has a higher DRX priority than any of the existing bearers, the DRX configuration will be set to those selected by the drxProfileId for this QCI. The drxPriority has to be unique across all the configured QciProfilePredefined and QciProfileOperatorDefined MOC instances except for instances where the drxProfileId is the same. That is, instances that share the same drxProfileId may have the same drxPriority value. Also note that larger drxPriority values indicate higher relative priority.";
      yexte:disturbances "Changing this attribute can cause loss of traffic. Possible mismatch between DRX setting used by network and UE for ongoing connections.";
      yexte:takes-effect "Object unlocked";
      type erienmnrmlrat:ddt-Lrat_QciProfilePredefined_drxPriority;
      default 0;
    }
    leaf rohcEnabled {
      description "Indicates if Robust Header Compression (ROHC) is enabled.\nNote: Enabling ROHC is only supported for a QCI that is intended to carry RTP/RTCP/UDP based VoIP traffic as for example the standardized QCI1 (3GPP TS 23.203) and not for any other type of traffic.";
      yexte:takes-effect "New connection";
      type boolean;
      default false;
    }
    leaf tReorderingUl {
      description "This timer is used by the receiving end of the Acknowledged Mode (AM) or Unacknowledged Mode (UM) Radio Link Control (RLC) entity in eNB, to detect loss of uplink RLC protocol data units at lower layers.";
      yexte:takes-effect "Cell lock/unlock";
      yexte:dependencies "Not applicable for RLC TM. Only relevant when rlcMode is UM or AM";
      type erienmnrmlrat:ddt-Lrat_QciProfilePredefined_tReorderingUl;
      default 35;
    }
    leaf aqmMode {
      description "Active Queue Management (AQM) mode";
      yexte:takes-effect "Cell lock/unlock";
      type erienmnrmlrat:enum-AQMMode;
      default OFF;
    }
    leaf resourceAllocationStrategy {
      description "Defines the resource allocation strategy of the QoS Class Identifier (QCI).";
      yexte:takes-effect "New connection";
      yexte:dependencies "Only relevant if the licenses for Uplink Frequency Selective Scheduling and QoS Aware Scheduler are present and the features are active.\n";
      type erienmnrmlrat:enum-ResourceAllocationStrategy;
      default RESOURCE_FAIR;
    }
    leaf rlfProfileRef {
      description "Points out the RLF profile associated with this QCI. If not set the default reference will be to the RlfProfile instance corresponding to Local Distinguished Name (LDN) = ManagementElement=1, ENodeBFunction=1, RlfProfile=0.";
      yexte:takes-effect "Object unlocked";
      yexte:dependencies "The RLF profile must exist, otherwise it will be interpreted as default RLF profile.";
      erienmyext:enm-type MOREF;
      type string;
    }
    leaf ulMinBitRate {
      description "The scheduler will attempt to achieve minbitrate for all bearers before giving any user a higher rate. Value 0 means that the minRate scheduler is not used.";
      yexte:disturbances "Changing this attribute can cause loss of traffic.";
      yexte:takes-effect "New connection";
      yexte:dependencies "This parameter will only be used if one of the following Proportional Fair scheduling algorithms, \"maximum_C_over_I\", \"proportional_fair_low\", \"proportional_fair_medium\", \"proportional_fair_high\" or \"equal_rate\", has been selected.\nOnly relevant if the license for QoS Aware Scheduler is present and the feature is active.";
      type erienmnrmlrat:ddt-Lrat_QciProfilePredefined_ulMinBitRate;
      default 0;
    }
    leaf-list reservedBy {
      min-elements 0;
      erienmyext:no-notification;
      config false;
      description "Contains a list of MO instances that reserve this MO instance.";
      erienmyext:enm-type MOREF;
      type string;
    }
    leaf timerPriority {
      description "Relative priority among the timer profiles. TimerProfile with highest priority can be applied for a new connection in case the bearer QCI has an associated TimerProfile.\nIn case several bearers with different QCIs are established, the TimerProfile with highest relative priority is applied.\nThe TimerProfile with lowest QCI number is applied, if TimerProfiles have the same priority,\nLarger timerPriority value indicates higher relative priority.";
      yexte:takes-effect "Object unlocked";
      type erienmnrmlrat:ddt-Lrat_QciProfilePredefined_timerPriority;
      default 0;
    }
    leaf dlMaxHARQTxQci {
      description "Maximum number of transmissions for one HARQ process in DL when this QCI has the highest HARQ priority. Values higher than 7 will be treated as 7.";
      yexte:takes-effect "New connection";
      type erienmnrmlrat:ddt-Lrat_QciProfilePredefined_dlMaxHARQTxQci;
      default 5;
    }
    leaf lessMaxDelayThreshold {
      description "Time delay that scheduling stays on-hold for Low Energy Scheduler Solution.\nIf 0, Low Energy Scheduler Solution is disabled.";
      yexte:takes-effect "New connection";
      type erienmnrmlrat:ddt-Lrat_QciProfilePredefined_lessMaxDelayThreshold;
      default 0;
    }
    leaf timerProfileRef {
      description "Refers to the timer profile associated with this QCI.";
      yexte:takes-effect "Object unlocked";
      erienmyext:enm-type MOREF;
      type string;
    }
    leaf resourceType {
      yexte:restricted;
      description "Indicates if the resource type of the Quality of Service Class Indicator (QCI) is Guaranteed Bit Rate (GBR) or non-GBR as defined in 3GPP TS 23.203.";
      mandatory true;
      yexte:takes-effect "Object unlocked";
      type erienmnrmlrat:enum-ResourceType;
    }
  } // end 'grouping moc-QciProfilePredefined'
  grouping moc-PmchMch-keys {
    description "Key(s) for MOC PmchMch";
    leaf id {
      erienmyext:no-notification;
      description "The value component of the Relative Distinguished Name (RDN).";
      mandatory true;
      yexte:ecim-name pmchMchId;
      type string;
    }
  } // end 'grouping moc-PmchMch-keys'
  grouping moc-PmchMch {
    description "This MO represents configuration related to the Uu physical and transport layers for Multimedia Broadcast Multicast Service (MBMS).";
    leaf userLabel {
      description "Label for free use.";
      type erienmnrmlrat:ddt-Lrat_PmchMch_userLabel;
    }
    leaf syncSequenceLength {
      description "Synchronization sequence length used for MBMS data on the M1 interface.";
      yexte:takes-effect "New connection";
      yexte:dependencies "syncSequenceLength must not exceed mchSchedulingPeriod.";
      type erienmnrmlrat:ddt-Lrat_PmchMch_syncSequenceLength;
      default 8;
    }
    leaf dataMcs {
      description "Specifies the value for parameter I-MCS in TS 36.213, Table 7.1.7.1-1, which defines the Modulation and Coding Scheme (MCS) applicable for the subframes of this (P)MCH as indicated by the field commonSF-Alloc. The MCS does however neither apply to the subframes that may carry MCCH i.e. the subframes indicated by the field sf-AllocInfo within SystemInformationBlockType13 nor for the first subframe of each MCH scheduling period (which may contain the MCH scheduling information provided by MAC).";
      mandatory true;
      yexte:takes-effect "lock/unlock MbsfnArea";
      type erienmnrmlrat:ddt-Lrat_PmchMch_dataMcs;
    }
    leaf-list qci {
      min-elements 0;
      max-elements 10;
      description "QCIs that are supported by this (P)MCH. When Autoconfiguration of LTE Broadcast Subframes is not used, use empty sequence.";
      yexte:disturbances "Can affect traffic if changed. MBMS services can become inconsistent between MBSFN areas.";
      yexte:takes-effect "Object unlocked";
      yexte:precondition "All MbmsService MOs under the PmchMch must be deleted. The corresponding MbsfnArea must have administrative state LOCKED.";
      yexte:dependencies "QCI must be unique value under MbsfnArea.\nQCI and serviceAreaId combination can be set for at most two PmchMch under different MbsfnAreas.\nQCI must not be changed when MbsfnArea is unlocked.\nQCI must not be changed if system-created MO instance exists under any PmchMch MO instance under the MbsfnArea.";
      type erienmnrmlrat:ddt-Lrat_PmchMch_qci;
    }
    leaf sfAllocEnd {
      description "Last subframe allocated to (P)MCH within a period identified by field commonSF-AllocPeriod. If value is 0, the first subframe defined by the field commonSF-Alloc. If Autoconfiguration of LTE Broadcast Subframes is used, new values are set by system every time subframe allocation changes for (P)MCH. If value is -1, no subframe is allocated.";
      yexte:takes-effect "lock/unlock MbsfnArea";
      type erienmnrmlrat:ddt-Lrat_PmchMch_sfAllocEnd;
      default -1;
    }
    leaf mchSchedulingPeriod {
      description "MCH scheduling period. Used to provide MCH scheduling information at applicable lower layers (MAC). Value 8 sets 8 radio frames, 16 sets 16 radio frames and so on.\nValues 512 and 1024 cannot be used.";
      yexte:takes-effect "lock/unlock MbsfnArea";
      yexte:dependencies "mchSchedulingPeriod must be:\n- a multiple of commonSFAllocPeriod in MO class MbsfnArea.\n- smaller than or equal to mcchRepetitionPeriod in MO class MbsfnArea.";
      type erienmnrmlrat:ddt-Lrat_PmchMch_mchSchedulingPeriod;
      default 32;
    }
  } // end 'grouping moc-PmchMch'
  grouping moc-ReportConfigA5SoftLock-keys {
    description "Key(s) for MOC ReportConfigA5SoftLock";
    leaf id {
      erienmyext:no-notification;
      description "The value component of the RDN.";
      mandatory true;
      yexte:ecim-name reportConfigA5SoftLockId;
      type string;
    }
  } // end 'grouping moc-ReportConfigA5SoftLock-keys'
  grouping moc-ReportConfigA5SoftLock {
    description "Contains the Report Configuration settings for the A5 event measurements initiated for Soft-Lock of Cell.\n\nThe RDN of this MO is ReportConfigA5SoftLock=1.";
    leaf a5Threshold2Rsrp {
      description "RSRP threshold2 value for eventA5.";
      type erienmnrmlrat:ddt-Lrat_ReportConfigA5SoftLock_a5Threshold2Rsrp;
      default -140;
    }
  } // end 'grouping moc-ReportConfigA5SoftLock'
  grouping moc-ReportConfigB1Geran-keys {
    description "Key(s) for MOC ReportConfigB1Geran";
    leaf id {
      erienmyext:no-notification;
      description "The value component of the Relative Distinguished Name (RDN).";
      mandatory true;
      yexte:ecim-name reportConfigB1GeranId;
      type string;
    }
  } // end 'grouping moc-ReportConfigB1Geran-keys'
  grouping moc-ReportConfigB1Geran {
    description "This managed object contains report configuration settings for the B1 event for GERAN measurements. The B1 event is used to detect when a GERAN cell becomes better than threshold.\n\nThe RDN of this MO is ReportConfigB1Geran=1.";
    leaf timeToTriggerB1 {
      description "The time to trigger value for the eventB1 measurement.";
      yexte:takes-effect "New connection";
      type erienmnrmlrat:ddt-Lrat_ReportConfigB1Geran_timeToTriggerB1;
      default 640;
    }
    leaf hysteresisB1 {
      description "The hysteresis value for the eventB1 measurement on GERAN";
      yexte:takes-effect "New connection";
      type erienmnrmlrat:ddt-Lrat_ReportConfigB1Geran_hysteresisB1;
      default 10;
    }
    leaf b1ThresholdGeran {
      description "The Signal Quality in the ThresholdGERAN, threshold value for eventB1.";
      yexte:takes-effect "New connection";
      type erienmnrmlrat:ddt-Lrat_ReportConfigB1Geran_b1ThresholdGeran;
      default -110;
    }
  } // end 'grouping moc-ReportConfigB1Geran'
  grouping moc-GeranCellRelation-keys {
    description "Key(s) for MOC GeranCellRelation";
    leaf id {
      erienmyext:no-notification;
      description "The value component of the Relative Distinguished Name (RDN).";
      mandatory true;
      yexte:ecim-name geranCellRelationId;
      type string;
    }
  } // end 'grouping moc-GeranCellRelation-keys'
  grouping moc-GeranCellRelation {
    description "This Managed Object represents a mobility relation between an EUtranCellFDD or an EUtranCellTDD and a GeranCell. It contains parameters that are specific for this relation";
    leaf isHoAllowed {
      description "This attribute specifies if handover between the cells in this relation is allowed.";
      yexte:disturbances "Changing this attribute to false stops outgoing HO.";
      type boolean;
      default true;
    }
    leaf createdBy {
      config false;
      description "Indicates whether the MO has been created by the Automated Neighbor Relations (ANR) function or operator.";
      notife:notifiable-state-data true;
      type erienmnrmlrat:enum-CreatedByIrat;
    }
    leaf isRemoveAllowed {
      description "Indicates if the Automated Neighbor Relations (ANR) function is allowed to remove this object. It does not restrict operator removal of the object. Objects created by ANR have this parameter set to true initially.";
      type boolean;
      default false;
    }
    leaf timeOfCreation {
      config false;
      description "Indicates the date and time when the MO was created by the Automated Neighbor Relations (ANR) function or operator. Format: YYYY-MM-DD HH:MM:SS";
      notife:notifiable-state-data true;
      type erienmnrmlrat:ddt-Lrat_GeranCellRelation_timeOfCreation;
    }
    leaf lastModification {
      config false;
      description "Indicates whether the MO has been last modified by the Automated Neighbor Relations (ANR) function or operator.";
      notife:notifiable-state-data true;
      type erienmnrmlrat:enum-LastModificationGeran;
    }
    leaf extGeranCellRef {
      yexte:restricted;
      description "Reference to ExternalGeranCell  instance.\nAt MO creation, it is mandatory to supply a valid reference to an ExternalGeranCell.";
      erienmyext:enm-type MOREF;
      type string;
    }
    container mobilityStatus {
      description "Mobility status information. When struct member mobilityStatus.available is set to false, no HO is performed on cell relation. Reason why HO is not allowed is shown on mobilityStatus.reason.";
      erienmyext:enm-type STRUCT;
      uses erienmnrmlrat:struct-MobilityStatusIratRO;
    } // end 'container mobilityStatus'
    leaf coverageIndicator {
      description "Defines whether the coverage area of the EUTRAN cell and the GERAN cell are indicated to overlap (has approximately the same coverage area), or whether the coverage area of the GERAN cell is indicated to cover the EUTRAN cell, or if it is contained in the EUTRAN cell.";
      yexte:disturbances "Changes may affect traffic";
      type erienmnrmlrat:enum-SupportedCoverage;
      default NONE;
    }
    leaf timeOfLastModification {
      config false;
      description "The date and time when the MO was last modified by the Automated Neighbor Relations (ANR) function or operator. Format: YYYY-MM-DD HH:MM:SS";
      notife:notifiable-state-data true;
      type erienmnrmlrat:ddt-Lrat_GeranCellRelation_timeOfLastModification;
    }
  } // end 'grouping moc-GeranCellRelation'
  grouping moc-PmFlexCounterFilter-keys {
    description "Key(s) for MOC PmFlexCounterFilter";
    leaf id {
      erienmyext:no-notification;
      description "The value component of the RDN.";
      mandatory true;
      yexte:ecim-name pmFlexCounterFilterId;
      type string;
    }
  } // end 'grouping moc-PmFlexCounterFilter-keys'
  grouping moc-PmFlexCounterFilter {
    description "Filter parameters applied to the flexible counters. Same filter combinations between instances of this class are not allowed.";
    leaf qciFilterMin {
      description "Minimum filter value applied to QCI. Only valid if attribute qciFilterEnabled is enabled.";
      yexte:takes-effect "Next ROP";
      yexte:dependencies "qciFilterMin <= qciFilterMax";
      type erienmnrmlrat:ddt-Lrat_PmFlexCounterFilter_qciFilterMin;
      default 0;
    }
    leaf plmnFilterMin {
      description "Minimum filter value applied to PLMN Index. Only valid if attribute plmnFilterEnabled is enabled.";
      yexte:takes-effect "Next ROP";
      yexte:dependencies "plmnFilterMin <= plmnFilterMax";
      type erienmnrmlrat:ddt-Lrat_PmFlexCounterFilter_plmnFilterMin;
      default 0;
    }
    leaf pviFilterMax {
      description "Maximum filter value applied to PVI.";
      yexte:takes-effect "Next ROP";
      yexte:dependencies "pviFilterMin <= pviFilterMax. Only valid if attribute pviFilterEnabled is enabled.";
      type erienmnrmlrat:enum-PreemptionVulnerability;
      default NOT_PREEMPTABLE;
    }
    leaf lcgFilterMax {
      description "Maximum filter value applied to LCG. Only valid if attribute lcgFilterEnabled is enabled.";
      yexte:takes-effect "Next ROP";
      yexte:dependencies "lcgFilterMin <= lcgFilterMax";
      type erienmnrmlrat:ddt-Lrat_PmFlexCounterFilter_lcgFilterMax;
      default 0;
    }
    leaf ceLevelFilterEnabled {
      description "Whether or not bandwidth reduced PRACH Coverage Enhancement (CE) Level filter is enabled.";
      yexte:takes-effect "Next ROP";
      type boolean;
      default false;
    }
    leaf arpFilterEnabled {
      description "Whether or not ARP filter is enabled.";
      yexte:takes-effect "Next ROP";
      type boolean;
      default false;
    }
    leaf uePowerClassFilterEnabled {
      description "Whether or not UE Power Class filter is enabled.";
      yexte:takes-effect "Next ROP";
      type boolean;
      default false;
    }
    leaf endcFilterEnabled {
      description "Enables ENDC filter.";
      yexte:takes-effect "Next ROP";
      yexte:dependencies "Only applicable in Baseband Radio Node.";
      type boolean;
      default false;
    }
    leaf spidFilterMax {
      description "Maximum filter value applied to SPID. Only valid if attribute spidFilterEnabled is enabled.";
      yexte:takes-effect "Next ROP";
      yexte:dependencies "spidFilterMin <= spidFilterMax";
      type erienmnrmlrat:ddt-Lrat_PmFlexCounterFilter_spidFilterMax;
      default 1;
    }
    leaf counterNameSuffix {
      erienmyext:no-notification;
      config false;
      description "Name string that is appended to the flexible counters representing filter combination applied to current ROP.";
      type string;
    }
    leaf subscriberGroupFilterMin {
      description "Minimum filter value applied to subscriber group profile index. Only valid if attribute subscriberGroupFilterEnabled is enabled.";
      yexte:takes-effect "Next ROP";
      yexte:dependencies "subscriberGroupFilterMin <= subscriberGroupFilterMax";
      type erienmnrmlrat:ddt-Lrat_PmFlexCounterFilter_subscriberGroupFilterMin;
      default 0;
    }
    leaf ceLevelEnabled {
      status deprecated {
        yexte:status-information "Since 17.Q2. Replaced by ceLevelFilterEnabled. Planned to be removed.";
      }
      description "Whether or not CE Level filter is enabled.";
      yexte:takes-effect "Next ROP";
      type boolean;
      default false;
    }
    leaf ueCatFilterMin {
      description "Minimum filter value applied to UE Category. Only valid if attribute ueCatFilterEnabled is enabled.";
      yexte:takes-effect "Next ROP";
      yexte:dependencies "ueCatFilterMin <= ueCatFilterMax";
      type erienmnrmlrat:enum-UeCategory;
      default UE_CATEGORY_DL_M1_UL_M1;
    }
    leaf lcgFilterMin {
      description "Minimum filter value applied to LCG. Only valid if attribute lcgFilterEnabled is enabled.";
      yexte:takes-effect "Next ROP";
      yexte:dependencies "lcgFilterMin <= lcgFilterMax";
      type erienmnrmlrat:ddt-Lrat_PmFlexCounterFilter_lcgFilterMin;
      default 0;
    }
    leaf spidFilterEnabled {
      description "Whether or not SPID filter is enabled.";
      yexte:takes-effect "Next ROP";
      type boolean;
      default false;
    }
    leaf qciFilterMax {
      description "Maximum filter value applied to QCI. Only valid if attribute qciFilterEnabled is enabled.";
      yexte:takes-effect "Next ROP";
      yexte:dependencies "qciFilterMin <= qciFilterMax";
      type erienmnrmlrat:ddt-Lrat_PmFlexCounterFilter_qciFilterMax;
      default 0;
    }
    leaf uePowerClassFilterMax {
      description "Maximum filter value applied to UE Power Class. Only valid if attribute uePowerClassFilterEnabled is true.";
      yexte:takes-effect "Next ROP";
      yexte:dependencies "uePowerClassFilterMin <= uePowerClassFilterMax";
      type erienmnrmlrat:ddt-Lrat_PmFlexCounterFilter_uePowerClassFilterMax;
      default 1;
    }
    leaf pciFilterEnabled {
      description "Whether PCI filter is enabled.";
      yexte:takes-effect "Next ROP";
      type boolean;
      default false;
    }
    leaf plmnFilterEnabled {
      description "Whether or not PLMN filter is enabled.";
      yexte:takes-effect "Next ROP";
      type boolean;
      default false;
    }
    leaf spidFilterMin {
      description "Minimum filter value applied to SPID. Only valid if attribute spidFilterEnabled is enabled.";
      yexte:takes-effect "Next ROP";
      yexte:dependencies "spidFilterMin <= spidFilterMax";
      type erienmnrmlrat:ddt-Lrat_PmFlexCounterFilter_spidFilterMin;
      default 1;
    }
    leaf lcgFilterEnabled {
      description "Whether or not LCG filter is enabled.";
      yexte:takes-effect "Next ROP";
      type boolean;
      default false;
    }
    leaf subscriberGroupFilterMax {
      description "Maximum filter value applied to subscriber group profile index. Only valid if attribute subscriberGroupFilterEnabled is enabled.";
      yexte:takes-effect "Next ROP";
      yexte:dependencies "subscriberGroupFilterMin <= subscriberGroupFilterMax";
      type erienmnrmlrat:ddt-Lrat_PmFlexCounterFilter_subscriberGroupFilterMax;
      default 0;
    }
    leaf arpFilterMax {
      description "Maximum filter value applied to ARP. Only valid if attribute arpFilterEnabled is enabled.";
      yexte:takes-effect "Next ROP";
      yexte:dependencies "arpFilterMin <= arpFilterMax";
      type erienmnrmlrat:ddt-Lrat_PmFlexCounterFilter_arpFilterMax;
      default 0;
    }
    leaf ceLevelFilterMin {
      description "Minimum filter value applied to bandwidth reduced PRACH Coverage Enhancement (CE) Level. Only valid if attribute ceLevelFilterEnabled is enabled.";
      yexte:takes-effect "Next ROP";
      yexte:dependencies "ceLevelFilterMin <= ceLevelFilterMax";
      type erienmnrmlrat:enum-CeLevel;
      default CE_LEVEL_0;
    }
    leaf endcFilterMin {
      description "Minimum ENDC filter value.";
      yexte:takes-effect "Next ROP";
      yexte:dependencies "Only valid if endcFilterEnabled is enabled. Value of endcFilterMin must be lower than endcFilterMax.";
      type erienmnrmlrat:enum-EndcStage;
      default ENDC_NR_CAPABLE;
    }
    leaf subscriberGroupFilterEnabled {
      description "Whether or not operator-defined subscriber group filter is enabled.";
      yexte:takes-effect "Next ROP";
      type boolean;
      default false;
    }
    leaf ueCatFilterEnabled {
      description "Whether or not UE Category filter is enabled.";
      yexte:takes-effect "Next ROP";
      type boolean;
      default false;
    }
    leaf ueCatFilterMax {
      description "Maximum filter value applied to UE Category. Only valid if attribute ueCatFilterEnabled is enabled.";
      yexte:takes-effect "Next ROP";
      yexte:dependencies "ueCatFilterMin <= ueCatFilterMax";
      type erienmnrmlrat:enum-UeCategory;
      default UE_CATEGORY_DL_M1_UL_M1;
    }
    leaf pciFilterMax {
      description "Maximum filter value applied to PCI.";
      yexte:takes-effect "Next ROP";
      yexte:dependencies "pciFilterMin <= pciFilterMax. Only valid if attribute pciFilterEnabled is enabled.";
      type erienmnrmlrat:enum-PreemptionCapability;
      default SHALL_NOT_TRIGGER_PREEMPTION;
    }
    leaf qciFilterEnabled {
      description "Whether or not QCI filter is enabled.";
      yexte:takes-effect "Next ROP";
      type boolean;
      default false;
    }
    leaf endcFilterMax {
      config false;
      description "Maximum ENDC filter value. Always equals ENDC_UE_RELEASED.";
      yexte:dependencies "Only valid if endcFilterEnabled is enabled. Value of endcFilterMin must be lower than endcFilterMax.";
      notife:notifiable-state-data true;
      type erienmnrmlrat:enum-EndcStage;
    }
    leaf reportAppCounterOnly {
      description "Whether or not only applicable sub flexible counters are reported in ROP files.";
      yexte:takes-effect "Next ROP";
      type boolean;
      default true;
    }
    leaf uePowerClassFilterMin {
      description "Minimum filter value applied to UE Power Class. Only valid if attribute uePowerClassFilterEnabled is true.";
      yexte:takes-effect "Next ROP";
      yexte:dependencies "uePowerClassFilterMin <= uePowerClassFilterMax";
      type erienmnrmlrat:ddt-Lrat_PmFlexCounterFilter_uePowerClassFilterMin;
      default 1;
    }
    leaf arpFilterMin {
      description "Minimum filter value applied to ARP. Only valid if attribute arpFilterEnabled is enabled.";
      yexte:takes-effect "Next ROP";
      yexte:dependencies "arpFilterMin <= arpFilterMax";
      type erienmnrmlrat:ddt-Lrat_PmFlexCounterFilter_arpFilterMin;
      default 0;
    }
    leaf pviFilterEnabled {
      description "Whether PVI filter is enabled.";
      yexte:takes-effect "Next ROP";
      type boolean;
      default false;
    }
    leaf ceLevelFilterMax {
      description "Maximum filter value applied to bandwidth reduced PRACH Coverage Enhancement (CE) Level. Only valid if attribute ceLevelFilterEnabled is enabled.";
      yexte:takes-effect "Next ROP";
      yexte:dependencies "ceLevelFilterMin <= ceLevelFilterMax";
      type erienmnrmlrat:enum-CeLevel;
      default CE_LEVEL_0;
    }
    leaf plmnFilterMax {
      description "Maximum filter value applied to PLMN Index. Only valid if attribute plmnFilterEnabled is enabled.";
      yexte:takes-effect "Next ROP";
      yexte:dependencies "plmnFilterMin <= plmnFilterMax";
      type erienmnrmlrat:ddt-Lrat_PmFlexCounterFilter_plmnFilterMax;
      default 0;
    }
    leaf pciFilterMin {
      description "Minimum filter value applied to PCI.";
      yexte:takes-effect "Next ROP";
      yexte:dependencies "pciFilterMin <= pciFilterMax. Only valid if attribute pciFilterEnabled is enabled.";
      type erienmnrmlrat:enum-PreemptionCapability;
      default SHALL_NOT_TRIGGER_PREEMPTION;
    }
    leaf pviFilterMin {
      description "Minimum filter value applied to PVI.";
      yexte:takes-effect "Next ROP";
      yexte:dependencies "pviFilterMin <= pviFilterMax. Only valid if attribute pviFilterEnabled is enabled.";
      type erienmnrmlrat:enum-PreemptionVulnerability;
      default NOT_PREEMPTABLE;
    }
  } // end 'grouping moc-PmFlexCounterFilter'
  grouping moc-ReportConfigB2Cdma2000-keys {
    description "Key(s) for MOC ReportConfigB2Cdma2000";
    leaf id {
      erienmyext:no-notification;
      description "The value component of the Relative Distinguished Name (RDN).";
      mandatory true;
      yexte:ecim-name reportConfigB2Cdma2000Id;
      type string;
    }
  } // end 'grouping moc-ReportConfigB2Cdma2000-keys'
  grouping moc-ReportConfigB2Cdma2000 {
    description "This managed object contains report configuration settings for the B2 event for CDMA2000 measurements. The B2 event is used to detect when a CDMA2000 cell becomes better than threshold2, and serving cell becomes worse than threshold1. The actual threshold values used can be adjusted by frequency relation related offsets if the feature Multi-Layer Service-Triggered Mobility (MLSTM) is enabled.\n\nThe RDN of this MO is ReportConfigB2Cdma2000=1.";
    leaf b2Threshold1Rsrp {
      description "The Reference Signal Received Power (RSRP) threshold1 value for eventB2.";
      yexte:takes-effect "New connection";
      yexte:dependencies "Only used if triggerQuantityB2 is set to RSRP.";
      type erienmnrmlrat:ddt-Lrat_ReportConfigB2Cdma2000_b2Threshold1Rsrp;
      default -140;
    }
    leaf b2Threshold1Rsrq {
      description "The Reference Signal Received Quality (RSRQ) threshold1 value for eventB2.";
      yexte:takes-effect "New connection";
      yexte:dependencies "Only used if triggerQuantityB2 is set to RSRQ.";
      type erienmnrmlrat:ddt-Lrat_ReportConfigB2Cdma2000_b2Threshold1Rsrq;
      default -195;
    }
    leaf b2Threshold2Cdma2000 {
      description "The Signal Quality in the thresholdCDMA2000, threshold2 value for eventB2.";
      yexte:takes-effect "New connection";
      type erienmnrmlrat:ddt-Lrat_ReportConfigB2Cdma2000_b2Threshold2Cdma2000;
      default -75;
    }
    leaf triggerQuantityB2 {
      description "The quantity for threshold1 (serving EUTRAN cell) that is sent to the UE, and is used together with threshold2 to trigger the eventB2.";
      yexte:takes-effect "New connection";
      type erienmnrmlrat:enum-TriggerQuantity;
      default RSRP;
    }
    leaf hysteresisB2RsrqOffset {
      description "Offset to obtain the Hysteresis for B2 measurement for trigger quantity RSRQ. hysteresisB2Rsrq = hysteresisB2 + hysteresisB2RsrqOffset";
      yexte:takes-effect "New connection";
      yexte:dependencies "Feature Mobility Control at Poor Coverage must be active.";
      type erienmnrmlrat:ddt-Lrat_ReportConfigB2Cdma2000_hysteresisB2RsrqOffset;
      default 0;
    }
    leaf timeToTriggerB2Rsrq {
      description "Time-to-trigger value for event B2 with trigger quantity RSRQ. If set to -1, attribute is not used for report configuration.";
      yexte:takes-effect "New connection";
      yexte:dependencies "Feature Mobility Control at Poor Coverage must be active.";
      type erienmnrmlrat:ddt-Lrat_ReportConfigB2Cdma2000_timeToTriggerB2Rsrq;
      default -1;
    }
    leaf hysteresisB2 {
      description "The hysteresis value for the eventB2 measurement";
      yexte:takes-effect "New connection";
      type erienmnrmlrat:ddt-Lrat_ReportConfigB2Cdma2000_hysteresisB2;
      default 10;
    }
    leaf timeToTriggerB2 {
      description "Time-to-trigger value for event B2 measurements. If timeToTriggerB2Rsrq is -1, this attribute is used for both RSRP and RSRQ. But if not set to -1, this attribute is used only for RSRP.";
      yexte:takes-effect "New connection";
      type erienmnrmlrat:ddt-Lrat_ReportConfigB2Cdma2000_timeToTriggerB2;
      default 640;
    }
  } // end 'grouping moc-ReportConfigB2Cdma2000'
  grouping moc-PlmnAbConfProfile-keys {
    description "Key(s) for MOC PlmnAbConfProfile";
    leaf id {
      erienmyext:no-notification;
      description "The value component of the RDN.";
      mandatory true;
      yexte:ecim-name plmnAbConfProfileId;
      type string;
    }
  } // end 'grouping moc-PlmnAbConfProfile-keys'
  grouping moc-PlmnAbConfProfile {
    description "Access Barring configuration for PLMN.";
    leaf acBarringSkipForMmtelVoice {
      description "Whether access attempts for MMTEL voice from UEs skip Access Class Barring functionality.";
      yexte:disturbances "Changing this attribute can block VoLTE calls.";
      type boolean;
      default false;
    }
    leaf acBarringForMmtelVidPres {
      description "Presence of PLMN AB Mmtel Video configuration in SIB2.";
      yexte:disturbances "Changing this attribute can cause loss of traffic.";
      type erienmnrmlrat:enum-AcBarringMode;
      default OFF;
    }
    container ssacBarringForMmtelVideo {
      description "Service-specific Access Class Barring parameters for MMTEL video originating calls.\nInformation is broadcast in SIB2.";
      erienmyext:enm-type STRUCT;
      uses erienmnrmlrat:struct-AcBarringConfig;
    } // end 'container ssacBarringForMmtelVideo'
    leaf acBarringForMoDataPresence {
      description "Presence of PLMN AB Mo Data configuration in SIB2.";
      yexte:disturbances "Changing this attribute can cause loss of traffic.";
      type erienmnrmlrat:enum-AcBarringMode;
      default OFF;
    }
    leaf acBarringSkipForSms {
      description "Whether access attempts for SMS over SGs or SMS over IP from UEs skip Access Class Barring.";
      yexte:disturbances "Changing this attribute can block sms.";
      type boolean;
      default false;
    }
    container acBarringPlmnId {
      description "PLMN ID for which Access Barring configuration is provided.\n";
      erienmyext:enm-type STRUCT;
      uses erienmnrmlrat:struct-PlmnIdentity;
    } // end 'container acBarringPlmnId'
    container ssacBarringForMmtelVoice {
      description "Service-specific Access Class Barring parameters for MMTEL voice originating calls.\nInformation is broadcast in SIB2.";
      erienmyext:enm-type STRUCT;
      uses erienmnrmlrat:struct-AcBarringConfig;
    } // end 'container ssacBarringForMmtelVoice'
    leaf acBarringForCsfbPresence {
      description "Presence of PLMN AB Csfb configuration in SIB2.";
      yexte:disturbances "Changing this attribute can cause loss of traffic.";
      type erienmnrmlrat:enum-AcBarringMode;
      default OFF;
    }
    container acBarringForMoData {
      description "Access Class Barring parameters for mobile originating calls.\nInformation is broadcast in SIB2.";
      erienmyext:enm-type STRUCT;
      uses erienmnrmlrat:struct-AcBarringConfig;
    } // end 'container acBarringForMoData'
    leaf acBarringForMmtelVoicePres {
      description "Presence of PLMN AB Mmtel Voice configuration in SIB2.";
      yexte:disturbances "Changing this attribute can cause loss of traffic.";
      type erienmnrmlrat:enum-AcBarringMode;
      default OFF;
    }
    leaf acBarringSkipForMmtelVideo {
      description "Whether access attempts for MMTEL video from UEs skip Access Class Barring functionality.";
      yexte:disturbances "Changing this attribute can block Video calls.";
      type boolean;
      default false;
    }
    leaf-list reservedBy {
      min-elements 0;
      config false;
      description "List of MO instances that reserve this MO instance.";
      yexte:dependencies "MO can not be deleted if it is reserved.";
      notife:notifiable-state-data true;
      erienmyext:enm-type MOREF;
      type string;
    }
    container acBarringForMoSignalling {
      description "Access Class Barring parameters for mobile originating signalling.\nInformation is broadcast in SIB2.";
      erienmyext:enm-type STRUCT;
      uses erienmnrmlrat:struct-AcBarringConfig;
    } // end 'container acBarringForMoSignalling'
    leaf acBarringForEmergency {
      description "Access Class Barring for emergency, corresponds to access class 10.\nInformation is broadcast in SIB2.";
      yexte:disturbances "Changing this attribute can block emergency calls.";
      type boolean;
      default false;
    }
    container acBarringForCsfb {
      description "Access Class Barring parameters for mobile originating CSFB calls.\nInformation is broadcast in SIB2.";
      erienmyext:enm-type STRUCT;
      uses erienmnrmlrat:struct-AcBarringConfig;
    } // end 'container acBarringForCsfb'
    leaf acBarringPerPlmnPriority {
      description "Priority Level of PLMN ID used by PLMN-Specific Access Barring algorithm.";
      yexte:disturbances "Changing this attribute can cause loss of traffic.";
      type erienmnrmlrat:enum-AcBarringPlmnPriorityLevel;
      default PRIORITY0;
    }
    leaf acBarringForMoSignalPresence {
      description "Presence of PLMN AB Mo Signaling configuration in SIB2.";
      yexte:disturbances "Changing this attribute can cause loss of traffic.";
      type erienmnrmlrat:enum-AcBarringMode;
      default OFF;
    }
  } // end 'grouping moc-PlmnAbConfProfile'
  grouping moc-UtranCellRelation-keys {
    description "Key(s) for MOC UtranCellRelation";
    leaf id {
      erienmyext:no-notification;
      description "The value component of the Relative Distinguished Name (RDN).";
      mandatory true;
      yexte:ecim-name utranCellRelationId;
      type string;
    }
  } // end 'grouping moc-UtranCellRelation-keys'
  grouping moc-UtranCellRelation {
    description "This Managed Object represents a mobility relation between an EUtranCellFDD or an EUtranCellTDD and an UtranCell. It contains parameters that are specific for this relation";
    leaf isHoAllowed {
      description "Specifies if handover between the cells in this relation is allowed.";
      yexte:disturbances "Changing this attribute to false stops outgoing HO.";
      type boolean;
      default true;
    }
    leaf timeOfCreation {
      config false;
      description "Indicates the time and date when the MO was created by the Automated Neighbor Relations (ANR) function or operator. Format: YYYY-MM-DD HH:MM:SS";
      notife:notifiable-state-data true;
      type erienmnrmlrat:ddt-Lrat_UtranCellRelation_timeOfCreation;
    }
    leaf lbCovIndicated {
      description "Determines if the cell relation has high hitRate towards the source cell.";
      type boolean;
      default false;
    }
    leaf loadBalancing {
      description "Load balancing\nThe value specifies whether load balancing action to the referenced target UTRAN cell is allowed.";
      type erienmnrmlrat:enum-UtranLoadBalancingVals;
      default NOT_ALLOWED;
    }
    leaf timeOfLastModification {
      config false;
      description "The date and time when the MO was last modified by the Automated Neighbor Relations (ANR) function or operator. Format: YYYY-MM-DD HH:MM:SS";
      notife:notifiable-state-data true;
      type erienmnrmlrat:ddt-Lrat_UtranCellRelation_timeOfLastModification;
    }
    leaf externalUtranCellFDDRef {
      yexte:restricted;
      description "Reference to the external UTRAN FDD/TDD cell MO.";
      mandatory true;
      erienmyext:enm-type MOREF;
      type string;
    }
    leaf createdBy {
      config false;
      description "Indicates whether the MO has been created by the Automated Neighbor Relations (ANR) function or operator.";
      notife:notifiable-state-data true;
      type erienmnrmlrat:enum-CreatedByIrat;
    }
    leaf isRemoveAllowed {
      description "Indicates if the Automated Neighbor Relations (ANR) function is allowed to remove this object. It does not restrict operator removal of the object. Objects created by ANR have this parameter set to true initially.";
      type boolean;
      default false;
    }
    leaf lastModification {
      config false;
      description "Indicates whether the MO has been last modified by the Automated Neighbor Relations (ANR) function or operator.";
      notife:notifiable-state-data true;
      type erienmnrmlrat:enum-LastModificationUtran;
    }
    leaf lbBnrAllowed {
      description "Specifies if the feature Best Neighbor Relations for WCDMA IRAT Offload is allowed to automatically change the loadBalancing attribute for this Utran cell relation.";
      type boolean;
      default true;
    }
    container mobilityStatus {
      description "Mobility status information. When struct member mobilityStatus.available is set to false, no HO is performed on cell relation. Reason why HO is not allowed is shown on mobilityStatus.reason.";
      erienmyext:enm-type STRUCT;
      uses erienmnrmlrat:struct-MobilityStatusIratRO;
    } // end 'container mobilityStatus'
    leaf coverageIndicator {
      description "Defines whether the coverage areas of the EUTRAN cell and the UTRAN FDD/TDD cell are indicated to overlap (have approximately the same coverage area), or whether the coverage area of the UTRAN FDD/TDD cell is indicated to cover the EUTRAN cell, or if it is contained in the EUTRAN cell.";
      yexte:disturbances "Changes may affect traffic";
      type erienmnrmlrat:enum-SupportedCoverage;
      default NONE;
    }
  } // end 'grouping moc-UtranCellRelation'
  grouping moc-ReportConfigElcA1A2-keys {
    description "Key(s) for MOC ReportConfigElcA1A2";
    leaf id {
      erienmyext:no-notification;
      description "The value component of the RDN.";
      mandatory true;
      yexte:ecim-name reportConfigElcA1A2Id;
      type string;
    }
  } // end 'grouping moc-ReportConfigElcA1A2-keys'
  grouping moc-ReportConfigElcA1A2 {
    description "Contains the report configuration settings for A1/A2 measurements initiated by Ericsson Lean Carrier.\n\nThe RDN of this MO is ReportConfigElcA1A2=1.";
    leaf timeToTriggerA2 {
      description "Time-to-trigger value for measurement in event A2.";
      yexte:takes-effect "New connection";
      type erienmnrmlrat:ddt-Lrat_ReportConfigElcA1A2_timeToTriggerA2;
      default 40;
    }
    leaf hysteresisA1A2Rsrp {
      description "Hysteresis value for RSRP in events A1 and A2 measurements.";
      yexte:takes-effect "New connection";
      type erienmnrmlrat:ddt-Lrat_ReportConfigElcA1A2_hysteresisA1A2Rsrp;
      default 10;
    }
    leaf timeToTriggerA1 {
      description "Time-to-trigger value for measurement in event A1.";
      yexte:takes-effect "New connection";
      type erienmnrmlrat:ddt-Lrat_ReportConfigElcA1A2_timeToTriggerA1;
      default 40;
    }
    leaf a1a2ThresholdRsrp {
      description "RSRP threshold value for events A1 and A2.";
      yexte:takes-effect "New connection";
      type erienmnrmlrat:ddt-Lrat_ReportConfigElcA1A2_a1a2ThresholdRsrp;
      default -134;
    }
  } // end 'grouping moc-ReportConfigElcA1A2'
  grouping moc-MACConfiguration-keys {
    description "Key(s) for MOC MACConfiguration";
    leaf id {
      erienmyext:no-notification;
      description "The value component of the RDN.";
      mandatory true;
      yexte:ecim-name mACConfigurationId;
      type string;
    }
  } // end 'grouping moc-MACConfiguration-keys'
  grouping moc-MACConfiguration {
    description "MAC configuration.\n\nThe RDN of this MO is MACConfiguration=1.";
    leaf ulMaxHARQTx {
      description "Maximum number of transmissions for one HARQ process in UL.\n";
      yexte:disturbances "Changing this attribute can cause loss of traffic.";
      yexte:takes-effect "New connection.";
      yexte:dependencies "Overridden by ulTtiBundlingMaxHARQTx when UE is in TTI Bundling mode. TTI bundling mode occurs only when feature TTI Bundling is active.";
      type erienmnrmlrat:ddt-Lrat_MACConfiguration_ulMaxHARQTx;
      default 4;
    }
    leaf dlMaxHARQTx {
      description "Maximum number of transmissions for one HARQ process in DL. Values higher than 7 will be treated as 7.";
      yexte:takes-effect "New connection.";
      type erienmnrmlrat:ddt-Lrat_MACConfiguration_dlMaxHARQTx;
      default 4;
    }
    leaf ulTtiBundlingMaxHARQTx {
      description "Maximum number of transmissions for one HARQ process in UL when UE is in TTI Bundling mode.";
      yexte:takes-effect "New connection";
      yexte:dependencies "Valid only when feature TTI Bundling is active. Overrides ulMaxHARQTx when UE is in TTI Bundling mode.";
      type erienmnrmlrat:ddt-Lrat_MACConfiguration_ulTtiBundlingMaxHARQTx;
      default 4;
    }
  } // end 'grouping moc-MACConfiguration'
  grouping moc-Band46UnlicensedProfile-keys {
    description "Key(s) for MOC Band46UnlicensedProfile";
    leaf id {
      status deprecated {
        yexte:status-information "Since 17.Q2. Has no functional behavior. Planned to be removed.";
      }
      erienmyext:no-notification;
      description "The value component of the RDN.";
      mandatory true;
      yexte:precondition Band46UnlicensedProfile;
      yexte:ecim-name band46UnlicensedProfileId;
      type string;
    }
  } // end 'grouping moc-Band46UnlicensedProfile-keys'
  grouping moc-Band46UnlicensedProfile {
    description "Contains information about the regulatory requirements for each frequency in Band 46.";
    leaf b46C51290MaxPower {
      status deprecated {
        yexte:status-information "Since 17.Q2. Has no functional behavior. Planned to be removed.";
      }
      description "The maximum allowed transmission power on EARFCN 51290 (46C). Corresponds to Wi-Fi channel 120.";
      yexte:precondition Band46UnlicensedProfile;
      type erienmnrmlrat:ddt-Lrat_Band46UnlicensedProfile_b46C51290MaxPower;
      default 0;
    }
    leaf b46B48290MaxPower {
      status deprecated {
        yexte:status-information "Since 17.Q2. Has no functional behavior. Planned to be removed.";
      }
      description "The maximum allowed transmission power on EARFCN 48290 (46B). Corresponds to Wi-Fi channel 60.";
      yexte:precondition Band46UnlicensedProfile;
      type erienmnrmlrat:ddt-Lrat_Band46UnlicensedProfile_b46B48290MaxPower;
      default 0;
    }
    leaf b46C50290Allowed {
      status deprecated {
        yexte:status-information "Since 17.Q2. Has no functional behavior. Planned to be removed.";
      }
      description "Is EARFCN 50290 (46C) allowed for transmission. Corresponds to Wi-Fi channel 100.";
      yexte:precondition Band46UnlicensedProfile;
      type erienmnrmlrat:enum-B46ChannelUsage;
      default CHANNEL_DISABLED;
    }
    leaf b46A47690MaxPower {
      status deprecated {
        yexte:status-information "Since 17.Q2. Has no functional behavior. Planned to be removed.";
      }
      description "The maximum allowed transmission power on EARFCN 47690 (46A). Corresponds to Wi-Fi channel 48.";
      yexte:precondition Band46UnlicensedProfile;
      type erienmnrmlrat:ddt-Lrat_Band46UnlicensedProfile_b46A47690MaxPower;
      default 0;
    }
    leaf b46C50890Allowed {
      status deprecated {
        yexte:status-information "Since 17.Q2. Has no functional behavior. Planned to be removed.";
      }
      description "Is EARFCN 50890 (46C) allowed for transmission. Corresponds to Wi-Fi channel 112.";
      yexte:precondition Band46UnlicensedProfile;
      type erienmnrmlrat:enum-B46ChannelUsage;
      default CHANNEL_DISABLED;
    }
    leaf b46D54340MaxPower {
      status deprecated {
        yexte:status-information "Since 17.Q2. Has no functional behavior. Planned to be removed.";
      }
      description "The maximum allowed transmission power on EARFCN 54340 (46D).";
      yexte:precondition Band46UnlicensedProfile;
      type erienmnrmlrat:ddt-Lrat_Band46UnlicensedProfile_b46D54340MaxPower;
      default 0;
    }
    leaf b46A47490Allowed {
      status deprecated {
        yexte:status-information "Since 17.Q2. Has no functional behavior. Planned to be removed.";
      }
      description "Is EARFCN 47490 (46A) allowed for transmission. Corresponds to Wi-Fi channel 44.";
      yexte:precondition Band46UnlicensedProfile;
      type erienmnrmlrat:enum-B46ChannelUsage;
      default CHANNEL_DISABLED;
    }
    leaf b46A46890Allowed {
      status deprecated {
        yexte:status-information "Since 17.Q2. Has no functional behavior. Planned to be removed.";
      }
      description "Is EARFCN 46890 (46A) allowed for transmission.";
      yexte:precondition Band46UnlicensedProfile;
      type erienmnrmlrat:enum-B46ChannelUsage;
      default CHANNEL_DISABLED;
    }
    leaf b46C50890MaxPower {
      status deprecated {
        yexte:status-information "Since 17.Q2. Has no functional behavior. Planned to be removed.";
      }
      description "The maximum allowed transmission power on EARFCN 50890 (46C). Corresponds to Wi-Fi channel 112.";
      yexte:precondition Band46UnlicensedProfile;
      type erienmnrmlrat:ddt-Lrat_Band46UnlicensedProfile_b46C50890MaxPower;
      default 0;
    }
    leaf b46B48690MaxPower {
      status deprecated {
        yexte:status-information "Since 17.Q2. Has no functional behavior. Planned to be removed.";
      }
      description "The maximum allowed transmission power on EARFCN 48690 (46B).";
      yexte:precondition Band46UnlicensedProfile;
      type erienmnrmlrat:ddt-Lrat_Band46UnlicensedProfile_b46B48690MaxPower;
      default 0;
    }
    leaf b46D53140Allowed {
      status deprecated {
        yexte:status-information "Since 17.Q2. Has no functional behavior. Planned to be removed.";
      }
      description "Is EARFCN 53140 (46D) allowed for transmission. Corresponds to Wi-Fi channel 157.";
      yexte:precondition Band46UnlicensedProfile;
      type erienmnrmlrat:enum-B46ChannelUsage;
      default CHANNEL_DISABLED;
    }
    leaf b46D52740MaxPower {
      status deprecated {
        yexte:status-information "Since 17.Q2. Has no functional behavior. Planned to be removed.";
      }
      description "The maximum allowed transmission power on EARFCN 52740 (46D). Corresponds to Wi-Fi channel 149.";
      yexte:precondition Band46UnlicensedProfile;
      type erienmnrmlrat:ddt-Lrat_Band46UnlicensedProfile_b46D52740MaxPower;
      default 0;
    }
    leaf b46D53740Allowed {
      status deprecated {
        yexte:status-information "Since 17.Q2. Has no functional behavior. Planned to be removed.";
      }
      description "Is EARFCN 53740 (46D) allowed for transmission.";
      yexte:precondition Band46UnlicensedProfile;
      type erienmnrmlrat:enum-B46ChannelUsage;
      default CHANNEL_DISABLED;
    }
    leaf b46B48690Allowed {
      status deprecated {
        yexte:status-information "Since 17.Q2. Has no functional behavior. Planned to be removed.";
      }
      description "Is EARFCN 48690 (46B) allowed for transmission.";
      yexte:precondition Band46UnlicensedProfile;
      type erienmnrmlrat:enum-B46ChannelUsage;
      default CHANNEL_DISABLED;
    }
    leaf b46C52090Allowed {
      status deprecated {
        yexte:status-information "Since 17.Q2. Has no functional behavior. Planned to be removed.";
      }
      description "Is EARFCN 52090 (46C) allowed for transmission. Corresponds to Wi-Fi channel 136.";
      yexte:precondition Band46UnlicensedProfile;
      type erienmnrmlrat:enum-B46ChannelUsage;
      default CHANNEL_DISABLED;
    }
    leaf b46A46890MaxPower {
      status deprecated {
        yexte:status-information "Since 17.Q2. Has no functional behavior. Planned to be removed.";
      }
      description "The maximum allowed transmission power on EARFCN 46890 (46A).";
      yexte:precondition Band46UnlicensedProfile;
      type erienmnrmlrat:ddt-Lrat_Band46UnlicensedProfile_b46A46890MaxPower;
      default 0;
    }
    leaf b46C50490MaxPower {
      status deprecated {
        yexte:status-information "Since 17.Q2. Has no functional behavior. Planned to be removed.";
      }
      description "The maximum allowed transmission power on EARFCN 50490 (46C). Corresponds to Wi-Fi channel 104.";
      yexte:precondition Band46UnlicensedProfile;
      type erienmnrmlrat:ddt-Lrat_Band46UnlicensedProfile_b46C50490MaxPower;
      default 0;
    }
    leaf b46C51490Allowed {
      status deprecated {
        yexte:status-information "Since 17.Q2. Has no functional behavior. Planned to be removed.";
      }
      description "Is EARFCN 51490 (46C) allowed for transmission. Corresponds to Wi-Fi channel 124.";
      yexte:precondition Band46UnlicensedProfile;
      type erienmnrmlrat:enum-B46ChannelUsage;
      default CHANNEL_DISABLED;
    }
    leaf b46D54340Allowed {
      status deprecated {
        yexte:status-information "Since 17.Q2. Has no functional behavior. Planned to be removed.";
      }
      description "Is EARFCN 54340 (46D) allowed for transmission.";
      yexte:precondition Band46UnlicensedProfile;
      type erienmnrmlrat:enum-B46ChannelUsage;
      default CHANNEL_DISABLED;
    }
    leaf b46B47890MaxPower {
      status deprecated {
        yexte:status-information "Since 17.Q2. Has no functional behavior. Planned to be removed.";
      }
      description "The maximum allowed transmission power on EARFCN 47890 (46B). Corresponds to Wi-Fi channel 52.";
      yexte:precondition Band46UnlicensedProfile;
      type erienmnrmlrat:ddt-Lrat_Band46UnlicensedProfile_b46B47890MaxPower;
      default 0;
    }
    leaf b46C52090MaxPower {
      status deprecated {
        yexte:status-information "Since 17.Q2. Has no functional behavior. Planned to be removed.";
      }
      description "The maximum allowed transmission power on EARFCN 52090 (46C). Corresponds to Wi-Fi channel 136.";
      yexte:precondition Band46UnlicensedProfile;
      type erienmnrmlrat:ddt-Lrat_Band46UnlicensedProfile_b46C52090MaxPower;
      default 0;
    }
    leaf b46D53540MaxPower {
      status deprecated {
        yexte:status-information "Since 17.Q2. Has no functional behavior. Planned to be removed.";
      }
      description "The maximum allowed transmission power on EARFCN 53540 (46D). Corresponds to Wi-Fi channel 165.";
      yexte:precondition Band46UnlicensedProfile;
      type erienmnrmlrat:ddt-Lrat_Band46UnlicensedProfile_b46D53540MaxPower;
      default 0;
    }
    leaf b46C51890Allowed {
      status deprecated {
        yexte:status-information "Since 17.Q2. Has no functional behavior. Planned to be removed.";
      }
      description "Is EARFCN 51890 (46C) allowed for transmission. Corresponds to Wi-Fi channel 132.";
      yexte:precondition Band46UnlicensedProfile;
      type erienmnrmlrat:enum-B46ChannelUsage;
      default CHANNEL_DISABLED;
    }
    leaf b46C51290Allowed {
      status deprecated {
        yexte:status-information "Since 17.Q2. Has no functional behavior. Planned to be removed.";
      }
      description "Is EARFCN 51290 (46C) allowed for transmission. Corresponds to Wi-Fi channel 120.";
      yexte:precondition Band46UnlicensedProfile;
      type erienmnrmlrat:enum-B46ChannelUsage;
      default CHANNEL_DISABLED;
    }
    leaf b46C50690Allowed {
      status deprecated {
        yexte:status-information "Since 17.Q2. Has no functional behavior. Planned to be removed.";
      }
      description "Is EARFCN 50690 (46C) allowed for transmission. Corresponds to Wi-Fi channel 108.";
      yexte:precondition Band46UnlicensedProfile;
      type erienmnrmlrat:enum-B46ChannelUsage;
      default CHANNEL_DISABLED;
    }
    leaf b46C52490Allowed {
      status deprecated {
        yexte:status-information "Since 17.Q2. Has no functional behavior. Planned to be removed.";
      }
      description "Is EARFCN 52490 (46C) allowed for transmission. Corresponds to Wi-Fi channel 144.";
      yexte:precondition Band46UnlicensedProfile;
      type erienmnrmlrat:enum-B46ChannelUsage;
      default CHANNEL_DISABLED;
    }
    leaf b46C52290MaxPower {
      status deprecated {
        yexte:status-information "Since 17.Q2. Has no functional behavior. Planned to be removed.";
      }
      description "The maximum allowed transmission power on EARFCN 52290 (46C). Corresponds to Wi-Fi channel 140.";
      yexte:precondition Band46UnlicensedProfile;
      type erienmnrmlrat:ddt-Lrat_Band46UnlicensedProfile_b46C52290MaxPower;
      default 0;
    }
    leaf b46C51690MaxPower {
      status deprecated {
        yexte:status-information "Since 17.Q2. Has no functional behavior. Planned to be removed.";
      }
      description "The maximum allowed transmission power on EARFCN 51690 (46C). Corresponds to Wi-Fi channel 128.";
      yexte:precondition Band46UnlicensedProfile;
      type erienmnrmlrat:ddt-Lrat_Band46UnlicensedProfile_b46C51690MaxPower;
      default 0;
    }
    leaf b46A47090MaxPower {
      status deprecated {
        yexte:status-information "Since 17.Q2. Has no functional behavior. Planned to be removed.";
      }
      description "The maximum allowed transmission power on EARFCN 47090 (46A). Corresponds to Wi-Fi channel 36.";
      yexte:precondition Band46UnlicensedProfile;
      type erienmnrmlrat:ddt-Lrat_Band46UnlicensedProfile_b46A47090MaxPower;
      default 0;
    }
    leaf b46D53940MaxPower {
      status deprecated {
        yexte:status-information "Since 17.Q2. Has no functional behavior. Planned to be removed.";
      }
      description "The maximum allowed transmission power on EARFCN 53940 (46D).";
      yexte:precondition Band46UnlicensedProfile;
      type erienmnrmlrat:ddt-Lrat_Band46UnlicensedProfile_b46D53940MaxPower;
      default 0;
    }
    leaf b46C50090MaxPower {
      status deprecated {
        yexte:status-information "Since 17.Q2. Has no functional behavior. Planned to be removed.";
      }
      description "The maximum allowed transmission power on EARFCN 50090 (46C).";
      yexte:precondition Band46UnlicensedProfile;
      type erienmnrmlrat:ddt-Lrat_Band46UnlicensedProfile_b46C50090MaxPower;
      default 0;
    }
    leaf b46A47690Allowed {
      status deprecated {
        yexte:status-information "Since 17.Q2. Has no functional behavior. Planned to be removed.";
      }
      description "Is EARFCN 47690 (46A) allowed for transmission. Corresponds to Wi-Fi channel 48.";
      yexte:precondition Band46UnlicensedProfile;
      type erienmnrmlrat:enum-B46ChannelUsage;
      default CHANNEL_DISABLED;
    }
    leaf b46D54140MaxPower {
      status deprecated {
        yexte:status-information "Since 17.Q2. Has no functional behavior. Planned to be removed.";
      }
      description "The maximum allowed transmission power on EARFCN 54120 (46D).";
      yexte:precondition Band46UnlicensedProfile;
      type erienmnrmlrat:ddt-Lrat_Band46UnlicensedProfile_b46D54140MaxPower;
      default 0;
    }
    leaf b46C50690MaxPower {
      status deprecated {
        yexte:status-information "Since 17.Q2. Has no functional behavior. Planned to be removed.";
      }
      description "The maximum allowed transmission power on EARFCN 50690 (46C). Corresponds to Wi-Fi channel 108.";
      yexte:precondition Band46UnlicensedProfile;
      type erienmnrmlrat:ddt-Lrat_Band46UnlicensedProfile_b46C50690MaxPower;
      default 0;
    }
    leaf b46D53940Allowed {
      status deprecated {
        yexte:status-information "Since 17.Q2. Has no functional behavior. Planned to be removed.";
      }
      description "Is EARFCN 53940 (46D) allowed for transmission.";
      yexte:precondition Band46UnlicensedProfile;
      type erienmnrmlrat:enum-B46ChannelUsage;
      default CHANNEL_DISABLED;
    }
    leaf b46B48090MaxPower {
      status deprecated {
        yexte:status-information "Since 17.Q2. Has no functional behavior. Planned to be removed.";
      }
      description "The maximum allowed transmission power on EARFCN 48090 (46B). Corresponds to Wi-Fi channel 56.";
      yexte:precondition Band46UnlicensedProfile;
      type erienmnrmlrat:ddt-Lrat_Band46UnlicensedProfile_b46B48090MaxPower;
      default 0;
    }
    leaf b46B48290Allowed {
      status deprecated {
        yexte:status-information "Since 17.Q2. Has no functional behavior. Planned to be removed.";
      }
      description "Is EARFCN 48290 (46B) allowed for transmission. Corresponds to Wi-Fi channel 60.";
      yexte:precondition Band46UnlicensedProfile;
      type erienmnrmlrat:enum-B46ChannelUsage;
      default CHANNEL_DISABLED;
    }
    leaf b46C51090MaxPower {
      status deprecated {
        yexte:status-information "Since 17.Q2. Has no functional behavior. Planned to be removed.";
      }
      description "The maximum allowed transmission power on EARFCN 51090 (46C). Corresponds to Wi-Fi channel 116.";
      yexte:precondition Band46UnlicensedProfile;
      type erienmnrmlrat:ddt-Lrat_Band46UnlicensedProfile_b46C51090MaxPower;
      default 0;
    }
    leaf b46C51490MaxPower {
      status deprecated {
        yexte:status-information "Since 17.Q2. Has no functional behavior. Planned to be removed.";
      }
      description "The maximum allowed transmission power on EARFCN 51490 (46C). Corresponds to Wi-Fi channel 124.";
      yexte:precondition Band46UnlicensedProfile;
      type erienmnrmlrat:ddt-Lrat_Band46UnlicensedProfile_b46C51490MaxPower;
      default 0;
    }
    leaf b46D52940MaxPower {
      status deprecated {
        yexte:status-information "Since 17.Q2. Has no functional behavior. Planned to be removed.";
      }
      description "The maximum allowed transmission power on EARFCN 52940 (46D). Corresponds to Wi-Fi channel 153.";
      yexte:precondition Band46UnlicensedProfile;
      type erienmnrmlrat:ddt-Lrat_Band46UnlicensedProfile_b46D52940MaxPower;
      default 0;
    }
    leaf b46D53340Allowed {
      status deprecated {
        yexte:status-information "Since 17.Q2. Has no functional behavior. Planned to be removed.";
      }
      description "Is EARFCN 53340 (46D) allowed for transmission. Corresponds to Wi-Fi channel 161.";
      yexte:precondition Band46UnlicensedProfile;
      type erienmnrmlrat:enum-B46ChannelUsage;
      default CHANNEL_DISABLED;
    }
    leaf b46D53740MaxPower {
      status deprecated {
        yexte:status-information "Since 17.Q2. Has no functional behavior. Planned to be removed.";
      }
      description "The maximum allowed transmission power on EARFCN 53740 (46D).";
      yexte:precondition Band46UnlicensedProfile;
      type erienmnrmlrat:ddt-Lrat_Band46UnlicensedProfile_b46D53740MaxPower;
      default 0;
    }
    leaf b46A47090Allowed {
      status deprecated {
        yexte:status-information "Since 17.Q2. Has no functional behavior. Planned to be removed.";
      }
      description "Is EARFCN 47090 (46A) allowed for transmission. Corresponds to Wi-Fi channel 36.";
      yexte:precondition Band46UnlicensedProfile;
      type erienmnrmlrat:enum-B46ChannelUsage;
      default CHANNEL_DISABLED;
    }
    leaf b46A47490MaxPower {
      status deprecated {
        yexte:status-information "Since 17.Q2. Has no functional behavior. Planned to be removed.";
      }
      description "The maximum allowed transmission power on EARFCN 47490 (46A). Corresponds to Wi-Fi channel 44.";
      yexte:precondition Band46UnlicensedProfile;
      type erienmnrmlrat:ddt-Lrat_Band46UnlicensedProfile_b46A47490MaxPower;
      default 0;
    }
    leaf b46D52740Allowed {
      status deprecated {
        yexte:status-information "Since 17.Q2. Has no functional behavior. Planned to be removed.";
      }
      description "Is EARFCN 52740 (46D) allowed for transmission. Corresponds to Wi-Fi channel 149.";
      yexte:precondition Band46UnlicensedProfile;
      type erienmnrmlrat:enum-B46ChannelUsage;
      default CHANNEL_DISABLED;
    }
    leaf b46D53340MaxPower {
      status deprecated {
        yexte:status-information "Since 17.Q2. Has no functional behavior. Planned to be removed.";
      }
      description "The maximum allowed transmission power on EARFCN 53340 (46D). Corresponds to Wi-Fi channel 161.";
      yexte:precondition Band46UnlicensedProfile;
      type erienmnrmlrat:ddt-Lrat_Band46UnlicensedProfile_b46D53340MaxPower;
      default 0;
    }
    leaf b46B48490MaxPower {
      status deprecated {
        yexte:status-information "Since 17.Q2. Has no functional behavior. Planned to be removed.";
      }
      description "The maximum allowed transmission power on EARFCN 48490 (46B). Corresponds to Wi-Fi channel 64.";
      yexte:precondition Band46UnlicensedProfile;
      type erienmnrmlrat:ddt-Lrat_Band46UnlicensedProfile_b46B48490MaxPower;
      default 0;
    }
    leaf b46A47290Allowed {
      status deprecated {
        yexte:status-information "Since 17.Q2. Has no functional behavior. Planned to be removed.";
      }
      description "Is EARFCN 47290 (46A) allowed for transmission. Corresponds to Wi-Fi channel 40.";
      yexte:precondition Band46UnlicensedProfile;
      type erienmnrmlrat:enum-B46ChannelUsage;
      default CHANNEL_DISABLED;
    }
    leaf b46C50090Allowed {
      status deprecated {
        yexte:status-information "Since 17.Q2. Has no functional behavior. Planned to be removed.";
      }
      description "Is EARFCN 50090 (46C) allowed for transmission.";
      yexte:precondition Band46UnlicensedProfile;
      type erienmnrmlrat:enum-B46ChannelUsage;
      default CHANNEL_DISABLED;
    }
    leaf b46D52940Allowed {
      status deprecated {
        yexte:status-information "Since 17.Q2. Has no functional behavior. Planned to be removed.";
      }
      description "Is EARFCN 52940 (46D) allowed for transmission. Corresponds to Wi-Fi channel 153.";
      yexte:precondition Band46UnlicensedProfile;
      type erienmnrmlrat:enum-B46ChannelUsage;
      default CHANNEL_DISABLED;
    }
    leaf b46B48490Allowed {
      status deprecated {
        yexte:status-information "Since 17.Q2. Has no functional behavior. Planned to be removed.";
      }
      description "Is EARFCN 48490 (46B) allowed for transmission. Corresponds to Wi-Fi channel 64.";
      yexte:precondition Band46UnlicensedProfile;
      type erienmnrmlrat:enum-B46ChannelUsage;
      default CHANNEL_DISABLED;
    }
    leaf b46B47890Allowed {
      status deprecated {
        yexte:status-information "Since 17.Q2. Has no functional behavior. Planned to be removed.";
      }
      description "Is EARFCN 47890 (46B) allowed for transmission. Corresponds to Wi-Fi channel 52.";
      yexte:precondition Band46UnlicensedProfile;
      type erienmnrmlrat:enum-B46ChannelUsage;
      default CHANNEL_DISABLED;
    }
    leaf b46D53140MaxPower {
      status deprecated {
        yexte:status-information "Since 17.Q2. Has no functional behavior. Planned to be removed.";
      }
      description "The maximum allowed transmission power on EARFCN 53140 (46D). Corresponds to Wi-Fi channel 157.";
      yexte:precondition Band46UnlicensedProfile;
      type erienmnrmlrat:ddt-Lrat_Band46UnlicensedProfile_b46D53140MaxPower;
      default 0;
    }
    leaf b46C50290MaxPower {
      status deprecated {
        yexte:status-information "Since 17.Q2. Has no functional behavior. Planned to be removed.";
      }
      description "The maximum allowed transmission power on EARFCN 50290 (46C). Corresponds to Wi-Fi channel 100.";
      yexte:precondition Band46UnlicensedProfile;
      type erienmnrmlrat:ddt-Lrat_Band46UnlicensedProfile_b46C50290MaxPower;
      default 0;
    }
    leaf b46A47290MaxPower {
      status deprecated {
        yexte:status-information "Since 17.Q2. Has no functional behavior. Planned to be removed.";
      }
      description "The maximum allowed transmission power on EARFCN 47290 (46A). Corresponds to Wi-Fi channel 40.";
      yexte:precondition Band46UnlicensedProfile;
      type erienmnrmlrat:ddt-Lrat_Band46UnlicensedProfile_b46A47290MaxPower;
      default 0;
    }
    leaf b46C51690Allowed {
      status deprecated {
        yexte:status-information "Since 17.Q2. Has no functional behavior. Planned to be removed.";
      }
      description "Is EARFCN 51690 (46C) allowed for transmission. Corresponds to Wi-Fi channel 128.";
      yexte:precondition Band46UnlicensedProfile;
      type erienmnrmlrat:enum-B46ChannelUsage;
      default CHANNEL_DISABLED;
    }
    leaf b46D54140Allowed {
      status deprecated {
        yexte:status-information "Since 17.Q2. Has no functional behavior. Planned to be removed.";
      }
      description "Is EARFCN 54140 (46D) allowed for transmission.";
      yexte:precondition Band46UnlicensedProfile;
      type erienmnrmlrat:enum-B46ChannelUsage;
      default CHANNEL_DISABLED;
    }
    leaf b46B48090Allowed {
      status deprecated {
        yexte:status-information "Since 17.Q2. Has no functional behavior. Planned to be removed.";
      }
      description "Is EARFCN 48090 (46B) allowed for transmission. Corresponds to Wi-Fi channel 56.";
      yexte:precondition Band46UnlicensedProfile;
      type erienmnrmlrat:enum-B46ChannelUsage;
      default CHANNEL_DISABLED;
    }
    leaf b46C51090Allowed {
      status deprecated {
        yexte:status-information "Since 17.Q2. Has no functional behavior. Planned to be removed.";
      }
      description "Is EARFCN 51090 (46C) allowed for transmission. Corresponds to Wi-Fi channel 116.";
      yexte:precondition Band46UnlicensedProfile;
      type erienmnrmlrat:enum-B46ChannelUsage;
      default CHANNEL_DISABLED;
    }
    leaf-list reservedBy {
      min-elements 0;
      status deprecated {
        yexte:status-information "Since 17.Q2. Has no functional behavior. Planned to be removed.";
      }
      config false;
      description "List of MO instances that reserve this MO instance.";
      yexte:takes-effect "Node restart";
      yexte:dependencies "MO can not be deleted if it is reserved.";
      notife:notifiable-state-data true;
      erienmyext:enm-type MOREF;
      type string;
    }
    leaf b46C52290Allowed {
      status deprecated {
        yexte:status-information "Since 17.Q2. Has no functional behavior. Planned to be removed.";
      }
      description "Is EARFCN 52290 (46C) allowed for transmission. Corresponds to Wi-Fi channel 140.";
      yexte:precondition Band46UnlicensedProfile;
      type erienmnrmlrat:enum-B46ChannelUsage;
      default CHANNEL_DISABLED;
    }
    leaf b46C52490MaxPower {
      status deprecated {
        yexte:status-information "Since 17.Q2. Has no functional behavior. Planned to be removed.";
      }
      description "The maximum allowed transmission power on EARFCN 52490 (46C). Corresponds to Wi-Fi channel 144.";
      yexte:precondition Band46UnlicensedProfile;
      type erienmnrmlrat:ddt-Lrat_Band46UnlicensedProfile_b46C52490MaxPower;
      default 0;
    }
    leaf b46D53540Allowed {
      status deprecated {
        yexte:status-information "Since 17.Q2. Has no functional behavior. Planned to be removed.";
      }
      description "Is EARFCN 53540 (46D) allowed for transmission. Corresponds to Wi-Fi channel 165.";
      yexte:precondition Band46UnlicensedProfile;
      type erienmnrmlrat:enum-B46ChannelUsage;
      default CHANNEL_DISABLED;
    }
    leaf b46C50490Allowed {
      status deprecated {
        yexte:status-information "Since 17.Q2. Has no functional behavior. Planned to be removed.";
      }
      description "Is EARFCN 50490 (46C) allowed for transmission. Corresponds to Wi-Fi channel 104.";
      yexte:precondition Band46UnlicensedProfile;
      type erienmnrmlrat:enum-B46ChannelUsage;
      default CHANNEL_DISABLED;
    }
    leaf b46C51890MaxPower {
      status deprecated {
        yexte:status-information "Since 17.Q2. Has no functional behavior. Planned to be removed.";
      }
      description "The maximum allowed transmission power on EARFCN 51890 (46C). Corresponds to Wi-Fi channel 132.";
      yexte:precondition Band46UnlicensedProfile;
      type erienmnrmlrat:ddt-Lrat_Band46UnlicensedProfile_b46C51890MaxPower;
      default 0;
    }
  } // end 'grouping moc-Band46UnlicensedProfile'
  grouping moc-ReportConfigA5DlComp-keys {
    description "Key(s) for MOC ReportConfigA5DlComp";
    leaf id {
      erienmyext:no-notification;
      description "The value component of the RDN.";
      mandatory true;
      yexte:ecim-name reportConfigA5DlCompId;
      type string;
    }
  } // end 'grouping moc-ReportConfigA5DlComp-keys'
  grouping moc-ReportConfigA5DlComp {
    description "This MO contains report configuration settings for the A5 event measurements that assist Downlink Coordinated Multi-Point. The A5 event is used to detect when serving cell becomes worse than threshold1, and neighbor cell becomes better than threshold2.\n\nThe RDN of this MO is ReportConfigA5DlComp=1.";
  } // end 'grouping moc-ReportConfigA5DlComp'
  grouping moc-ImeisvProfile-keys {
    description "Key(s) for MOC ImeisvProfile";
    leaf id {
      erienmyext:no-notification;
      description "Value component of the RDN";
      mandatory true;
      yexte:ecim-name imeisvProfileId;
      type string;
    }
  } // end 'grouping moc-ImeisvProfile-keys'
  grouping moc-ImeisvProfile {
    description "Contains UE IMEISV configuration used for feature Differentiated UE Handling. Instances of this class are created on demand by the operator. The instances can be created and configured independent of the serviceState for DifferentiatedUeHandling. But the IMEISV profiles cannot be used unless the service state is OPERABLE.\n\n";
    leaf-list listOfFeaturesToTurnOff {
      min-elements 0;
      max-elements 10;
      description "List of features to be turned off for the list of quintuples  {tac, minSv, maxSv, minSn, maxSn} specified in listOfTacSvSns";
      yexte:disturbances "Changing this attribute can affect traffic.";
      yexte:takes-effect "New connection";
      yexte:dependencies "listOfFeaturesToTurnOff and listOfFeaturesToTurnOn must be disjoint sets";
      type erienmnrmlrat:enum-FeatureName;
    }
    list listOfTacSvSns {
      min-elements 0;
      max-elements 20;
      key auto-generated-struct-key;
      leaf auto-generated-struct-key {
        type uint16;
        description "This leaf has been injected to allow for struct instances in a sequence to be ordered.";
        mandatory true;
      }
      description "List of quintuples {tac, minSv, maxSv, minSn, maxSn} that are configured with similar \"special\" handling needs.";
      erienmyext:enm-type STRUCT;
      uses erienmnrmlrat:struct-TacSvAndSnRange;
    } // end 'list listOfTacSvSns'
    leaf nonVoiceDrxProfileRef {
      description "Points out the DRX profile associated with this IMEISV profile, used for UEs without voice bearers.";
      yexte:disturbances "Changing this attribute can affect traffic.";
      yexte:takes-effect "New connection";
      erienmyext:enm-type MOREF;
      type string;
    }
    leaf elcPreHeatingLength {
      description "UE-dependent parameter. Defines necessary number of subframes with available CRS  before a DRX onDuration. Allows the operator to configure UE behavior for each IMEISV. Only applicable when the feature Ericsson Lean Carrier is enabled.";
      yexte:disturbances "Can affect traffic. If incorrectly set, RSRP measurement performed by the UE can become corrupt and cause degraded NW performance.";
      yexte:takes-effect "New connection";
      type erienmnrmlrat:ddt-Lrat_ImeisvProfile_elcPreHeatingLength;
      default 1;
    }
    leaf-list listOfFeaturesToTurnOn {
      min-elements 0;
      max-elements 10;
      description "List of features to be turned on for the list of quintuples  {tac, minSv, maxSv, minSn, maxSn} specified in listOfTacSvSns";
      yexte:disturbances "Changing this attribute can affect traffic.";
      yexte:takes-effect "New connection";
      yexte:dependencies "listOfFeaturesToTurnOff and listOfFeaturesToTurnOn must be disjoint sets";
      type erienmnrmlrat:enum-FeatureName;
    }
    leaf voiceDrxProfileRef {
      description "Points out the DRX profile associated with this IMEISV profile, used for UEs with voice bearers.";
      yexte:disturbances "Changing this attribute can affect traffic.";
      yexte:takes-effect "New connection";
      erienmyext:enm-type MOREF;
      type string;
    }
    leaf elc320msDrxEnabled {
      description "If set to true, 320ms long DRX cycle is configured to ELC UE.";
      yexte:takes-effect "New connection";
      yexte:dependencies "Only relevant if license Ericsson Lean Carrier is present and feature is active.";
      type boolean;
      default false;
    }
    leaf elcPostHeatingLength {
      description "UE-dependent parameter. Defines necessary number of subframes with available CRS  after a DRX onDuration. Allows the operator to configure UE behavior for each IMEISV. Only applicable when the feature Ericsson Lean Carrier is enabled.";
      yexte:disturbances "Can affect traffic. If incorrectly set, RSRP measurement performed by the UE can become corrupt and cause degraded NW performance.";
      yexte:takes-effect "New connection";
      type erienmnrmlrat:ddt-Lrat_ImeisvProfile_elcPostHeatingLength;
      default 0;
    }
  } // end 'grouping moc-ImeisvProfile'
  grouping moc-FlexibleQoSGroupMember-keys {
    description "Key(s) for MOC FlexibleQoSGroupMember";
    leaf id {
      erienmyext:no-notification;
      description "The value component of the RDN.";
      mandatory true;
      yexte:ecim-name flexibleQoSGroupMemberId;
      type string;
    }
  } // end 'grouping moc-FlexibleQoSGroupMember-keys'
  grouping moc-FlexibleQoSGroupMember {
    description "Specifies a mapping configuration to decide what SciProfile should be assigned to a bearer.";
    leaf sciProfileRef {
      description "Reference to instance of SciProfile MO.";
      mandatory true;
      yexte:disturbances "Changing this attribute can affect traffic.";
      yexte:takes-effect "New connection";
      yexte:dependencies "Default SCI profiles cannot be used.";
      erienmyext:enm-type MOREF;
      type string;
    }
    leaf userProfileRef {
      description "Reference to instance of UserProfile MO.";
      mandatory true;
      yexte:disturbances "Changing this attribute can affect traffic.";
      yexte:takes-effect "New connection";
      yexte:dependencies "Each FlexibleQoSGroupMember MO instance in same FlexibleQoSGroup MOC must have unique userProfileRef.";
      erienmyext:enm-type MOREF;
      type string;
    }
  } // end 'grouping moc-FlexibleQoSGroupMember'
  grouping moc-CellSleepNodeFunction-keys {
    description "Key(s) for MOC CellSleepNodeFunction";
    leaf id {
      erienmyext:no-notification;
      description "The value component of the RDN.";
      mandatory true;
      yexte:ecim-name cellSleepNodeFunctionId;
      type string;
    }
  } // end 'grouping moc-CellSleepNodeFunction-keys'
  grouping moc-CellSleepNodeFunction {
    description "Contains parameters for Cell Sleep Mode support in the node that are common for all cells.\nThe RDN of this MO is CellSleepNodeFunction=1.";
    leaf csmEutranInterFMeasReportIncr {
      description "Increase in the target number of periodic measurement reports for each EUtranFreqRelation when the required hit rate to identify cell sleep mode coverage cells is not yet achieved. Note that the unit is decMeasurementReport. Thus, the given number of measurement reports is divided by 10.";
      yexte:disturbances "Changing this attribute can cause loss of traffic.";
      type erienmnrmlrat:ddt-Lrat_CellSleepNodeFunction_csmEutranInterFMeasReportIncr;
      default 10;
    }
    leaf csmMinHitRateForCovCell {
      description "Minimum required hit rate value for related cell to be assigned as coverage cell. When hit rate of given cell is higher than value, cell can be selected as coverage cell for capacity cell.";
      type erienmnrmlrat:ddt-Lrat_CellSleepNodeFunction_csmMinHitRateForCovCell;
      default 50;
    }
    leaf csmEutranInterFMeasReportMax {
      description "Maximum target number of cell sleep mode measurement reports each hour for each EUtranFreqRelation. The number of measurement reports can deviate from the target. Note that the unit is decMeasurementReport. Thus, the given number of measurement reports is divided by 10.";
      yexte:disturbances "Changing this attribute can cause loss of traffic.";
      yexte:dependencies "csmEutranInterFMeasReportMax > csmEutranInterFMeasReportMin";
      type erienmnrmlrat:ddt-Lrat_CellSleepNodeFunction_csmEutranInterFMeasReportMax;
      default 100;
    }
    leaf csmEutranInterFMeasReportDecr {
      description "Decrease in the target number of periodic measurement reports for each EUtranFreqRelation when the required hit rate to identify cell sleep mode coverage cells is achieved. Note that the unit is decMeasurementReport. Thus, the given number of measurement reports is divided by 10.";
      yexte:disturbances "Changing this attribute can cause loss of traffic.";
      type erienmnrmlrat:ddt-Lrat_CellSleepNodeFunction_csmEutranInterFMeasReportDecr;
      default 1;
    }
    leaf csmEutranInterFMeasReportMin {
      description "Minimum target number of cell sleep mode measurement reports each hour for each EUtranFreqRelation. The number of measurement reports can deviate from the target. Note that the unit is decMeasurementReport. Thus, the given number of measurement reports is divided by 10.";
      yexte:disturbances "Changing this attribute can cause loss of traffic.";
      yexte:dependencies "csmEutranInterFMeasReportMin < csmEutranInterFMeasReportMax";
      type erienmnrmlrat:ddt-Lrat_CellSleepNodeFunction_csmEutranInterFMeasReportMin;
      default 5;
    }
  } // end 'grouping moc-CellSleepNodeFunction'
  grouping moc-TermPointToGNB-keys {
    description "Key(s) for MOC TermPointToGNB";
    leaf id {
      erienmyext:no-notification;
      description "The value component of the RDN.";
      mandatory true;
      yexte:ecim-name termPointToGNBId;
      type string;
    }
  } // end 'grouping moc-TermPointToGNB-keys'
  grouping moc-TermPointToGNB {
    description "Models the local eNB termination point of an X2 link between the gNB and an eNB.";
    leaf usedIpAddress {
      config false;
      description "The destination address used for initialization of the underlying SCTP association of the latest successful X2-Setup.\nThe IP address can be an IPv4 or an IPv6 address.\nNote: usedIpAddress never changes during the lifetime of the SCTP association.";
      notife:notifiable-state-data true;
      type erienmnrmlrat:ddt-Lrat_TermPointToGNB_usedIpAddress;
    }
    leaf ipv6Address {
      description "The IP address of the neighboring RBS. The format is eight fields, separated by colons.\nEach field consists of four hexadecimal characters. The value of each field is in the range 0-FFFF.\nLeading zeroes can be omitted in a field, and multiple groups of 16 bits of zeroes can be compressed to ::\nThe :: can appear only once in an address.";
      yexte:dependencies "To set this attribute, administrativeState must be LOCKED.";
      type erienmnrmlrat:ddt-Lrat_TermPointToGNB_ipv6Address;
      default ::;
    }
    leaf administrativeState {
      description "The administrative state.\nNote: If this attribute is set to SHUTTING_DOWN, it will immediately go into the state LOCKED.";
      type erienmnrmlrat:enum-AdmState;
      default LOCKED;
    }
    leaf domainName {
      description "The fully-qualified domain name of the RBS.\nA valid domain name consists of 1 or more labels separated by dots (.). Valid characters for a label are limited to letters a-z, A-Z, digits 0-9, and the character - (dash).\nThe following format is used for automatically created domain names:\nx2.enbidDDDDD.enb.tac-lbEE.tac-hbFF.tac.eutran.mncBBB.mccCCC.3gppnetwork.org.\nThe D's (five or seven) represent hexadecimal coding of ENBID (enodeB Identity) without padding.\nB & C represent BCD (binary coded decimal) coding of MNC (mobile network code) and MCC (mobile country code) respectively.\nE & F represent hexadecimal coding of the least and most significant bytes (low & high byte) of the tracking area code.\nB, C, E & F are always padded with leading zeros to match the number of characters in the format above.";
      type erienmnrmlrat:ddt-Lrat_TermPointToGNB_domainName;
      default "";
    }
    leaf ipAddress {
      description "The IP address of the neighboring RBS. The input format is four fields of digits, separated by dots. Each field may consist of three digits. The value of each field is in the range 0-255.";
      yexte:dependencies "To set this attribute, administrativeState must be LOCKED.";
      type erienmnrmlrat:ddt-Lrat_TermPointToGNB_ipAddress;
      default 0.0.0.0;
    }
    leaf-list availabilityStatus {
      min-elements 0;
      config false;
      description "The availability status. It contains details about operational state. This attribute is set by the application in the RBS.";
      notife:notifiable-state-data true;
      type erienmnrmlrat:enum-AvailStatus;
    }
    leaf operationalState {
      config false;
      description "The operational state. This attribute is set by the application in the RBS.";
      notife:notifiable-state-data true;
      type erienmnrmlrat:enum-OperState;
    }
  } // end 'grouping moc-TermPointToGNB'
  grouping moc-EUtranFrequency-keys {
    description "Key(s) for MOC EUtranFrequency";
    leaf id {
      erienmyext:no-notification;
      description "The value component of the Relative Distinguished Name (RDN).\n";
      mandatory true;
      yexte:ecim-name eUtranFrequencyId;
      type string;
    }
  } // end 'grouping moc-EUtranFrequency-keys'
  grouping moc-EUtranFrequency {
    description "This Managed Object contains information of a specific EUtran frequency.\nMO is created manually, and when executing action changeFrequency in MO ExternalEUtranCellFDD/TDD.\nMO is also created automatically at X2 link setup with neighbor eNB.\n\nThe RDNs of these MOs are EUtranFrequency=<number>, for example EUtranFrequency=2586.\nRDN must match attribute arfcnValueEUtranDl. If it does not match, automatic creation of MO can fail, leading to X2 link setup failure with neighbor eNB.";
    leaf userLabel {
      description "Label for free use.\n";
      type erienmnrmlrat:ddt-Lrat_EUtranFrequency_userLabel;
    }
    leaf-list additionalFreqBandList {
      min-elements 0;
      max-elements 8;
      config false;
      description "A list of additional frequency bands the frequency belongs to. The list is automatically set by the eNB. The list does not include the frequency band indicated by the EARFCN value of the frequency (primary frequency band). These additional frequency bands are broadcasted to the UEs in SystemInformationBlockType5 in case the feature Multiple Frequency Band Indicators is enabled in the cell.";
      notife:notifiable-state-data true;
      type erienmnrmlrat:ddt-Lrat_EUtranFrequency_additionalFreqBandList;
    }
    leaf freqBand {
      config false;
      description "The primary frequency band the frequency belongs to according to its defined EARFCN.";
      notife:notifiable-state-data true;
      type erienmnrmlrat:ddt-Lrat_EUtranFrequency_freqBand;
    }
    leaf-list reservedBy {
      min-elements 0;
      config false;
      description "Contains a list of MO instances that reserve this MO instance.\n";
      notife:notifiable-state-data true;
      erienmyext:enm-type MOREF;
      type string;
    }
    leaf arfcnValueEUtranDl {
      yexte:restricted;
      description "ARFCN applicable for a downlink E-UTRA carrier frequency, as defined in 3GPP TS 36.104 for specified E-UTRA bands. For TDD this also indicates the ARFCN for uplink. Values that can be used depend on national operator specific frequency allocation as well as supported frequency band(s) of the equipment in the eNodeB. Must match EUtranFrequencyId.";
      mandatory true;
      type erienmnrmlrat:ddt-Lrat_EUtranFrequency_arfcnValueEUtranDl;
    }
    leaf-list excludeAdditionalFreqBandList {
      min-elements 0;
      max-elements 8;
      description "A list of frequency bands to be excluded from the list of additional frequency bands in the additionalFreqBandList MOM attribute. The list shall not include the frequency band indicated by the EARFCN value of the frequency (primary frequency band). These frequency bands are excluded from the list of broadcasted additional frequency bands in SystemInformationBlockType5 in case the feature Multiple Frequency Band Indicators is enabled in the cell.";
      type erienmnrmlrat:ddt-Lrat_EUtranFrequency_excludeAdditionalFreqBandList;
    }
  } // end 'grouping moc-EUtranFrequency'
  grouping moc-PtmAtoConfig-keys {
    description "Key(s) for MOC PtmAtoConfig";
    leaf id {
      erienmyext:no-notification;
      description "The value component of the RDN.";
      mandatory true;
      yexte:ecim-name ptmAtoConfigId;
      type string;
    }
  } // end 'grouping moc-PtmAtoConfig-keys'
  grouping moc-PtmAtoConfig {
    description "Contains PTM specific parameters affecting Admission Triggered Offload feature.\n\nThe RDN of this MO is PtmAtoConfig=1.";
    leaf-list ptmSubscriberGroupRef {
      min-elements 0;
      max-elements 12;
      description "Reference to an instance of PtmSubscriberGroup MO Class.\nOrder of PTM Subscriber Group offload from cell, using ATO feature.\nUEs not assigned to any group are offloaded in first group.\nIf list is empty, functionality is disabled.\nNo effect when PtmCellProfile::cellType is set to NON_PRIORITY.";
      yexte:disturbances "Changing this attribute can affect traffic.";
      erienmyext:enm-type MOREF;
      type string;
    }
    leaf minSuccRateThreshold {
      description "If ATO candidate selection success ratio during a selection interval is below threshold, cell enlarges set of PTM Subscriber Groups that can be offloaded by ATO feature.\nNo effect when PtmCellProfile::cellType is set to NON_PRIORITY.";
      yexte:disturbances "Changing this attribute can affect traffic.";
      type erienmnrmlrat:ddt-Lrat_PtmAtoConfig_minSuccRateThreshold;
      default 50;
    }
  } // end 'grouping moc-PtmAtoConfig'
  grouping moc-RadioBearerTable-keys {
    description "Key(s) for MOC RadioBearerTable";
    leaf id {
      erienmyext:no-notification;
      description "The value component of the RDN.";
      mandatory true;
      yexte:ecim-name radioBearerTableId;
      type string;
    }
  } // end 'grouping moc-RadioBearerTable-keys'
  grouping moc-RadioBearerTable {
    description "Contains Radio Bearer configurations.\n\nThe RDN of this MO is RadioBearerTable=default.";
  } // end 'grouping moc-RadioBearerTable'
  grouping moc-ReportConfigInterEnbUlComp-keys {
    description "Key(s) for MOC ReportConfigInterEnbUlComp";
    leaf id {
      erienmyext:no-notification;
      description "The value component of the RDN.";
      mandatory true;
      yexte:ecim-name reportConfigInterEnbUlCompId;
      type string;
    }
  } // end 'grouping moc-ReportConfigInterEnbUlComp-keys'
  grouping moc-ReportConfigInterEnbUlComp {
    description "Contains the Report Configuration settings for UE measurements initiated for Inter-eNB UL CoMP.\n\nThe RDN of this MO is ReportConfigInterEnbUlComp=1.";
    leaf a3Offset {
      description "The offset value for eventA3.";
      yexte:takes-effect "New connection";
      type erienmnrmlrat:ddt-Lrat_ReportConfigInterEnbUlComp_a3Offset;
      default -20;
    }
    leaf hysteresisA3 {
      description "The hysteresis value for eventA3.";
      yexte:takes-effect "New connection";
      type erienmnrmlrat:ddt-Lrat_ReportConfigInterEnbUlComp_hysteresisA3;
      default 10;
    }
    leaf reportIntervalA3 {
      description "Interval for event-triggered periodical reporting.";
      yexte:takes-effect "New connection";
      type erienmnrmlrat:enum-ReportInterval;
      default MS_1024;
    }
    leaf timeToTriggerA3 {
      description "Time-to-trigger value for event A3.";
      yexte:takes-effect "New connection";
      type erienmnrmlrat:ddt-Lrat_ReportConfigInterEnbUlComp_timeToTriggerA3;
      default 40;
    }
  } // end 'grouping moc-ReportConfigInterEnbUlComp'
  grouping moc-ExternalCdma2000Cell-keys {
    description "Key(s) for MOC ExternalCdma2000Cell";
    leaf id {
      erienmyext:no-notification;
      description "The value component of the Relative Distinguished Name (RDN).\n";
      mandatory true;
      yexte:ecim-name externalCdma2000CellId;
      type string;
    }
  } // end 'grouping moc-ExternalCdma2000Cell-keys'
  grouping moc-ExternalCdma2000Cell {
    description "The MO represents a CDMA2000 HRPD cell.";
    leaf userLabel {
      description "Label for free use.\n";
      type erienmnrmlrat:ddt-Lrat_ExternalCdma2000Cell_userLabel;
    }
    leaf-list reservedBy {
      min-elements 0;
      config false;
      description "Contains a list of MO instances that reserve this MO instance.\n";
      yexte:dependencies "The MO may not be deleted if it is reserved.";
      notife:notifiable-state-data true;
      erienmyext:enm-type MOREF;
      type string;
    }
    leaf cellGlobalIdHrpd {
      description "The IPv6 address for a CDMA2000 HRPD cell. The input format is eight groups of four digits and characters each, separated by colons.\nEx. 2001:0db8:0000:0000:0000:0000:1428:07ab\n";
      mandatory true;
      type string;
    }
    leaf pnOffset {
      description "The CDMA physical cell identity.";
      mandatory true;
      yexte:takes-effect "New connection.";
      type erienmnrmlrat:ddt-Lrat_ExternalCdma2000Cell_pnOffset;
    }
  } // end 'grouping moc-ExternalCdma2000Cell'
  grouping moc-AnrFunctionEUtran-keys {
    description "Key(s) for MOC AnrFunctionEUtran";
    leaf id {
      erienmyext:no-notification;
      description "The value component of the Relative Distinguished Name (RDN).";
      mandatory true;
      yexte:ecim-name anrFunctionEUtranId;
      type string;
    }
  } // end 'grouping moc-AnrFunctionEUtran-keys'
  grouping moc-AnrFunctionEUtran {
    description "Parameters and constraints for LTE ANR functions.\n\nThe RDN of this MO is AnrFunctionEUtran=1.";
    leaf x2SetupPolicy {
      description "Indicates if X2 is to be set up when an ExternalENodeBFunction that is not in the x2BlackList is created by ANR (Automatic Neighbor Relations).";
      type boolean;
      default true;
    }
    leaf hoAllowedEutranPolicy {
      description "Starting value of the parameter isHoAllowed when a EUtranCellRelation is created by ANR (Automatic Neighbor Relations) or X2.";
      type boolean;
      default true;
    }
    leaf anrEutranInterFMeasReportMax {
      description "Maximum target number of periodic measurement reports each hour for each EUtranFreqRelation. The number of measurement reports can deviate from the target.\nNote that the unit is decMeasurementReport. Thus, the given number of measurement reports is divided by 10.";
      yexte:dependencies "anrEutranInterFMeasReportMax >= anrEutranInterFMeasReportMin.";
      type erienmnrmlrat:ddt-Lrat_AnrFunctionEUtran_anrEutranInterFMeasReportMax;
      default 100;
    }
    leaf anrUesEUtraIntraFDecr {
      description "This parameter defines the decrease in the target number of UEs in each cell, that are assigned ANR specific thresholds for EUTRAN intra-frequency neighbour cell reports, every time a neighbour cell report is received with only known neighbour cells.\n";
      type erienmnrmlrat:ddt-Lrat_AnrFunctionEUtran_anrUesEUtraIntraFDecr;
      default 10;
    }
    leaf anrUesThreshInterFMin {
      description "This parameter defines the minimum target number of UEs in each cell, that are assigned ANR specific thresholds for EUTRAN inter-frequency neighbor cell reports. The actual number of UEs with these thresholds may deviate from the target.";
      yexte:takes-effect "New connection";
      type erienmnrmlrat:ddt-Lrat_AnrFunctionEUtran_anrUesThreshInterFMin;
      default 0;
    }
    leaf anrIntraFreqState {
      description "Activates or deactivates the Automated Neighbor Relation (ANR) function support for Intra frequency LTE  for one RBS. The value of the attribute is irrelevant when no valid license key is installed for the ANR feature.";
      type erienmnrmlrat:enum-ActivationVals;
      default ACTIVATED;
    }
    leaf anrInterFreqState {
      description "Activates or deactivates the Automated Neighbor Relation (ANR) function support for Inter frequency LTE  for one RBS. The value of the attribute is irrelevant when no valid license key is installed for the ANR feature.";
      type erienmnrmlrat:enum-ActivationVals;
      default DEACTIVATED;
    }
    leaf anrUesEUtraIntraFIncrAnr {
      description "This parameter defines the increase in the target number of UEs in each cell, that are assigned ANR specific thresholds for EUTRAN intra-frequency neighbour cell reports, every time a neighbour cell report for ANR is received with unknown neighbour cells.\n";
      type erienmnrmlrat:ddt-Lrat_AnrFunctionEUtran_anrUesEUtraIntraFIncrAnr;
      default 20;
    }
    leaf anrEutranInterFMeasReportIncr {
      description "Increase in the target number of periodic measurement reports for each EUtranFreqRelation each time an ANR EUTRAN measurement report is received with unknown neighbor EUTRAN cells. Note that the unit is decMeasurementReport. Thus, the given number of measurement reports is divided by 10.";
      type erienmnrmlrat:ddt-Lrat_AnrFunctionEUtran_anrEutranInterFMeasReportIncr;
      default 10;
    }
    leaf eutranAnrAgQci1 {
      status deprecated {
        yexte:status-information "Since L16B. Planned to be removed";
      }
      description "Enables or disables eNodeB to order CGI measurement when LTE AG capable UE has QCI1.";
      yexte:takes-effect "New connection";
      yexte:dependencies "This attribute is effective only when ANR for LTE feature is activated.";
      type boolean;
      default true;
    }
    leaf anrUesEUtraIntraFMax {
      description "This parameter defines the maximum target number of UEs in each cell, that are assigned ANR specific thresholds for EUTRAN intra-frequency neighbour cell reports. The actual number of UEs with these thresholds may deviate from the target.\n";
      type erienmnrmlrat:ddt-Lrat_AnrFunctionEUtran_anrUesEUtraIntraFMax;
      default 0;
    }
    leaf anrEutranInterFMeasReportDecr {
      description "Decrease in the target number of periodic measurement reports for each EUtranFreqRelation each time an ANR EUTRAN measurement report is received with only known neighbor cells. Note that the unit is decMeasurementReport. Thus, the given number of measurement reports is divided by 10.";
      type erienmnrmlrat:ddt-Lrat_AnrFunctionEUtran_anrEutranInterFMeasReportDecr;
      default 1;
    }
    leaf anrUesThreshInterFIncrAnr {
      description "This parameter defines the increase in the target number of UEs in each cell, that are assigned ANR specific thresholds for EUTRAN inter-frequency neighbor cell reports, every time a neighbor cell report for ANR is received with unknown neighbor cells.";
      yexte:takes-effect "New connection";
      type erienmnrmlrat:ddt-Lrat_AnrFunctionEUtran_anrUesThreshInterFIncrAnr;
      default 20;
    }
    leaf anrUesThreshInterFMax {
      description "This parameter defines the maximum target number of UEs in each cell, that are assigned ANR specific thresholds for EUTRAN inter-frequency neighbor cell reports. The actual number of UEs with these thresholds may deviate from the target.";
      yexte:takes-effect "New connection";
      type erienmnrmlrat:ddt-Lrat_AnrFunctionEUtran_anrUesThreshInterFMax;
      default 0;
    }
    leaf cellAddRsrpThresholdEutran {
      description "Threshold value for reported power for a cell to be automatically added as neighbor.\n";
      type erienmnrmlrat:ddt-Lrat_AnrFunctionEUtran_cellAddRsrpThresholdEutran;
      default -1150;
    }
    leaf anrUesEUtraIntraFIncrHo {
      description "This parameter defines the increase in the target number of UEs in each cell, that are assigned ANR specific thresholds for EUTRAN intra-frequency neighbour cell reports, every time a neighbour cell report for HO is received with unknown neighbour cells.\n";
      type erienmnrmlrat:ddt-Lrat_AnrFunctionEUtran_anrUesEUtraIntraFIncrHo;
      default 100;
    }
    leaf anrEutranInterFMeasReportMin {
      description "Minimum target number of periodic measurement reports each hour for each EUtranFreqRelation. The number of measurement reports can deviate from the target.\nNote that the unit is decMeasurementReport. Thus, the given number of measurement reports is divided by 10.";
      yexte:dependencies "anrEutranInterFMeasReportMin <= anrEutranInterFMeasReportMax.";
      type erienmnrmlrat:ddt-Lrat_AnrFunctionEUtran_anrEutranInterFMeasReportMin;
      default 5;
    }
    leaf anrUesEUtraIntraFMin {
      description "This parameter defines the minimum target number of UEs in each cell, that are assigned ANR specific thresholds for EUTRAN intra-frequency neighbour cell reports. The actual number of UEs with these thresholds may deviate from the target.\n";
      type erienmnrmlrat:ddt-Lrat_AnrFunctionEUtran_anrUesEUtraIntraFMin;
      default 0;
    }
    leaf lbCellOffloadCapacityPolicy {
      description "This attribute indicates the starting value of the attribute lbEUtranCellOffloadCapacity when an ExternalEUtranCell is created by Automated Neighbour Relations (ANR).";
      type erienmnrmlrat:ddt-Lrat_AnrFunctionEUtran_lbCellOffloadCapacityPolicy;
      default 1000;
    }
    leaf anrUesThreshInterFDecr {
      description "This parameter defines the decrease in the target number of UEs in each cell, that are assigned ANR specific thresholds for EUTRAN inter-frequency neighbor cell reports, every time a neighbor cell report is received with only known neighbor cells.";
      yexte:takes-effect "New connection";
      type erienmnrmlrat:ddt-Lrat_AnrFunctionEUtran_anrUesThreshInterFDecr;
      default 10;
    }
    leaf anrUesThreshInterFIncrHo {
      description "This parameter defines the increase in the target number of UEs in each cell, that are assigned ANR specific thresholds for EUTRAN inter-frequency neighbor cell reports, every time a neighbor cell report for HO is received with unknown neighbor cells.";
      yexte:takes-effect "New connection";
      type erienmnrmlrat:ddt-Lrat_AnrFunctionEUtran_anrUesThreshInterFIncrHo;
      default 100;
    }
    leaf cellAddRsrqThresholdEutran {
      description "Threshold value for reported quality for a cell to be automatically added as neighbor.\n";
      type erienmnrmlrat:ddt-Lrat_AnrFunctionEUtran_cellAddRsrqThresholdEutran;
      default -1530;
    }
  } // end 'grouping moc-AnrFunctionEUtran'
  grouping moc-TermPointToSGW-keys {
    description "Key(s) for MOC TermPointToSGW";
    leaf id {
      erienmyext:no-notification;
      description "The value component of the RDN.";
      mandatory true;
      yexte:ecim-name termPointToSGWId;
      type string;
    }
  } // end 'grouping moc-TermPointToSGW-keys'
  grouping moc-TermPointToSGW {
    description "Models SGW termination point of S1 link between RBS and SGW node.\n\nThe RDNs of these MOs are TermPointToSGW=1 to TermPointToSGW=64.";
    leaf usedIpAddress {
      erienmyext:no-notification;
      config false;
      description "Remote address used for SGW termination point. Can be IPv4 or IPv6 address.";
      type erienmnrmlrat:ddt-Lrat_TermPointToSGW_usedIpAddress;
    }
    leaf timeOfCreation {
      erienmyext:no-notification;
      config false;
      description "Time and date when MO was created. Format: YYYY-MM-DD HH:MM:SS";
      type erienmnrmlrat:ddt-Lrat_TermPointToSGW_timeOfCreation;
    }
  } // end 'grouping moc-TermPointToSGW'
  grouping moc-UtranTDDFreqRelation-keys {
    description "Key(s) for MOC UtranTDDFreqRelation";
    leaf id {
      erienmyext:no-notification;
      description "The value component of the Relative Distinguished Name (RDN).";
      mandatory true;
      yexte:ecim-name utranTDDFreqRelationId;
      type string;
    }
  } // end 'grouping moc-UtranTDDFreqRelation-keys'
  grouping moc-UtranTDDFreqRelation {
    description "This Managed Object represents a UTRAN TDD mobility relation between a EUtranCellFDD or EUtranCellTDD and a UtranFrequency. It contains parameters that are specific for this relation.\n\nDeleting this MO while the parent EUtranCellFDD/EUtranCellTDD has operationalState set to ENABLED is not recommended as it may affect traffic.";
    leaf userLabel {
      description "Label for free use.";
      type erienmnrmlrat:ddt-Lrat_UtranTDDFreqRelation_userLabel;
    }
    leaf csFallbackPrio {
      description "Prioritizes UTRAN frequencies among all frequencies related to the cell for UEs in connected mode.\nSets the priority to which frequency/frequency group to make CS Fallback to.\nThe value -1 means the frequency is excluded.\nThe value 0 means the lowest priority.\nThe value 7 means the highest priority.";
      yexte:takes-effect "New connection";
      type erienmnrmlrat:ddt-Lrat_UtranTDDFreqRelation_csFallbackPrio;
      default 0;
    }
    leaf connectedModeMobilityPrio {
      description "Prioritizes UTRA frequencies among all frequencies related to the cell for UEs in connected mode.\n(0 means the lowest priority. -1 means the frequency is excluded.)";
      yexte:takes-effect "New connection";
      type erienmnrmlrat:ddt-Lrat_UtranTDDFreqRelation_connectedModeMobilityPrio;
      default 6;
    }
    leaf mobilityActionCsfb {
      description "The preferred way to transfer a UE in connected mode to a UTRAN TDD frequency in case of CS Fallback mobility.";
      type erienmnrmlrat:enum-MobilityActionCsfbUtranTDD;
      default HANDOVER;
    }
    leaf b2Thr1RsrqUtraFreqOffset {
      description "The frequency-relation specific offset for the absolute threshold b2Threshold1Rsrq, RSRQ threshold1 for event B2, used for Multi-Layer Service-Triggered Mobility.";
      yexte:takes-effect "Ongoing connection";
      type erienmnrmlrat:ddt-Lrat_UtranTDDFreqRelation_b2Thr1RsrqUtraFreqOffset;
      default 0;
    }
    list qciB2ThrOffsets {
      min-elements 0;
      max-elements 23;
      key auto-generated-struct-key;
      leaf auto-generated-struct-key {
        type uint16;
        description "This leaf has been injected to allow for struct instances in a sequence to be ordered.";
        mandatory true;
      }
      description "Parameters for adding QCI profile and frequency relation specific offsets to B2 threshold values used for mobility decisions. Applicable if Multi-Layer Service-Triggered Mobility (MLSTM) is active";
      erienmyext:enm-type STRUCT;
      uses erienmnrmlrat:struct-UtranFreqToQciProfileRelation;
    } // end 'list qciB2ThrOffsets'
    leaf utranFrequencyRef {
      yexte:restricted;
      description "Reference to the UTRAN frequency MO, UtranFrequency.";
      erienmyext:enm-type MOREF;
      type string;
    }
    leaf mobilityAction {
      description "The preferred way to transfer a UE in connected mode to a UTRAN TDD frequency in case of coverage triggered mobility.";
      yexte:takes-effect "New connection";
      type erienmnrmlrat:enum-MobilityActionUtran;
      default HANDOVER;
    }
    leaf pMaxUtra {
      description "The maximum allowed transmission power on the (uplink) carrier frequency, see TS 25.304.";
      type erienmnrmlrat:ddt-Lrat_UtranTDDFreqRelation_pMaxUtra;
      default 33;
    }
    list allowedPlmnList {
      min-elements 0;
      max-elements 15;
      key auto-generated-struct-key;
      leaf auto-generated-struct-key {
        type uint16;
        description "This leaf has been injected to allow for struct instances in a sequence to be ordered.";
        mandatory true;
      }
      description "List of all Public Land Mobile Network (PLMN) IDs allowed for this frequency relation.\n\nA UE that does not support one of the IDs included in the allowedPlmnList does not measure on this frequency, according to the UE Handover Restriction List.\n\nNo values in allowedPlmnList imply that the frequency has no restrictions for PLMN.\n\nThe PLMN ID contains the following parts:\n1. MobileCountryCode, MCC, 3 digits\n2. MobileNetworkCode, MNC, 2 or 3 digits (the correct number of digits is set in the mncLength member of this Struct)\n\nFor example, if MCC=125 and MNC=46, then plmnId=12546.";
      erienmyext:enm-type STRUCT;
      uses erienmnrmlrat:struct-PlmnIdentity;
    } // end 'list allowedPlmnList'
    leaf b2Thr2RscpUtraFreqOffset {
      description "The frequency-relation specific offset for the absolute threshold b2Threshold2Rscp, RSCP in the ThresholdUTRATDD for event B2, used for Multi-Layer Service-Triggered Mobility.";
      yexte:takes-effect "Ongoing connection";
      type erienmnrmlrat:ddt-Lrat_UtranTDDFreqRelation_b2Thr2RscpUtraFreqOffset;
      default 0;
    }
    leaf threshXLow {
      description "This specifies the threshold used in reselection towards frequency X priority from a higher priority frequency. Each frequency of UTRAN might have a specific threshold. Parameter \"Threshx,low\" in TS 36.304.";
      type erienmnrmlrat:ddt-Lrat_UtranTDDFreqRelation_threshXLow;
      default 0;
    }
    leaf threshXHigh {
      description "This specifies the threshold used by the UE when reselecting towards the higher priority frequency X than current serving frequency. Each frequency of UTRAN might have a specific threshold. Parameter \"Threshx,high\" in TS 36.304";
      type erienmnrmlrat:ddt-Lrat_UtranTDDFreqRelation_threshXHigh;
      default 4;
    }
    leaf anrMeasOn {
      description "ANR performs measurement on the referenced frequency if this parameter is set to true. Otherwise, ANR does not perform any measurements on this frequency.";
      yexte:takes-effect "New connection";
      type boolean;
      default true;
    }
    leaf qRxLevMin {
      description "Parameter Qrxlevmin, see TS 25.304. Specifies the minimum required Rx level in the cell expressed in dBm.";
      type erienmnrmlrat:ddt-Lrat_UtranTDDFreqRelation_qRxLevMin;
      default -119;
    }
    leaf b2Thr1RsrpUtraFreqOffset {
      description "The frequency-relation specific offset for the absolute threshold b2Threshold1Rsrp, RSRP threshold1 for event B2, used for Multi-Layer Service-Triggered Mobility.";
      yexte:takes-effect "Ongoing connection";
      type erienmnrmlrat:ddt-Lrat_UtranTDDFreqRelation_b2Thr1RsrpUtraFreqOffset;
      default 0;
    }
    leaf cellReselectionPriority {
      description "CellReselectionPriority concerns the absolute priority of the concerned carrier frequency, as used by the cell reselection procedure. Corresponds with parameter \"priority\" in TS 36.304.\nValue 0 means lowest priority. The UE behaviour for the case the field is absent, if applicable, is specified in TS 36.304.";
      yexte:dependencies "The value must be unique and not already used by other RAT, i.e. equal priorities between RATs are not supported.";
      type erienmnrmlrat:ddt-Lrat_UtranTDDFreqRelation_cellReselectionPriority;
      default 6;
    }
    leaf csFallbackPrioEC {
      description "Prioritizes UTRAN frequencies for emergency calls among all frequencies/frequency groups related to the cell for UEs in connected mode.\nSets the priority to which frequency to make emergency call CS Fallback to.\nThe value -1 means the frequency is excluded.\nThe value 0 means the lowest priority.\nThe value 7 means the highest priority.";
      yexte:takes-effect "New connection";
      type erienmnrmlrat:ddt-Lrat_UtranTDDFreqRelation_csFallbackPrioEC;
      default 0;
    }
    leaf qOffsetFreq {
      description "Indicates a frequency-specific offset to apply when evaluating triggering conditions for measurement reporting.";
      yexte:takes-effect "New connection";
      type erienmnrmlrat:ddt-Lrat_UtranTDDFreqRelation_qOffsetFreq;
      default 0;
    }
  } // end 'grouping moc-UtranTDDFreqRelation'
  grouping moc-PtmStmConfig-keys {
    description "Key(s) for MOC PtmStmConfig";
    leaf id {
      erienmyext:no-notification;
      description "The value component of the RDN.";
      mandatory true;
      yexte:ecim-name ptmStmConfigId;
      type string;
    }
  } // end 'grouping moc-PtmStmConfig-keys'
  grouping moc-PtmStmConfig {
    description "Contains PTM specific parameters affecting Subscriber Triggered Mobility feature.\n\nThe RDN of this MO is PtmStmConfig=1.";
    leaf-list ptmSubscriberGroupRef {
      min-elements 0;
      max-elements 12;
      description "Reference to an instance of PtmSubscriberGroup MO Class.\nIf PtmCellProfile::cellType is set to NON_PRIORITY, specifies PTM Subscriber Groups inhibited for Idle Mode Prioritization.\nIf empty, functionality is disabled.\nNo effect when PtmCellProfile::cellType is set to PRIORITY.";
      yexte:disturbances "Changing this attribute can affect traffic.";
      erienmyext:enm-type MOREF;
      type string;
    }
    leaf inhibitImpInterval {
      description "Time interval when Inhibit Idle Mode Prioritization function is applied for UEs included in subscriber groups.";
      yexte:disturbances "Changing this attribute can affect traffic.";
      type erienmnrmlrat:ddt-Lrat_PtmStmConfig_inhibitImpInterval;
      default 60;
    }
  } // end 'grouping moc-PtmStmConfig'
  grouping moc-ReportConfigB2Geran-keys {
    description "Key(s) for MOC ReportConfigB2Geran";
    leaf id {
      erienmyext:no-notification;
      description "The value component of the Relative Distinguished Name (RDN).";
      mandatory true;
      yexte:ecim-name reportConfigB2GeranId;
      type string;
    }
  } // end 'grouping moc-ReportConfigB2Geran-keys'
  grouping moc-ReportConfigB2Geran {
    description "This managed object contains report configuration settings for the B2 event for GERAN measurements. The B2 event is used to detect when a GERAN cell becomes better than threshold2, and serving cell becomes worse than threshold1. The actual threshold values used can be adjusted by frequency relation related offsets if the feature Multi-Layer Service-Triggered Mobility (MLSTM) is enabled.\n\nThe RDN of this MO is ReportConfigB2Geran=1.";
    leaf b2Threshold1Rsrp {
      description "The Reference Signal Received Power (RSRP) threshold1 value for eventB2.";
      yexte:takes-effect "New connection";
      yexte:dependencies "Only used if triggerQuantityB2 is set to RSRP.";
      type erienmnrmlrat:ddt-Lrat_ReportConfigB2Geran_b2Threshold1Rsrp;
      default -140;
    }
    leaf b2Threshold1Rsrq {
      description "The Reference Signal Received Quality (RSRQ) threshold1 value for eventB2.";
      yexte:takes-effect "New connection";
      yexte:dependencies "Only used if triggerQuantityB2 is set to RSRQ.";
      type erienmnrmlrat:ddt-Lrat_ReportConfigB2Geran_b2Threshold1Rsrq;
      default -195;
    }
    leaf triggerQuantityB2 {
      description "The quantity for threshold1 (serving EUTRAN cell) that is sent to the UE, and is used together with threshold2 to trigger the eventB2.";
      yexte:takes-effect "New connection";
      type erienmnrmlrat:enum-TriggerQuantity;
      default RSRP;
    }
    leaf hysteresisB2RsrqOffset {
      description "Offset to obtain the Hysteresis for B2 measurement for trigger quantity RSRQ. hysteresisB2Rsrq = hysteresisB2 + hysteresisB2RsrqOffset";
      yexte:takes-effect "New connection";
      yexte:dependencies "Feature Mobility Control at Poor Coverage must be active.";
      type erienmnrmlrat:ddt-Lrat_ReportConfigB2Geran_hysteresisB2RsrqOffset;
      default 0;
    }
    leaf timeToTriggerB2Rsrq {
      description "Time-to-trigger value for event B2 with trigger quantity RSRQ. If set to -1, attribute is not used for report configuration.";
      yexte:takes-effect "New connection";
      yexte:dependencies "Feature Mobility Control at Poor Coverage must be active.";
      type erienmnrmlrat:ddt-Lrat_ReportConfigB2Geran_timeToTriggerB2Rsrq;
      default -1;
    }
    leaf hysteresisB2 {
      description "The hysteresis value for the eventB2 measurement";
      yexte:takes-effect "New connection";
      type erienmnrmlrat:ddt-Lrat_ReportConfigB2Geran_hysteresisB2;
      default 10;
    }
    leaf b2Threshold2Geran {
      description "The Signal Quality in the ThresholdGERAN, threshold2 value for eventB2.";
      yexte:takes-effect "New connection";
      type erienmnrmlrat:ddt-Lrat_ReportConfigB2Geran_b2Threshold2Geran;
      default -110;
    }
    leaf timeToTriggerB2 {
      description "Time-to-trigger value for event B2 measurements. If timeToTriggerB2Rsrq is -1, this attribute is used for both RSRP and RSRQ. But if not set to -1, this attribute is used only for RSRP.";
      yexte:takes-effect "New connection";
      type erienmnrmlrat:ddt-Lrat_ReportConfigB2Geran_timeToTriggerB2;
      default 640;
    }
  } // end 'grouping moc-ReportConfigB2Geran'
  grouping moc-EranInterMeLink-keys {
    description "Key(s) for MOC EranInterMeLink";
    leaf id {
      erienmyext:no-notification;
      description "The value component of the RDN.";
      mandatory true;
      yexte:ecim-name eranInterMeLinkId;
      type string;
    }
  } // end 'grouping moc-EranInterMeLink-keys'
  grouping moc-EranInterMeLink {
    description "Models a eRAN link between a ME and a neighboring ME.\n\nThe RDNs of these MOs are EranInterMeLink=1 to EranInterMeLink=4.";
    leaf eranVlanPortRef {
      erienmyext:no-notification;
      config false;
      description "Refers to the VlanPort instance used by the EranInterMeLink and its BbLinks.";
      erienmyext:enm-type MOREF;
      type string;
    }
    leaf localPort {
      erienmyext:no-notification;
      config false;
      description "The EthernetPortId for the local end of the EranInterMeLink.";
      type erienmnrmlrat:ddt-Lrat_EranInterMeLink_localPort;
    }
    leaf linkLatency15minHWM {
      erienmyext:no-notification;
      config false;
      description "The highest latency measured during the last completed 15 minute period.";
      type erienmnrmlrat:ddt-Lrat_EranInterMeLink_linkLatency15minHWM;
    }
    leaf remotePort {
      erienmyext:no-notification;
      config false;
      description "The EthernetPortId for the remote end of the EranInterMeLink.";
      type erienmnrmlrat:ddt-Lrat_EranInterMeLink_remotePort;
    }
    leaf-list availabilityStatus {
      min-elements 0;
      erienmyext:no-notification;
      config false;
      description "The availability status. It contains details about operationalState.";
      type erienmnrmlrat:enum-AvailStatus;
    }
    leaf operationalState {
      erienmyext:no-notification;
      config false;
      description "The operational state.";
      type erienmnrmlrat:enum-OperState;
    }
    leaf linkLatency1minAvg {
      erienmyext:no-notification;
      config false;
      description "The average latency measured during the last 1 minute period.";
      type erienmnrmlrat:ddt-Lrat_EranInterMeLink_linkLatency1minAvg;
    }
    leaf linkLatency24hrsHWM {
      erienmyext:no-notification;
      config false;
      description "The highest latency measured during the last 24hrs.";
      type erienmnrmlrat:ddt-Lrat_EranInterMeLink_linkLatency24hrsHWM;
    }
  } // end 'grouping moc-EranInterMeLink'
  grouping moc-EUtranFreqRelationUnlicensed-keys {
    description "Key(s) for MOC EUtranFreqRelationUnlicensed";
    leaf id {
      erienmyext:no-notification;
      description "The value component of the RDN.";
      mandatory true;
      yexte:ecim-name eUtranFreqRelationUnlicensedId;
      type string;
    }
  } // end 'grouping moc-EUtranFreqRelationUnlicensed-keys'
  grouping moc-EUtranFreqRelationUnlicensed {
    description "MO represents mobility relation between EUtranCellFDD (or-TDD) and EUtranFrequencyUnlicensed. Contains parameters specific for this relation.\nOne instance of this MO must refer to Band46UnlicensedProfile MO.";
    leaf userLabel {
      description "Label for free use.";
      type erienmnrmlrat:ddt-Lrat_EUtranFreqRelationUnlicensed_userLabel;
    }
    leaf caFreqProportion {
      description "In conjunction with caFreqPriority the value sets a threshold for the number of SCells on this frequency carrier that can be configured using prioritized SCell selection. A normalized value is applied. When frequency carriers have same priority, SCells are selected on the carrier with the lowest proportional SCell utilization.";
      yexte:takes-effect "New connection";
      yexte:dependencies "Only applicable when CarrierAggregationFunction::dynamicSCellSelectionMethod == PRIORITIZED.";
      type erienmnrmlrat:ddt-Lrat_EUtranFreqRelationUnlicensed_caFreqProportion;
      default 100;
    }
    list allowedPlmnList {
      min-elements 0;
      max-elements 15;
      key auto-generated-struct-key;
      leaf auto-generated-struct-key {
        type uint16;
        description "This leaf has been injected to allow for struct instances in a sequence to be ordered.";
        mandatory true;
      }
      description "Lists all Public Land Mobile Network (PLMN) IDs allowed for this frequency relation.\nA UE that does not support a PLMN included in allowedPlmnList does not measure on this frequency according to the UE Handover Restriction List.\nNo values in allowedPlmnList imply that the frequency has no restrictions for PLMN.\nThe PLMN identity consists of the following parts:\n1. MobileCountryCode, MCC, 3 digits\n2. MobileNetworkCode, MNC, 2 or 3 digits (the correct number of digits is set in the mncLength member of this Struct)\nFor example, if MCC=125 and MNC=46, then plmnId=12546.";
      status deprecated {
        yexte:status-information "Since 17.Q2. Has no functional behavior. Planned to be removed.";
      }
      erienmyext:enm-type STRUCT;
      uses erienmnrmlrat:struct-PlmnIdentity;
    } // end 'list allowedPlmnList'
    leaf band46UnlicensedProfileRef {
      status deprecated {
        yexte:status-information "Since 17.Q2. Has no functional behavior. Planned to be removed.";
      }
      yexte:restricted;
      description "Refers to Band46UnlicensedProfile MO.";
      erienmyext:enm-type MOREF;
      type string;
    }
    leaf unlicensedBandProfileRef {
      description "Refers to UnlicensedBandProfile MO.";
      mandatory true;
      erienmyext:enm-type MOREF;
      type string;
    }
    leaf allowedMeasBandwidth {
      description "The maximum allowed measurement bandwidth on a carrier frequency.\nNote: The values indicate the number of resource blocks and correspond to the channel bandwidth 1,4MHz, 3MHz, 5MHz, 10MHz, 15MHz, 20MHz respectively specified in 3GPP TS 36.104.";
      type erienmnrmlrat:ddt-Lrat_EUtranFreqRelationUnlicensed_allowedMeasBandwidth;
      default 100;
    }
    leaf caFreqPriority {
      description "Prioritizes EUTRAN frequency carriers from which to pick SCells for carrier aggregation. 0 means lowest priority. -1 means the frequency is excluded from SCell selection.";
      yexte:takes-effect "New connection";
      yexte:dependencies "Only applicable when CarrierAggregationFunction::dynamicSCellSelectionMethod == PRIORITIZED.";
      type erienmnrmlrat:ddt-Lrat_EUtranFreqRelationUnlicensed_caFreqPriority;
      default 7;
    }
  } // end 'grouping moc-EUtranFreqRelationUnlicensed'
  grouping moc-GeraNetwork-keys {
    description "Key(s) for MOC GeraNetwork";
    leaf id {
      erienmyext:no-notification;
      description "The value component of the Relative Distinguished Name (RDN).\n";
      mandatory true;
      yexte:ecim-name geraNetworkId;
      type string;
    }
  } // end 'grouping moc-GeraNetwork-keys'
  grouping moc-GeraNetwork {
    description "This managed object represents a Gera network.\n";
    leaf userLabel {
      description "Label for free use.\n";
      type erienmnrmlrat:ddt-Lrat_GeraNetwork_userLabel;
    }
  } // end 'grouping moc-GeraNetwork'
  grouping moc-ReportConfigA1Sec-keys {
    description "Key(s) for MOC ReportConfigA1Sec";
    leaf id {
      erienmyext:no-notification;
      description "The value component of the Relative Distinguished Name (RDN).";
      mandatory true;
      yexte:ecim-name reportConfigA1SecId;
      type string;
    }
  } // end 'grouping moc-ReportConfigA1Sec-keys'
  grouping moc-ReportConfigA1Sec {
    description "This managed object contains report configuration settings for the secondary A1 event measurements. The A1 event is used to the detect traffic-related Bad Coverage Cease condition.\nPrimary and secondary reporting configuration MOs refer to the option to use different settings for two simultaneous measurements for the event A1.\n\nThe RDN of this MO is ReportConfigA1Sec=1.";
    leaf timeToTriggerA1Sec {
      description "The time-to-trigger value for the secondary eventA1 measurement.";
      yexte:takes-effect "New connection";
      type erienmnrmlrat:ddt-Lrat_ReportConfigA1Sec_timeToTriggerA1Sec;
      default 640;
    }
    leaf hysteresisA1Sec {
      description "The hysteresis value for the secondary eventA1 measurement.";
      yexte:takes-effect "New connection";
      type erienmnrmlrat:ddt-Lrat_ReportConfigA1Sec_hysteresisA1Sec;
      default 10;
    }
    leaf a1ThrRsrpSecOffsetCeABr {
      description "CAT-M UE in CE mode A Good coverage Offset for the absolute threshold a1ThresholdRsrpSec.";
      yexte:takes-effect "New connection";
      type erienmnrmlrat:ddt-Lrat_ReportConfigA1Sec_a1ThrRsrpSecOffsetCeABr;
      default 0;
    }
    leaf a1ThresholdRsrpSec {
      description "The Reference Signal Received Power (RSRP) threshold value for the secondary eventA1.";
      yexte:takes-effect "New connection";
      yexte:dependencies "Only used if triggerQuantityA2Sec is set to RSRP.";
      type erienmnrmlrat:ddt-Lrat_ReportConfigA1Sec_a1ThresholdRsrpSec;
      default -136;
    }
    leaf a1ThresholdRsrqSec {
      description "The Reference Signal Received Quality (RSRQ) threshold value for the secondary eventA1.";
      yexte:takes-effect "New connection";
      yexte:dependencies "Only used if triggerQuantityA2Sec is set to RSRQ.";
      type erienmnrmlrat:ddt-Lrat_ReportConfigA1Sec_a1ThresholdRsrqSec;
      default -195;
    }
  } // end 'grouping moc-ReportConfigA1Sec'
  grouping moc-CellPortion-keys {
    description "Key(s) for MOC CellPortion";
    leaf id {
      erienmyext:no-notification;
      description "The value component of the RDN.";
      mandatory true;
      yexte:ecim-name cellPortionId;
      type string;
    }
  } // end 'grouping moc-CellPortion-keys'
  grouping moc-CellPortion {
    description "This MO represents the area within a Cell, which can be used for feature, e.g. UE Positioning.";
    leaf altitude {
      description "The altitude of the transmitter antenna in meters. Use +/- values to denote height/depth.";
      type erienmnrmlrat:ddt-Lrat_CellPortion_altitude;
      default 0;
    }
    container cellPortionCoverage {
      description "Models the cell portion coverage area used for UE positioning. The cell portion coverage area is defined by the bearing, opening angle and radius.";
      erienmyext:enm-type STRUCT;
      uses erienmnrmlrat:struct-EutranCellArea;
    } // end 'container cellPortionCoverage'
    leaf latitude {
      description "The degree of latitude of the transmitter antenna position.";
      type erienmnrmlrat:ddt-Lrat_CellPortion_latitude;
      default 0;
    }
    list cellPortionPolygon {
      min-elements 0;
      max-elements 15;
      key auto-generated-struct-key;
      leaf auto-generated-struct-key {
        type uint16;
        description "This leaf has been injected to allow for struct instances in a sequence to be ordered.";
        mandatory true;
      }
      description "Models the manageable characteristics for the cell portion polygon used for UE. positioning. Each polygon corner is described by a latitude and longitude pair. Each polygon corner is represented with one position in the sequence. The other configured polygon corners follow in sequence.";
      erienmyext:enm-type STRUCT;
      uses erienmnrmlrat:struct-EutranCellCorner;
    } // end 'list cellPortionPolygon'
    leaf longitude {
      description "The degree of longitude of the transmitter antenna position.";
      type erienmnrmlrat:ddt-Lrat_CellPortion_longitude;
      default 0;
    }
    leaf lppaCellPortionId {
      description "The LPPa Cell Portion ID IE defined in 3GPP TS 36.455.";
      type erienmnrmlrat:ddt-Lrat_CellPortion_lppaCellPortionId;
      default 0;
    }
    leaf sectorCarrierRef {
      description "Reference to an instance of SectorCarrier MO.";
      erienmyext:enm-type MOREF;
      type string;
    }
  } // end 'grouping moc-CellPortion'
  grouping moc-ReportConfigA1A2Br-keys {
    description "Key(s) for MOC ReportConfigA1A2Br";
    leaf id {
      erienmyext:no-notification;
      description "The value component of the RDN.";
      mandatory true;
      yexte:ecim-name reportConfigA1A2BrId;
      type string;
    }
  } // end 'grouping moc-ReportConfigA1A2Br-keys'
  grouping moc-ReportConfigA1A2Br {
    description "Contains report configuration settings for A1/A2 measurements for CAT-M UE.\n\nThe RDN of this MO is ReportConfigA1A2Br=1.";
    leaf a1a2UlIntraSearchIntraFThr {
      description "UL-normalized SINR max threshold for events A1 UL and A2 UL search.";
      type erienmnrmlrat:ddt-Lrat_ReportConfigA1A2Br_a1a2UlIntraSearchIntraFThr;
      default 340;
    }
    leaf hysteresisA1A2UlIntraFSearch {
      description "Hysteresis value for UL events A1 UL search and A2 UL search intra-frequency measurements.";
      type erienmnrmlrat:ddt-Lrat_ReportConfigA1A2Br_hysteresisA1A2UlIntraFSearch;
      default 20;
    }
    leaf timeToTriggerA1UlIntraFSearch {
      description "Time-to-trigger value for uplink intra-frequency measurement in event A1UlSearch.";
      type erienmnrmlrat:ddt-Lrat_ReportConfigA1A2Br_timeToTriggerA1UlIntraFSearch;
      default 40;
    }
    leaf timeToTriggerA2UlIntraFSearch {
      description "Time-to-trigger value for uplink intra-frequency measurement in event A2UlSearch.";
      type erienmnrmlrat:ddt-Lrat_ReportConfigA1A2Br_timeToTriggerA2UlIntraFSearch;
      default 40;
    }
  } // end 'grouping moc-ReportConfigA1A2Br'
  grouping moc-MbsfnAreaCellRelation-keys {
    description "Key(s) for MOC MbsfnAreaCellRelation";
    leaf id {
      erienmyext:no-notification;
      description "The value component of the Relative Distinguished Name (RDN).";
      mandatory true;
      yexte:ecim-name mbsfnAreaCellRelationId;
      type string;
    }
  } // end 'grouping moc-MbsfnAreaCellRelation-keys'
  grouping moc-MbsfnAreaCellRelation {
    description "This managed object represents the relationship between a MBSFN Area and a EUTRAN cell.";
    leaf userLabel {
      description "Label for free use.";
      type erienmnrmlrat:ddt-Lrat_MbsfnAreaCellRelation_userLabel;
    }
    leaf mbsfnAreaCellRef {
      yexte:restricted;
      description "Reference to a related EUtranCell that supports the MBSFN Area.";
      mandatory true;
      erienmyext:enm-type MOREF;
      type string;
    }
    leaf isReservedCell {
      yexte:restricted;
      description "Defines if the related EUtranCell in MBSFN Area reserved cell or not. A Reserved Cell is a unicast cell. No data is sent in the MBSFN subframes. The Cell CSR (cell specific reference) will be sent as a normal unicast cell.";
      type boolean;
      default false;
    }
    leaf mbsfnAreaCellStatus {
      config false;
      description "The MBSFN area status of the related Cell.";
      notife:notifiable-state-data true;
      type erienmnrmlrat:enum-MbsfnAreaCellStatus;
    }
  } // end 'grouping moc-MbsfnAreaCellRelation'
  grouping moc-ReportConfigSCellA6-keys {
    description "Key(s) for MOC ReportConfigSCellA6";
    leaf id {
      erienmyext:no-notification;
      description "The value component of the Relative Distinguished Name (RDN).";
      mandatory true;
      yexte:ecim-name reportConfigSCellA6Id;
      type string;
    }
  } // end 'grouping moc-ReportConfigSCellA6-keys'
  grouping moc-ReportConfigSCellA6 {
    description "This managed object contains the report configuration settings for A6 measurements on the frequency of any serving SCell when this cell is used as PCell.\n\nThe RDN of this MO is ReportConfigSCellA6=1.";
    leaf a6offset {
      description "The offset value for event A6.\nChanged value may take effect related to the next SCell configuration during the ongoing connection.";
      yexte:takes-effect "Ongoing connection";
      type erienmnrmlrat:ddt-Lrat_ReportConfigSCellA6_a6offset;
      default 30;
    }
    leaf timeToTriggerA6 {
      description "The time-to-trigger value for event A6.\nChanged value may take effect related to the next SCell configuration during the ongoing connection.";
      yexte:takes-effect "Ongoing connection";
      type erienmnrmlrat:ddt-Lrat_ReportConfigSCellA6_timeToTriggerA6;
      default 40;
    }
    leaf triggerQuantityA6 {
      description "The quantity that triggers the event.\nChanged value may take effect related to the next SCell configuration during the ongoing connection.";
      yexte:takes-effect "Ongoing connection";
      type erienmnrmlrat:enum-TriggerQuantity;
      default RSRP;
    }
    leaf hysteresisA6 {
      description "The hysteresis value for event A6.\nChanged value may take effect related to the next SCell configuration during the ongoing connection.";
      yexte:takes-effect "Ongoing connection";
      type erienmnrmlrat:ddt-Lrat_ReportConfigSCellA6_hysteresisA6;
      default 10;
    }
  } // end 'grouping moc-ReportConfigSCellA6'
  grouping moc-SubscriberProfileID-keys {
    description "Key(s) for MOC SubscriberProfileID";
    leaf id {
      erienmyext:no-notification;
      description "The value component of the RDN";
      mandatory true;
      yexte:ecim-name subscriberProfileIDId;
      type string;
    }
  } // end 'grouping moc-SubscriberProfileID-keys'
  grouping moc-SubscriberProfileID {
    description "Parent for all SPID related MOCs";
    leaf userLabel {
      description "Label for free use.\n";
      type erienmnrmlrat:ddt-Lrat_SubscriberProfileID_userLabel;
    }
  } // end 'grouping moc-SubscriberProfileID'
  grouping moc-ReportConfigSCellA4-keys {
    description "Key(s) for MOC ReportConfigSCellA4";
    leaf id {
      erienmyext:no-notification;
      description "The value component of the Relative Distinguished Name (RDN).";
      mandatory true;
      yexte:ecim-name reportConfigSCellA4Id;
      type string;
    }
  } // end 'grouping moc-ReportConfigSCellA4-keys'
  grouping moc-ReportConfigSCellA4 {
    description "This managed object contains the report configuration settings for A4 measurements on the frequency of any non-serving SCell candidate when this cell is used as PCell.\nNote: This MO class is valid only for FDD cells.\n\nThe RDN of this MO is ReportConfigSCellA4=1.";
    leaf a4ThresholdRsrq {
      description "The Reference Signal Received Quality (RSRQ) threshold value for eventA4.\nChanged value may take effect related to the next SCell configuration during the ongoing connection.";
      yexte:takes-effect "Ongoing connection";
      yexte:dependencies "Only used if triggerQuantityA4 is set to RSRQ.";
      type erienmnrmlrat:ddt-Lrat_ReportConfigSCellA4_a4ThresholdRsrq;
      default -195;
    }
    leaf triggerQuantityA4 {
      description "The quantity that triggers the eventA4 for the eventA4 measurement.\nChanged value may take effect related to the next SCell configuration during the ongoing connection.";
      yexte:takes-effect "Ongoing connection";
      type erienmnrmlrat:enum-TriggerQuantity;
      default RSRP;
    }
    leaf hysteresisA4 {
      description "The hysteresis value for the eventA4 measurement.\nChanged value may take effect related to the next SCell configuration during the ongoing connection.";
      yexte:takes-effect "Ongoing connection";
      type erienmnrmlrat:ddt-Lrat_ReportConfigSCellA4_hysteresisA4;
      default 10;
    }
    leaf a4ThresholdRsrp {
      description "The Reference Signal Received Power (RSRP) threshold value for eventA4.\nChanged value may take effect related to the next SCell configuration during the ongoing connection.";
      yexte:takes-effect "Ongoing connection";
      yexte:dependencies "Only used if triggerQuantityA4 is set to RSRP.";
      type erienmnrmlrat:ddt-Lrat_ReportConfigSCellA4_a4ThresholdRsrp;
      default -140;
    }
    leaf timeToTriggerA4 {
      description "The time-to-trigger value for the eventA4 measurement.\nChanged value may take effect related to the next SCell configuration during the ongoing connection.";
      yexte:takes-effect "Ongoing connection";
      type erienmnrmlrat:ddt-Lrat_ReportConfigSCellA4_timeToTriggerA4;
      default 640;
    }
  } // end 'grouping moc-ReportConfigSCellA4'
  grouping moc-PtmCellProfile-keys {
    description "Key(s) for MOC PtmCellProfile";
    leaf id {
      erienmyext:no-notification;
      description "The value component of the RDN.";
      mandatory true;
      yexte:ecim-name ptmCellProfileId;
      type string;
    }
  } // end 'grouping moc-PtmCellProfile-keys'
  grouping moc-PtmCellProfile {
    description "Parameters that can be used to define a PTM Cell Profile, describing per cell configuration of Preferential Traffic Management. PtmCellProfile can be referenced from multiple cells on the eNodeB by using EUtranCellFDD.PtmCellProfileRef or EUtranCellTDD.PtmCellProfileRef.";
    container atoConfig {
      description "PTM-specific parameters affecting Admission Triggered Offload.";
      status deprecated {
        yexte:status-information "Since 18.Q4. Has no functional behavior. Planned to be removed.";
      }
      erienmyext:enm-type STRUCT;
      uses erienmnrmlrat:struct-AtoConfig;
    } // end 'container atoConfig'
    leaf cellType {
      description "PTM-specific actions triggered on every cell referencing this PtmCellProfile.\nValue PRIORITY enables IFO, ATO, Cell Reserved For Operator Use related actions, and sending of Traffic Load States to neighboring cells. Value NON_PRIORITY allows evaluation of Traffic Load States and related IFLB, STM actions.";
      yexte:disturbances "Changing this attribute can affect traffic.";
      type erienmnrmlrat:enum-PtmCellType;
      default NON_PRIORITY;
    }
    container ifoConfig {
      description "PTM-specific parameters affecting Inter-Frequency Offload.";
      status deprecated {
        yexte:status-information "Since 18.Q4. Has no functional behavior. Planned to be removed.";
      }
      erienmyext:enm-type STRUCT;
      uses erienmnrmlrat:struct-IfoConfig;
    } // end 'container ifoConfig'
    leaf-list reservedBy {
      min-elements 0;
      config false;
      description "Contains a list of MO instances that reserve this MO instance.";
      notife:notifiable-state-data true;
      erienmyext:enm-type MOREF;
      type string;
    }
    container resOpUseConfig {
      description "PTM-specific parameters affecting the Cell Reserved For Operator Use functionality.";
      status deprecated {
        yexte:status-information "Since 18.Q4. Has no functional behavior. Planned to be removed.";
      }
      erienmyext:enm-type STRUCT;
      uses erienmnrmlrat:struct-ResOpUseConfig;
    } // end 'container resOpUseConfig'
    container iflbConfig {
      description "PTM-specific parameters affecting Inter-Frequency Load Balancing.";
      status deprecated {
        yexte:status-information "Since 18.Q4. Has no functional behavior. Planned to be removed.";
      }
      erienmyext:enm-type STRUCT;
      uses erienmnrmlrat:struct-IflbConfig;
    } // end 'container iflbConfig'
    container stmConfig {
      description "PTM-specific parameters affecting Subscriber Triggered Mobility.";
      status deprecated {
        yexte:status-information "Since 18.Q4. Has no functional behavior. Planned to be removed.";
      }
      erienmyext:enm-type STRUCT;
      uses erienmnrmlrat:struct-StmConfig;
    } // end 'container stmConfig'
  } // end 'grouping moc-PtmCellProfile'
  grouping moc-ExternalUtranCellTDD-keys {
    description "Key(s) for MOC ExternalUtranCellTDD";
    leaf id {
      erienmyext:no-notification;
      description "The value component of the Relative Distinguished Name (RDN).";
      mandatory true;
      yexte:ecim-name externalUtranCellTDDId;
      type string;
    }
  } // end 'grouping moc-ExternalUtranCellTDD-keys'
  grouping moc-ExternalUtranCellTDD {
    description "This Managed Object contains a UTRAN cell for TDD (Time Division Duplex).";
    leaf userLabel {
      description "Label for free use.";
      type erienmnrmlrat:ddt-Lrat_ExternalUtranCellTDD_userLabel;
    }
    leaf rimAssociationStatus {
      config false;
      description "This parameter indicates the current status of the RIM association to this external cell.";
      notife:notifiable-state-data true;
      type erienmnrmlrat:enum-RIMAssociationStatus;
    }
    leaf timeOfCreation {
      erienmyext:no-notification;
      config false;
      description "Indicates the time and date when the MO was created by the Automated Neighbor Relations (ANR) function or operator. Format: \"YYYY-MM-DD HH:MM:SS\"";
      type erienmnrmlrat:ddt-Lrat_ExternalUtranCellTDD_timeOfCreation;
    }
    leaf masterUtranCellId {
      description "The identity of the UtranCell represented by this MO, particularly for automatically created ExternalUtranCell managed objects. The masterUtranCellId is set to the Full Distinguished Name (FDN).";
      type erienmnrmlrat:ddt-Lrat_ExternalUtranCellTDD_masterUtranCellId;
      default "";
    }
    container cellIdentity {
      description "UTRAN Cell Identity.\nUsed to identity the cell uniquely within UTRAN Iu mode.";
      erienmyext:enm-type STRUCT;
      uses erienmnrmlrat:struct-CellIdentityUtra;
    } // end 'container cellIdentity'
    leaf physicalCellIdentity {
      description "Indicates the physical layer identity of the cell, that is, the primary scrambling code.";
      mandatory true;
      yexte:takes-effect "New connection";
      type erienmnrmlrat:ddt-Lrat_ExternalUtranCellTDD_physicalCellIdentity;
    }
    leaf timeOfLastModification {
      config false;
      description "The date and time when the MO was last modified by the Automated Neighbor Relations (ANR) function or operator. Format: YYYY-MM-DD HH:MM:SS";
      notife:notifiable-state-data true;
      type erienmnrmlrat:ddt-Lrat_ExternalUtranCellTDD_timeOfLastModification;
    }
    leaf lac {
      description "The Location Area Code of the external UTRAN cell. A fixed-length code identifying the location area within a PLMN. Refer to 3GPP TS 23.003.\nThe value 0 of the attribute is used to mark invalid/unusable lac information for the cell. For example, handover to an external UTRAN cell (that is part of a Utran cell relation) can be considered only if the value of the lac attribute is NOT 0.";
      yexte:disturbances "Changes may affect traffic";
      type erienmnrmlrat:ddt-Lrat_ExternalUtranCellTDD_lac;
      default 0;
    }
    leaf rimCapable {
      description "This parameter indicates if the external UTRAN cell is RIM capable. If the value is RIMIncapable, no attempt will be made to create a RIM association to the external UTRAN cell, other values will result in a attempt to create a RIM association.";
      yexte:disturbances "If the value is other than RIMIncapable the eNB will try to set up a RIM association to the external cell";
      type erienmnrmlrat:enum-RIMCapability;
      default RIM_CAPABLE;
    }
    leaf rac {
      description "The Routing Area Code of a routing area.\nThe value -1 of the attribute is used to mark that the optional RAC IE should NOT be sent in the Target ID IE of the HANDOVER REQUIRED S1 message. Refer to 3GPP TS 36.413.";
      yexte:disturbances "Changes may affect traffic";
      type erienmnrmlrat:ddt-Lrat_ExternalUtranCellTDD_rac;
      default -1;
    }
    leaf createdBy {
      erienmyext:no-notification;
      config false;
      description "Indicates whether the MO has been created by the Automated Neighbor Relations (ANR) function or operator.";
      type erienmnrmlrat:enum-CreatedByIrat;
    }
    leaf isRemoveAllowed {
      description "Indicates if the Automated Neighbor Relations (ANR) function is allowed to remove this object. It does not restrict operator removal of the object. Objects created by ANR have this parameter set to true initially.";
      type boolean;
      default false;
    }
    leaf lastModification {
      config false;
      description "Indicates whether the MO has been last modified by the Automated Neighbor Relations (ANR) function or operator.";
      notife:notifiable-state-data true;
      type erienmnrmlrat:enum-LastModificationUtran;
    }
    container plmnIdentity {
      description "PLMN ID supported by the cell.\n";
      erienmyext:enm-type STRUCT;
      uses erienmnrmlrat:struct-PlmnIdentity;
    } // end 'container plmnIdentity'
    leaf-list reservedBy {
      min-elements 0;
      config false;
      description "Contains a list of MO instances that reserve this MO instance.";
      notife:notifiable-state-data true;
      erienmyext:enm-type MOREF;
      type string;
    }
    action changeFrequency {
      description "Changes the frequency of the external cell. This MO action includes the following steps:\n - Create the UtranFrequency MO (with the specified arfcnValueUtranDl) if it does not already exist.\n - Create the UtranTDDFreqRelation MO (using default values for attributes) if it does not already exist.\n - Create a new ExternalUtranCellTDD MO (with the same attribute values as the existing ExternalUtranCellTDD MO) under the specified UtranFrequency MO.\n - For each UtranCellRelation to the old ExternalUtranCellTDD, create a new UtranCellRelation MO (with the same attribute values as the existing UtranCellRelation MO) referring to the new ExternalUtranCellTDD MO. The old UtranCellRelation MOs are then removed.\n - Remove the old ExternalUtranCellTDD MO. This will be performed after successful execution of this MO action. ";
      input {
        leaf arfcnValueUtranDl {
          mandatory true;
          description "The new DL frequency for this cell.";
          type erienmnrmlrat:ddt-ExternalUtranCellTDD_changeFrequency_arfcnValueUtranDl;
        }
      }
    }
  } // end 'grouping moc-ExternalUtranCellTDD'
  grouping moc-ExternalGUtranCell-keys {
    description "Key(s) for MOC ExternalGUtranCell";
    leaf id {
      erienmyext:no-notification;
      description "The value component of the RDN.";
      mandatory true;
      yexte:ecim-name externalGUtranCellId;
      type string;
    }
  } // end 'grouping moc-ExternalGUtranCell-keys'
  grouping moc-ExternalGUtranCell {
    description "This managed object contains a GUtran cell.";
    leaf physicalLayerSubCellId {
      description "Unique subidentity within group. Physical layer cell identities are grouped into 336 unique physical layer cell identity groups, each group containing 3 unique subidentities.";
      mandatory true;
      type erienmnrmlrat:ddt-Lrat_ExternalGUtranCell_physicalLayerSubCellId;
    }
    leaf gUtranSyncSignalFrequencyRef {
      yexte:restricted;
      description "Reference to an instance of GUtranSyncSignalFrequency.";
      erienmyext:enm-type MOREF;
      type string;
    }
    leaf-list reservedBy {
      min-elements 0;
      config false;
      description "Contains a list of MO instances that reserve this MO instance.";
      yexte:dependencies "The managed object cannot be deleted if it is reserved.";
      notife:notifiable-state-data true;
      erienmyext:enm-type MOREF;
      type string;
    }
    leaf physicalLayerCellIdGroup {
      description "Physical layer cell identity group. Physical layer cell identities are grouped into 336 unique physical layer cell identity groups, each group containing 3 unique subidentities.";
      mandatory true;
      type erienmnrmlrat:ddt-Lrat_ExternalGUtranCell_physicalLayerCellIdGroup;
    }
    leaf localCellId {
      description "RBS internal ID for ExternalGUtranCell. Must be unique in RBS. Together with Node ID and PLMN ID this is a globally unique NR Cell ID (NR CGI).";
      mandatory true;
      yexte:dependencies "localCellId =< (2^(36-ExternalGNodeBFunction::gNodeBIdLength))-1";
      type erienmnrmlrat:ddt-Lrat_ExternalGUtranCell_localCellId;
    }
  } // end 'grouping moc-ExternalGUtranCell'
  grouping moc-ResourcePartitionGroupMember-keys {
    description "Key(s) for MOC ResourcePartitionGroupMember";
    leaf id {
      erienmyext:no-notification;
      description "The value component of the RDN.";
      mandatory true;
      yexte:ecim-name resourcePartitionGroupMemberId;
      type string;
    }
  } // end 'grouping moc-ResourcePartitionGroupMember-keys'
  grouping moc-ResourcePartitionGroupMember {
    description "Specifies a resource partition configuration and the share of resources it should be granted in the cell.";
    leaf resourcePartitionRef {
      description "Reference to an instance of ResourcePartition MO.";
      mandatory true;
      yexte:disturbances "Changing this attribute can affect traffic.";
      yexte:takes-effect "Cell lock/unlock";
      erienmyext:enm-type MOREF;
      type string;
    }
    leaf resourcePartitionShare {
      description "Share of scheduling resources available to a resource partition.\nPartitions may use more than their share as long as there are free resources remaining in the cell but in a congested network the additional resources may instead be used to fulfill the shares of other partitions.";
      mandatory true;
      yexte:disturbances "Changing this attribute can affect traffic.";
      yexte:takes-effect "Cell lock/unlock";
      type erienmnrmlrat:ddt-Lrat_ResourcePartitionGroupMember_resourcePartitionShare;
    }
  } // end 'grouping moc-ResourcePartitionGroupMember'
  grouping moc-TermPointToLbm-keys {
    description "Key(s) for MOC TermPointToLbm";
    leaf id {
      erienmyext:no-notification;
      description "The value component of the Relative Distinguished Name (RDN).";
      mandatory true;
      yexte:ecim-name termPointToLbmId;
      type string;
    }
  } // end 'grouping moc-TermPointToLbm-keys'
  grouping moc-TermPointToLbm {
    description "Designates endpoints from a baseband unit on the local eNodeB to reach a particular baseband unit on the remote eNodeB indicated by TermPointToENB.\n\nThe RDNs of these MOs are TermPointToLbm=1 to TermPointToLbm=27.";
    leaf operationalState {
      erienmyext:no-notification;
      config false;
      description "Operational state of inter-eNodeB tunnels.";
      type erienmnrmlrat:enum-OperState;
    }
  } // end 'grouping moc-TermPointToLbm'
  grouping moc-ReportConfigA5Anr-keys {
    description "Key(s) for MOC ReportConfigA5Anr";
    leaf id {
      erienmyext:no-notification;
      description "The value component of the Relative Distinguished Name (RDN).";
      mandatory true;
      yexte:ecim-name reportConfigA5AnrId;
      type string;
    }
  } // end 'grouping moc-ReportConfigA5Anr-keys'
  grouping moc-ReportConfigA5Anr {
    description "The Automated Neighbor Relations (ANR) delta report configuration settings for the A5 event measurements as compared to mobility provided in the parent MO class.\n\nThe RDN of this MO is ReportConfigA5Anr=1.";
    leaf a5Threshold2RsrqAnrDelta {
      description "This parameter together with a5Threshold2Rsrq specifies \"The Reference Signal Received Quality (RSRQ) threshold2 value for eventA5.\" . The equation for calculating the RSRQ threshold2 value for ANR is a5Threshold2Rsrq -a5Threshold2RsrqAnrDelta . Only used if triggerQuantityA5 onReportConfigA5 MO is set to RSRQ.";
      yexte:takes-effect "New connection";
      yexte:dependencies "Not pure dependence towards parameter on ReportConficA5 Mo, but there should be a check that this attribute and corresponding attribute on ReportConfigA5 MO together sends out a valid number to the UE";
      type erienmnrmlrat:ddt-Lrat_ReportConfigA5Anr_a5Threshold2RsrqAnrDelta;
      default 10;
    }
    leaf a5Threshold1RsrqAnrDelta {
      description "This parameter together with a5Threshold1Rsrq specifies \"The Reference Signal Received Quality (RSRQ) threshold1 value for eventA5.\" . The equation for calculating the RSRQ threshold1 value for ANR is a5Threshold1Rsrq + a5Threshold1RsrqAnrDelta . Only used if triggerQuantityA5 onReportConfigA5 MO is set to RSRQ.";
      yexte:takes-effect "New connection";
      yexte:dependencies "Not pure dependence towards parameter on ReportConficA5 Mo, but there should be a check that this attribute and corresponding attribute on ReportConfigA5 MO together sends out a valid number to the UE";
      type erienmnrmlrat:ddt-Lrat_ReportConfigA5Anr_a5Threshold1RsrqAnrDelta;
      default 10;
    }
    leaf a5Threshold2RsrpAnrDelta {
      description "This parameter together with a5Threshold2Rsrp specifies \"The Reference Signal Received Power (RSRP) threshold2 value for eventA5.\" . The equation for calculating the RSRP threshold2 value for ANR is a5Threshold2Rsrp - a5Threshold2RsrpAnrDelta . Only used if triggerQuantityA5 onReportConfigA5 MO is set to RSRP.";
      yexte:takes-effect "New connection";
      yexte:dependencies "Not pure dependence towards parameter on ReportConficA5 Mo, but there should be a check that this attribute and corresponding attribute on ReportConfigA5 MO together sends out a valid number to the UE";
      type erienmnrmlrat:ddt-Lrat_ReportConfigA5Anr_a5Threshold2RsrpAnrDelta;
      default 1;
    }
    leaf a5Threshold1RsrpAnrDelta {
      description "This parameter together with a5Threshold1Rsrp specifies \"The Reference Signal Received Power (RSRP) threshold1 value for eventA5.\" . The equation for calculating the RSRP threshold1 value for ANR is a5Threshold1Rsrp + a5Threshold1RsrpAnrDelta . Only used if triggerQuantityA5 onReportConfigA5 MO is set to RSRP.";
      yexte:takes-effect "New connection";
      yexte:dependencies "Not pure dependence towards parameter on ReportConficA5 Mo, but there should be a check that this attribute and corresponding attribute on ReportConfigA5 MO together sends out a valid number to the UE";
      type erienmnrmlrat:ddt-Lrat_ReportConfigA5Anr_a5Threshold1RsrpAnrDelta;
      default 1;
    }
    leaf timeToTriggerA5 {
      description "The time-to-trigger value for the eventA5 measurement.";
      yexte:takes-effect "New connection";
      type erienmnrmlrat:ddt-Lrat_ReportConfigA5Anr_timeToTriggerA5;
      default 640;
    }
    leaf hysteresisA5 {
      description "The hysteresis value for the eventA5 measurement.";
      yexte:takes-effect "New connection";
      type erienmnrmlrat:ddt-Lrat_ReportConfigA5Anr_hysteresisA5;
      default 10;
    }
  } // end 'grouping moc-ReportConfigA5Anr'
  grouping moc-UnlicensedAccessFunction-keys {
    description "Key(s) for MOC UnlicensedAccessFunction";
    leaf id {
      erienmyext:no-notification;
      description "The value component of the RDN.";
      mandatory true;
      yexte:ecim-name unlicensedAccessFunctionId;
      type string;
    }
  } // end 'grouping moc-UnlicensedAccessFunction-keys'
  grouping moc-UnlicensedAccessFunction {
    description "Definitions of LAA properties, for example LBT and DRS attributes.";
    leaf laaChannelEvaluationTimer {
      description "When timer expires, channel evaluation is performed to find better carrier. Only applicable for Dynamic Channel Selection.";
      yexte:takes-effect "Next cell unlock";
      type erienmnrmlrat:ddt-Lrat_UnlicensedAccessFunction_laaChannelEvaluationTimer;
      default 180;
    }
    leaf laaLbtCheckTimer {
      description "When timer expires, LBT success rate is evaluated. If less than threshold, new channel evaluation is performed to find better carrier.\nOnly applicable for Dynamic Channel Selection.";
      yexte:takes-effect "Next cell unlock";
      type erienmnrmlrat:ddt-Lrat_UnlicensedAccessFunction_laaLbtCheckTimer;
      default 900;
    }
    leaf laaDrsOffset {
      description "Offset of DRS within a DMTC. Depending on DRS periodicity, the value can be set within the ranges 0-39, 0-79 or 0-159.";
      yexte:takes-effect "Cell lock/unlock";
      yexte:dependencies "laaDrsOffset < laaDrsPeriodicity";
      type erienmnrmlrat:ddt-Lrat_UnlicensedAccessFunction_laaDrsOffset;
      default 5;
    }
    leaf laaSCellActDeactDataThres {
      description "SCells can be activated if minimum time needed to transmit all bits in all priority queues of UE is higher than laaSCellActDeactDataThres.\nMinimum time is calculated as number of bits in all priority queues, divided by number of bits that can be transmitted in one TTI by all active serving cells (prior to activation decision). Computed as if UE is given all resources in those cells.\nIf condition for activating one SCell is satisfied, a second SCell is also considered for activation. Minimum time needed to transmit all bits is now re-calculated with added capacity of new SCell. Another SCell is added if still over threshhold.\n\"-1\" means data-triggered activation condition is always satisfied even with no data in buffer, and also that data-triggered deactivation condition is never satisfied\nOnly used if LAA is configured in RBS.";
      yexte:takes-effect "Next cell unlock";
      yexte:dependencies "laaSCellActDeactDataThresHyst <= laaSCellActDeactDataThres when sCellActDeactDataThres is not equal to -1.";
      type erienmnrmlrat:ddt-Lrat_UnlicensedAccessFunction_laaSCellActDeactDataThres;
      default 100;
    }
    leaf laaSCellActDeactDataThresHyst {
      description "Deactivation of one component carrier is considered if:\nminimum time to transmit all bits in all priority queues of a UE is less than or equal to laaSCellActDeactDataThres minus laaSCellActDeactDataThresHyst.\nMinimum time is calculated as number of bits in all priority queues, divided by number of bits that can be transmitted in one TTI by all active serving cells (after deactivation decision). Computed as if UE is given all resources in those cells.\nIf laaSCellActDeactDataThres is set to \"-1\", data-triggered deactivation condition is never satisfied and value of laaSCellActDeactDataThresHyst is ignored.";
      yexte:takes-effect "Next cell unlock";
      yexte:dependencies "laaSCellActDeactDataThresHyst <= laaSCellActDeactDataThres when sCellActDeactDataThres is not equal to -1.";
      type erienmnrmlrat:ddt-Lrat_UnlicensedAccessFunction_laaSCellActDeactDataThresHyst;
      default 90;
    }
    leaf laaMaxOccupancy {
      description "Duration of SCell occupancy. Complies with regulations for maximum transmission time.";
      yexte:takes-effect "Cell lock/unlock";
      type erienmnrmlrat:ddt-Lrat_UnlicensedAccessFunction_laaMaxOccupancy;
      default 8;
    }
    leaf laaChannelSelectionType {
      description "Selects channel selection type:\n- Static channel selection configures carriers according to UnlicensedBandProfile.\n- Dynamic channel selection dynamically chooses best available channels.";
      yexte:takes-effect "Next cell unlock";
      type erienmnrmlrat:enum-ChannelSelectionType;
      default DYNAMIC_CHANNEL_SELECTION;
    }
    leaf laaMasterCarrierTimer {
      description "For future use.\nWhen timer expires, LBT master carrier is evaluated to get best master carrier. Only applicable for Multi-Carrier Access type B.";
      yexte:takes-effect "Next cell unlock";
      type erienmnrmlrat:ddt-Lrat_UnlicensedAccessFunction_laaMasterCarrierTimer;
      default 10;
    }
    leaf laaDrsPeriodicity {
      description "Periodicity of DRS.";
      yexte:takes-effect "Cell lock/unlock";
      yexte:dependencies "laaDrsOffset < laaDrsPeriodicity";
      type erienmnrmlrat:ddt-Lrat_UnlicensedAccessFunction_laaDrsPeriodicity;
      default 40;
    }
    leaf laaLbtSuccessRateThreshold {
      description "Level of LBT success rate for an acceptable LAA carrier. If less than threshold, new carrier is considered. Only applicable for Dynamic Channel Selection.";
      yexte:takes-effect "Next cell unlock";
      type erienmnrmlrat:ddt-Lrat_UnlicensedAccessFunction_laaLbtSuccessRateThreshold;
      default 50;
    }
  } // end 'grouping moc-UnlicensedAccessFunction'
  grouping moc-EricssonLeanCarrierFunction-keys {
    description "Key(s) for MOC EricssonLeanCarrierFunction";
    leaf id {
      erienmyext:no-notification;
      description "The value component of the RDN.";
      mandatory true;
      yexte:ecim-name ericssonLeanCarrierFunctionId;
      type string;
    }
  } // end 'grouping moc-EricssonLeanCarrierFunction-keys'
  grouping moc-EricssonLeanCarrierFunction {
    description "Contains set of Ericsson Lean Carrier feature related parameters.\nAttributes take effect only if license for Ericsson Lean Carrier is present and the feature is active.\n\nThe RDN of this MO is EricssonLeanCarrierFunction=1.";
    leaf elcDrxOnDurationPostHeating {
      description "Defines a number of subframes after the end of the hardcoded ELC DRX onDurationTimer where full spectrum CRS:es are transmitted.";
      yexte:takes-effect "Next cell unlock";
      yexte:dependencies "Only relevant if EUtranCellFDD/EUtranCellTDD::elcEnabled is true.";
      type erienmnrmlrat:ddt-Lrat_EricssonLeanCarrierFunction_elcDrxOnDurationPostHeating;
      default 4;
    }
    leaf elcPdcchCrsMuting {
      description "Enables Ericsson Lean Carrier PDCCH CRS muting functionality.";
      yexte:takes-effect "Next cell unlock";
      yexte:dependencies "Only relevant if EUtranCellFDD/EUtranCellTDD::elcEnabled is true.";
      type boolean;
      default true;
    }
    leaf elcDrxOnDurationPreHeating {
      description "Defines a number of subframes before the start of the hardcoded ELC DRX onDurationTimer where full spectrum CRS:es are transmitted.";
      yexte:takes-effect "Next cell unlock";
      yexte:dependencies "Only relevant if EUtranCellFDD/EUtranCellTDD::elcEnabled is true.";
      type erienmnrmlrat:ddt-Lrat_EricssonLeanCarrierFunction_elcDrxOnDurationPreHeating;
      default 3;
    }
    leaf disableElcOnVolte {
      description "Disable ELC when VoLTE bearer is set up in the cell.";
      yexte:takes-effect "Next cell unlock";
      yexte:dependencies "Only relevant if EUtranCellFDD/EUtranCellTDD::elcEnabled is true.";
      type boolean;
      default false;
    }
  } // end 'grouping moc-EricssonLeanCarrierFunction'
  grouping moc-PmUlInterferenceReport-keys {
    description "Key(s) for MOC PmUlInterferenceReport";
    leaf id {
      erienmyext:no-notification;
      description "The value component of the RDN.";
      mandatory true;
      yexte:ecim-name pmUlInterferenceReportId;
      type string;
    }
  } // end 'grouping moc-PmUlInterferenceReport-keys'
  grouping moc-PmUlInterferenceReport {
    description "Contains RF branch information used for the feature Uplink Interference Reporting. Created when the feature license is activated.\n\nThe RDNs of these MOs are PmUlInterferenceReport=1 to PmUlInterferenceReport=8.";
    leaf rfBranchRxRef {
      config false;
      description "Reference to the instance of RfBranch MO used for the feature Uplink Interference Reporting.";
      notife:notifiable-state-data true;
      erienmyext:enm-type MOREF;
      type string;
    }
  } // end 'grouping moc-PmUlInterferenceReport'
  grouping moc-ReportConfigEUtraInterFreqLb-keys {
    description "Key(s) for MOC ReportConfigEUtraInterFreqLb";
    leaf id {
      erienmyext:no-notification;
      description "The value component of the Relative Distinguished Name (RDN).";
      mandatory true;
      yexte:ecim-name reportConfigEUtraInterFreqLbId;
      type string;
    }
  } // end 'grouping moc-ReportConfigEUtraInterFreqLb-keys'
  grouping moc-ReportConfigEUtraInterFreqLb {
    description "Contains the Report Configuration settings for UE measurements initiated for EUTRA Inter-frequency Load Balancing.\n\nThe RDN of this MO is ReportConfigEUtraInterFreqLb=1.";
    leaf a5Threshold2Rsrq {
      description "The Reference Signal Received Quality (RSRQ) threshold2 value for eventA5.";
      yexte:disturbances "Changing this attribute can affect traffic";
      type erienmnrmlrat:ddt-Lrat_ReportConfigEUtraInterFreqLb_a5Threshold2Rsrq;
      default -195;
    }
    leaf a5Threshold2Rsrp {
      description "The Reference Signal Received Power (RSRP) threshold2 value for eventA5.";
      yexte:disturbances "Changing this attribute can affect traffic";
      type erienmnrmlrat:ddt-Lrat_ReportConfigEUtraInterFreqLb_a5Threshold2Rsrp;
      default -44;
    }
    leaf hysteresisA5 {
      description "The hysteresis value for the eventA5 measurement.";
      yexte:disturbances "Changing this attribute can affect traffic";
      type erienmnrmlrat:ddt-Lrat_ReportConfigEUtraInterFreqLb_hysteresisA5;
      default 10;
    }
    leaf a5Threshold1Rsrp {
      description "The Reference Signal Received Power (RSRP) threshold1 value for eventA5.";
      yexte:disturbances "Changing this attribute can affect traffic";
      type erienmnrmlrat:ddt-Lrat_ReportConfigEUtraInterFreqLb_a5Threshold1Rsrp;
      default -44;
    }
  } // end 'grouping moc-ReportConfigEUtraInterFreqLb'
  grouping moc-UtranFrequency-keys {
    description "Key(s) for MOC UtranFrequency";
    leaf id {
      erienmyext:no-notification;
      description "The value component of the Relative Distinguished Name (RDN).\n";
      mandatory true;
      yexte:ecim-name utranFrequencyId;
      type string;
    }
  } // end 'grouping moc-UtranFrequency-keys'
  grouping moc-UtranFrequency {
    description "This Managed Object contains information of a specific Utran frequency.\n";
    leaf userLabel {
      description "Label for free use.\n";
      type erienmnrmlrat:ddt-Lrat_UtranFrequency_userLabel;
    }
    leaf arfcnValueUtranDl {
      yexte:restricted;
      description "Indicates the ARFCN applicable for a downlink UTRA carrier frequency, as defined in 3GPP TS 25.331.\nAllowed ARFCN values are specified in 3GPP TS 25.101 (UTRAN FDD) and 3GPP TS 25.102 (UTRAN TDD).";
      mandatory true;
      type erienmnrmlrat:ddt-Lrat_UtranFrequency_arfcnValueUtranDl;
    }
    leaf-list reservedBy {
      min-elements 0;
      config false;
      description "Contains a list of MO instances that reserve this MO instance.\n";
      notife:notifiable-state-data true;
      erienmyext:enm-type MOREF;
      type string;
    }
  } // end 'grouping moc-UtranFrequency'
  grouping moc-Paging-keys {
    description "Key(s) for MOC Paging";
    leaf id {
      erienmyext:no-notification;
      description "The value component of the RDN.\n";
      mandatory true;
      yexte:ecim-name pagingId;
      type string;
    }
  } // end 'grouping moc-Paging-keys'
  grouping moc-Paging {
    description "Configuration parameters for Paging feature in the RBS and applies to all cells.\n\nThe RDN of this MO is Paging=1.";
    leaf nBNbIot {
      description "Used to calculate number and position of NB IoT PO and NB IoT PF.\nWhen nBNbIot is set to T, it determines PO number for each PF, and PO position in PF. When nBNbIot is smaller than T, it affects System Frame Number of PF, PO position in PF, and UE distribution into groups with same PF.\nnBNbIot values of T2 and T4 are not allowed, as they result in grouping issues for paging occasions. T2 and T4 are converted to T.";
      yexte:takes-effect "Next cell unlock";
      type erienmnrmlrat:enum-NbValueNbIot;
      default T;
    }
    leaf pagingDiscardTimerEdrxNb {
      description "The time a received eDRX paging for NB-IoT is retained or queued in the RBS before it is discarded. Set to the same (or smaller) value as the paging resend timer in MME to prevent the RBS from retaining or sending an old paging after the re-sent copy is received from the MME.";
      yexte:takes-effect "After all the cells in the RBS have been locked, and subsequently been unlocked.";
      type erienmnrmlrat:ddt-Lrat_Paging_pagingDiscardTimerEdrxNb;
      default 31;
    }
    leaf pagingDiscardTimerDrxNb {
      description "The length of time a received NB-IoT paging is retained or queued in the RBS before it is discarded. The timer should be set to the same (or smaller) value as the NB-IoT paging resend timer in MME (T3413). This setting prevents the RBS from retaining or sending an old paging after the re-sent copy is received from the MME.";
      type erienmnrmlrat:ddt-Lrat_Paging_pagingDiscardTimerDrxNb;
      default 6;
    }
    leaf pagingDiscardTimerNb {
      status deprecated {
        yexte:status-information "Since 17.Q4. Replaced by pagingDiscardTimerDrxNb. Planned to be removed.";
      }
      description "The time a received paging for NB-IoT is retained or queued in the RBS before it is discarded. Set to the same (or smaller) value as the paging resend timer in MME to prevent the RBS from retaining or sending an old paging after the re-sent copy is received from the MME.";
      yexte:takes-effect "After all the cells in the RBS have been locked, and subsequently been unlocked.";
      type erienmnrmlrat:ddt-Lrat_Paging_pagingDiscardTimerNb;
      default 3;
    }
    leaf noOfDefPagCyclPrim {
      description "Number of consecutive \"DefaultPagingCycles\" in which paging for Earthquake and Tsunami Warning System (ETWS) Primary Notification shall be transmitted in the RBS.";
      type erienmnrmlrat:ddt-Lrat_Paging_noOfDefPagCyclPrim;
      default 8;
    }
    leaf maxNoOfPagingRecords {
      description "The maximum allowed number of paging records included in one Radio Resource Control (RRC) paging message. It is the allowed maximum number of UE that can be paged per paging occasion.";
      yexte:takes-effect "After all the cells in the RBS have been locked, and subsequently been unlocked.";
      type erienmnrmlrat:ddt-Lrat_Paging_maxNoOfPagingRecords;
      default 3;
    }
    leaf defaultPagingCycleNbIot {
      description "NB IoT paging cycle (also called T) used by RBS and broadcast in NB-SIB2. For defaultPagingCycle 128, numRepetitionsPaging must not exceed 512. For defaultPagingCycle 256, numRepetitionsPaging must not exceed 1024.";
      yexte:takes-effect "After all the cells in the RBS have been locked, and subsequently been unlocked";
      type erienmnrmlrat:ddt-Lrat_Paging_defaultPagingCycleNbIot;
      default 256;
    }
    leaf maxNoOfPagingRecordsNb {
      description "The maximum allowed number of NB-IoT paging records included in one Radio Resource Control (RRC) paging message. It is the allowed maximum number of UE that can be paged per paging occasion.";
      yexte:takes-effect "After all the cells in the RBS have been locked, and subsequently been unlocked.";
      type erienmnrmlrat:ddt-Lrat_Paging_maxNoOfPagingRecordsNb;
      default 3;
    }
    leaf pagingDiscardTimerEdrx {
      description "The time a received eDRX paging is retained or queued in the RBS before it is discarded. Set to the same (or smaller) value as the paging resend timer in MME to prevent the RBS from retaining or sending an old paging after the re-sent copy is received from the MME.";
      yexte:takes-effect "After all the cells in the RBS have been locked, and subsequently been unlocked.";
      type erienmnrmlrat:ddt-Lrat_Paging_pagingDiscardTimerEdrx;
      default 13;
    }
    leaf pagingDiscardTimer {
      status deprecated {
        yexte:status-information "Since 17.Q4. Replaced by pagingDiscardTimerDrx. Planned to be removed.";
      }
      description "The length of time a received paging is retained or queued in the RBS before it is discarded. The timer should be set to the same (or smaller) value as the paging resend timer in MME (T3413). This setting  prevents the RBS from retaining or sending an old paging after the re-sent copy is received from the MME.";
      yexte:takes-effect "After all the cells in the RBS have been locked, and subsequently been unlocked.";
      type erienmnrmlrat:ddt-Lrat_Paging_pagingDiscardTimer;
      default 3;
    }
    leaf nB {
      description "Used to calculate the number and position of Paging Occasions (PO) and Paging Frames (PF).\nThe numerical value of nB depends on the value of the defaultPagingCycle (T) and can be set to one of the following values:\n4T, 2T, T, T/2, T/4, T/8, T/16, T/32.\nWhen nB is set to T, 2T or 4T, it determines the number of POs per PF, and the PO position in PF.\nWhen nB is set to a value smaller than T, it affects the System Frame Number of the PF, the position of PO in the PF, and also distribution of UE into groups with the same PF.\nWhen nB is set to smaller value, amount of groups is smaller, but amount of UEs inside each groups is larger. When nB is set to a larger value, amount of groups is larger but amount of UEs inside each groups is smaller.\nIf categoryMAccess is enabled and nBBr is set to the default value (NOT_PRESENT) then further restrictions apply. If highestSupportedCeLevelBr = 0 then nB should be selected from the following available options (T, T/2, T/4, T/8, T/16, T/32) due to the half duplex nature of Cat-M devices. If highestSupportedCeLevelBr = 1 then nB should be selected from the following available options (T/8, T/16, T/32) due to repetitions.";
      yexte:takes-effect "After all the cells in the RBS have been locked, and subsequently been unlocked.";
      yexte:dependencies "nB=T4 can not be used in combination with specialSubframePattern = 5 on MO EUtranCellTDD, see 3GPP TS 36.213.";
      type erienmnrmlrat:enum-NBValue;
      default T;
    }
    leaf numRepetitionsPagingNbIot {
      status deprecated {
        yexte:status-information "Since 17.Q4. Has no functional behavior. Planned to be removed.";
      }
      description "Maximum number of repetitions for NPDCCH common search space (CSS) for paging. Provided in NB-SIB2.";
      yexte:takes-effect "Next cell unlock";
      type erienmnrmlrat:ddt-Lrat_Paging_numRepetitionsPagingNbIot;
      default 1;
    }
    leaf defaultPagingCycle {
      description "Paging cycle (T). Used by RBS and broadcast in system information type 2. UE-specific DRX cycle overrides defaultPagingCycle if UE-specific DRX cycle is provided in S1AP paging. If extended Idle Mode DRX feature is active, paging cycle can be extended up to 262144 radio frames.";
      yexte:disturbances "If cell lock/unlock is not performed immediately after changing defaultPagingCycle, the number of discarded paging messages increases, and KPI drops.";
      yexte:takes-effect "After all cells in the RBS are locked and then unlocked. Lock/unlock cells manually, immediately after changing defaultPagingCycle.";
      yexte:dependencies "Parameter modificationPeriodCoeff * defaultPagingCycle must be equal or less than 1024 radio frames.";
      type erienmnrmlrat:ddt-Lrat_Paging_defaultPagingCycle;
      default 128;
    }
    leaf nBBr {
      description "Calculates number and position of POs and PFs for Bandwidth Reduced (BR) UEs.\nNumerical value of nBBr depends on value of defaultPagingCycle (T) and can be set to one of the following values based on Enhanced Paging Capacity (EPC):\n- If EPC is on, then set to T/8, T/16, T/32, T/64, T/128, T/256, and NOT_PRESENT.\n- If EPC is off, then set to T/64, T/128, T/256, and NOT_PRESENT.\nnBBr value affects the following:\n- SFN of PF\n- Position of PO in PF\n- Distribution of UE into groups with same PF\nWhen nBBr is set to a smaller value, amount of groups is smaller, but amount of UEs inside each group is larger.\nWhen nBBr is set to a larger value, amount of groups is larger but amount of UEs inside each group is smaller. nBBr value needs to be always >=1 . That is, if T=128, then nBBr >= T/128, meaning that there is at least one paging group. For more information, see 3GPP TS 36.304, Evolved Universal Terrestrial Radio Access (E-UTRA); User Equipment (UE) procedures in idle mode.\nWhen nBBr is set to NOT_PRESENT, attribute is not used. Instead, nB value is used to calculate PF and PO for CAT-M1 users.\nWhen nBBr is set to T/8, T/16, or T/32 and CatMEnhancedPaggingCapacity is operable, attribute is not used. Instead, nB with same value is used to calculate PF and PO for CAT-M1 users.\nWhen nBBr is set to T/8, T/16, or T/32 and CatMEnhancedPaggingCapacity is not operable, then default value (T/64) is used to calculate PF and PO for CAT-M1 users.\nnBBr values 4T, 2T, T, T/2, and T/4 are not allowed.";
      yexte:disturbances "Setting unallowed value, described as \"Undefined value\" in enumeration NBValueBr, can cause loss of all traffic in the eNodeB.";
      yexte:takes-effect "After all the cells in the RBS have been locked, and subsequently been unlocked.";
      type erienmnrmlrat:enum-NBValueBr;
      default T1_64;
    }
    leaf pagingDiscardTimerDrx {
      description "The length of time a received paging is retained or queued in the RBS before it is discarded. The timer should be set to the same (or smaller) value as the paging resend timer in MME (T3413). This setting prevents the RBS from retaining or sending an old paging after the re-sent copy is received from the MME.";
      yexte:takes-effect "After all the cells in the RBS have been locked, and subsequently been unlocked.";
      type erienmnrmlrat:ddt-Lrat_Paging_pagingDiscardTimerDrx;
      default 3;
    }
  } // end 'grouping moc-Paging'
  grouping moc-PrefTrafficMgmt-keys {
    description "Key(s) for MOC PrefTrafficMgmt";
    leaf id {
      erienmyext:no-notification;
      description "The value component of the RDN.";
      mandatory true;
      yexte:disturbances "Changing this attribute can affect traffic.";
      yexte:ecim-name prefTrafficMgmtId;
      type string;
    }
  } // end 'grouping moc-PrefTrafficMgmt-keys'
  grouping moc-PrefTrafficMgmt {
    description "Contains cell specific configuration for the preferential traffic management functionality.";
    leaf plmnResOpUseSRatioThreshold {
      description "Upper threshold for total subscription ratio. If total subscription ratio is above the threshold, triggers a broadcast of PLMN IDs configured in plmnsToReserveAtHighLoad as \"reserved for operator use\".";
      yexte:disturbances "Changing this attribute can affect traffic.";
      yexte:dependencies plmnResOpUseSRatioThreshold>plmnUnresOpUseSRatioThreshold;
      type erienmnrmlrat:ddt-Lrat_PrefTrafficMgmt_plmnResOpUseSRatioThreshold;
      default 70;
    }
    leaf-list inhibitSpidList {
      min-elements 0;
      max-elements 6;
      description "List that includes all UEs affected by function Inhibit Idle Mode Prioritization.";
      yexte:disturbances "Changing this attribute can affect traffic.";
      type erienmnrmlrat:ddt-Lrat_PrefTrafficMgmt_inhibitSpidList;
    }
    leaf plmnUnresOpUseMsrUsageThreshold {
      description "Lower threshold for monitored system resource usage.\nIf usage of all Monitored System Resources is below the threshold and the total subscription ratio is below plmnUnresOpUseSRatioThreshold, then broadcast PLMN IDs configured in plmnsToReserveAtHighLoad as \"unreserved\", if previously broadcasted as \"reserved for operator use\".";
      yexte:disturbances "Changing this attribute can affect traffic.";
      yexte:dependencies plmnResOpUseMSRUsageThreshold>plmnUnresOpUseMSRUsageThreshold;
      type erienmnrmlrat:ddt-Lrat_PrefTrafficMgmt_plmnUnresOpUseMsrUsageThreshold;
      default 40;
    }
    leaf atoAllowedFrom {
      description "Whether or not ATO is activated from current cell towards any frequency.";
      yexte:disturbances "Changing this attribute can affect traffic.";
      type boolean;
      default true;
    }
    leaf plmnResOpUseMsrUsageThreshold {
      description "Upper threshold for monitored system resource usage. If usage of some monitored system resource is above the threshold, triggers a broadcast of PLMN IDs configured in plmnsToReserveAtHighLoad as \"reserved for operator use\".";
      yexte:disturbances "Changing this attribute can affect traffic.";
      yexte:dependencies plmnResOpUseMSRUsageThreshold>plmnUnresOpUseMSRUsageThreshold;
      type erienmnrmlrat:ddt-Lrat_PrefTrafficMgmt_plmnResOpUseMsrUsageThreshold;
      default 70;
    }
    leaf highLoadPlmnReservedEnabled {
      description "Enable function to broadcast PLMN ID(s) as \"reserved for operator use\" at high load.";
      yexte:disturbances "Changing this attribute can affect traffic.";
      type boolean;
      default false;
    }
    list plmnsToReserveAtHighLoad {
      min-elements 0;
      max-elements 5;
      key auto-generated-struct-key;
      leaf auto-generated-struct-key {
        type uint16;
        description "This leaf has been injected to allow for struct instances in a sequence to be ordered.";
        mandatory true;
      }
      description "List of PLMN IDs; broadcasted as \"reserved for operator use\" when total subscription ratio or total usage of any monitored system resource exceeds threshold.";
      erienmyext:enm-type STRUCT;
      uses erienmnrmlrat:struct-PlmnIdentity;
    } // end 'list plmnsToReserveAtHighLoad'
    leaf lbStopIncomingIflbThreshold {
      description "Threshold for subscription ratio in cell. If exceeded, IFLB towards cell must be stopped.";
      yexte:disturbances "Changing this attribute can affect traffic.";
      yexte:dependencies lbStopIncomingIFLBThreshold<=lbEUtranTriggerOffloadThreshold;
      type erienmnrmlrat:ddt-Lrat_PrefTrafficMgmt_lbStopIncomingIflbThreshold;
      default 60;
    }
    leaf inhibitIMPrioritizationInterval {
      description "Time interval when Inhibit Idle Mode Prioritization function is applied for UEs whose SPIDs are defined in inhibitSpidList.";
      yexte:disturbances "Changing this attribute can affect traffic.";
      type erienmnrmlrat:ddt-Lrat_PrefTrafficMgmt_inhibitIMPrioritizationInterval;
      default 10;
    }
    leaf plmnUnresOpUseSRatioThreshold {
      description "Lower threshold for total subscription ratio.\nIf the total subscription ratio is below the threshold and usage of all Monitored System Resources is below plmnUnresOpUseMsrUsageThreshold, then broadcast PLMN IDs configured in plmnsToReserveAtHighLoad as \"unreserved\", if previously broadcasted as \"reserved for operator use\".";
      yexte:disturbances "Changing this attribute can affect traffic.";
      yexte:dependencies plmnResOpUseSRatioThreshold>plmnUnresOpUseSRatioThreshold;
      type erienmnrmlrat:ddt-Lrat_PrefTrafficMgmt_plmnUnresOpUseSRatioThreshold;
      default 55;
    }
    leaf sendStopIncomingIflbEnabled {
      description "Enable function to send load state Stop Incoming IFLB when subscription ratio level in cell is above threshold.";
      yexte:disturbances "Changing this attribute can affect traffic.";
      type boolean;
      default false;
    }
    leaf inhibitIMPrioritizationEnabled {
      description "Enable Inhibit Idle Mode Prioritization function for UEs whose SPIDs are defined in inhibitSpidList.";
      yexte:disturbances "Changing this attribute can affect traffic.";
      type boolean;
      default false;
    }
    leaf sendInhibitIMPrioritizationEnabled {
      description "Enable function to send load state Inhibit Idle Mode Prioritization when subscription ratio level in cell is above threshold.";
      yexte:disturbances "Changing this attribute can affect traffic.";
      type boolean;
      default false;
    }
    leaf stopOutgoingIflbEnabled {
      description "Enable function to stop IFLB from source cell to target cell, where the target cell previously signaled load state Stop Incoming IFLB.";
      yexte:disturbances "Changing this attribute can affect traffic.";
      type boolean;
      default false;
    }
    leaf-list spidBlacklistHo {
      min-elements 0;
      max-elements 6;
      description "List of UEs affected by sub-routine to block incoming handover when PLMN ID is broadcasted as \"reserved for operator use\".\nIf set to -1, UEs with no SPID value allocated are also affected by the sub-routine to block incoming handover when PLMN ID is broadcasted as \"reserved for operator use\".";
      yexte:disturbances "Changing this attribute can affect traffic.";
      type erienmnrmlrat:ddt-Lrat_PrefTrafficMgmt_spidBlacklistHo;
    }
  } // end 'grouping moc-PrefTrafficMgmt'
  grouping moc-CellResource-keys {
    description "Key(s) for MOC CellResource";
    leaf id {
      status deprecated {
        yexte:status-information "Since 18.Q2. Has no functional behavior. Planned to be removed.";
      }
      erienmyext:no-notification;
      description "The value component of the RDN.";
      mandatory true;
      yexte:ecim-name cellResourceId;
      type string;
    }
  } // end 'grouping moc-CellResource-keys'
  grouping moc-CellResource {
    description "A combination of attributes which specify which cell resource partition a given UE should be included in.";
    leaf resourceId {
      status deprecated {
        yexte:status-information "Since 18.Q2. Has no functional behavior. Planned to be removed.";
      }
      description "Cell Resource ID.";
      yexte:takes-effect "Next cell unlock";
      yexte:dependencies "Unique id among all CellResource MOs.";
      type erienmnrmlrat:ddt-Lrat_CellResource_resourceId;
      default 0;
    }
    leaf-list spidList {
      min-elements 0;
      max-elements 20;
      status deprecated {
        yexte:status-information "Since 18.Q2. Has no functional behavior. Planned to be removed.";
      }
      description "SPID values which shall be included in this cell resource partition. A cell resource partition with a spidList containing the value 0 will include UEs with no defined SPID value. Empty spidList will include all UE's with a SPID value not appearing in any other cell resource partition referred by cellResourceRef of EUtranCellFDD/TDD only when plmnList is empty.";
      yexte:takes-effect "Next cell unlock";
      yexte:dependencies "Can only be configured if plmnList is empty.";
      type erienmnrmlrat:ddt-Lrat_CellResource_spidList;
    }
    leaf-list reservedBy {
      min-elements 0;
      status deprecated {
        yexte:status-information "Since 18.Q2. Has no functional behavior. Planned to be removed.";
      }
      config false;
      description "Contains a list of MO instances that reserve this MO instance.";
      notife:notifiable-state-data true;
      erienmyext:enm-type MOREF;
      type string;
    }
    list plmnList {
      min-elements 0;
      max-elements 6;
      key auto-generated-struct-key;
      leaf auto-generated-struct-key {
        type uint16;
        description "This leaf has been injected to allow for struct instances in a sequence to be ordered.";
        mandatory true;
      }
      description "PLMNs which shall be included in this cell resource partition.";
      status deprecated {
        yexte:status-information "Since 18.Q2. Has no functional behavior. Planned to be removed.";
      }
      erienmyext:enm-type STRUCT;
      uses erienmnrmlrat:struct-PlmnIdentity;
    } // end 'list plmnList'
  } // end 'grouping moc-CellResource'
  grouping moc-ExternalGeranCell-keys {
    description "Key(s) for MOC ExternalGeranCell";
    leaf id {
      erienmyext:no-notification;
      description "The value component of the Relative Distinguished Name (RDN).";
      mandatory true;
      yexte:ecim-name externalGeranCellId;
      type string;
    }
  } // end 'grouping moc-ExternalGeranCell-keys'
  grouping moc-ExternalGeranCell {
    description "This Managed Object contains a GERAN cell.";
    leaf userLabel {
      description "Label for free use.";
      type erienmnrmlrat:ddt-Lrat_ExternalGeranCell_userLabel;
    }
    leaf rimAssociationStatus {
      config false;
      description "This parameter indicates the current status of the RIM association to this external cell.";
      notife:notifiable-state-data true;
      type erienmnrmlrat:enum-RIMAssociationStatus;
    }
    leaf bcc {
      description "Base station Colour Code (BCC). BCC and NCC together denote the physical cell identity for the GERAN cell (that is the Base Station Identity Code, BSIC).";
      mandatory true;
      yexte:disturbances "Changes may affect traffic";
      type erienmnrmlrat:ddt-Lrat_ExternalGeranCell_bcc;
    }
    leaf timeOfCreation {
      erienmyext:no-notification;
      config false;
      description "Indicates the date and time when the MO was created by the Automated Neighbor Relations (ANR) function or operator. Format: YYYY-MM-DD HH:MM:SS";
      type erienmnrmlrat:ddt-Lrat_ExternalGeranCell_timeOfCreation;
    }
    leaf cellIdentity {
      description "Cell Identifier that is unique within the context of the GERAN location area. Refer to 3GPP TS 23.003.";
      mandatory true;
      yexte:disturbances "Changes may affect traffic";
      type erienmnrmlrat:ddt-Lrat_ExternalGeranCell_cellIdentity;
    }
    leaf timeOfLastModification {
      config false;
      description "The date and time when the MO was last modified by the Automated Neighbor Relations (ANR) function or operator. Format: YYYY-MM-DD HH:MM:SS";
      notife:notifiable-state-data true;
      type erienmnrmlrat:ddt-Lrat_ExternalGeranCell_timeOfLastModification;
    }
    leaf lac {
      description "The Location Area Code of the external GERAN cell. A fixed-length code identifying the location area within a PLMN. Refer to 3GPP TS 23.003.\nSpecial values:\nThe values 0 and 65534 are reserved for special cases where no valid Location Area Identity (LAI) exists in the network.";
      mandatory true;
      yexte:disturbances "Changes may affect traffic";
      type erienmnrmlrat:ddt-Lrat_ExternalGeranCell_lac;
    }
    leaf ncc {
      description "Network Colour Code (NCC). BCC and NCC together denote the physical cell identity for the GERAN cell (that is the Base Station Identity Code, BSIC).";
      mandatory true;
      yexte:disturbances "Changes may affect traffic";
      type erienmnrmlrat:ddt-Lrat_ExternalGeranCell_ncc;
    }
    leaf dtmSupport {
      description "This attribute describes the Dual Transfer Mode (DTM) capability of the external cell.";
      type erienmnrmlrat:enum-DtmSupport;
      default NO_DTM_SUPPORT;
    }
    leaf masterGeranCellId {
      description "The identity of the GeranCell represented by this MO, particularly for automatically created ExternalGeranCell managed objects. The masterGeranCellId is set to the Full Distinguished Name (FDN).";
      type erienmnrmlrat:ddt-Lrat_ExternalGeranCell_masterGeranCellId;
      default "";
    }
    leaf geranFrequencyRef {
      yexte:restricted;
      description "Reference to GeranFrequency instance.\nIt is mandatory to supply a valid reference to a frequency at creation. To change the reference to a new Geran frequency, use action changeFrequency.";
      erienmyext:enm-type MOREF;
      type string;
    }
    leaf rimCapable {
      description "This parameter indicates if the external GERAN cell is RIM capable. If the value is RIMIncapable, no attempt will be made to create a RIM association to the external GERAN cell, other values will result in a attempt to create a RIM association.";
      yexte:disturbances "If the value is other than RIMIncapable the eNB will try to set up a RIM association to the external cell";
      type erienmnrmlrat:enum-RIMCapability;
      default RIM_CAPABLE;
    }
    leaf createdBy {
      erienmyext:no-notification;
      config false;
      description "Indicates whether the MO has been created by the Automated Neighbor Relations (ANR) function or operator.";
      type erienmnrmlrat:enum-CreatedByIrat;
    }
    leaf isRemoveAllowed {
      description "Indicates if the Automated Neighbor Relations (ANR) function is allowed to remove this object. It does not restrict operator removal of the object. Objects created by ANR have this parameter set to true initially.";
      type boolean;
      default true;
    }
    leaf rac {
      description "The Routing Area Code of a routing area.\nThe value -1 of the attribute is used to mark that no valid routing area code has been defined.";
      yexte:disturbances "Changes may affect traffic";
      type erienmnrmlrat:ddt-Lrat_ExternalGeranCell_rac;
      default -1;
    }
    leaf-list reservedBy {
      min-elements 0;
      config false;
      description "Contains a list of MO instances that reserve this MO instance.";
      notife:notifiable-state-data true;
      erienmyext:enm-type MOREF;
      type string;
    }
    container plmnIdentity {
      description "PLMN ID supported by the cell.\n";
      erienmyext:enm-type STRUCT;
      uses erienmnrmlrat:struct-PlmnIdentity;
    } // end 'container plmnIdentity'
    leaf lastModification {
      config false;
      description "Indicates whether the MO has been last modified by the Automated Neighbor Relations (ANR) function or operator.";
      notife:notifiable-state-data true;
      type erienmnrmlrat:enum-LastModificationGeran;
    }
    action changeFrequency {
      description "Changes the frequency of an external Geran cell.\nBefore running this action, make sure that the target GeranFrequency for the ExternalGeranCell  is created and that it refer to one of the GeranFreqGroup(s) that is referred from the same eUtranCell as the ExternalGeranCell.\nThis MO action includes the following steps:\n- The ExternalGeranCell will be updated to refer to  the target GeranFrequency.\n- If the target GeranFrequency is not referred from same eUtranCell(s) as the ExternalGeranCell included in the changeFrequency  action,  the action will fail and an exception will be issued.";
      input {
        leaf bandIndicator {
          mandatory true;
          description "The attribute indicates the GERAN frequency band if the ARFCN value concerns either a DCS 1800 or a PCS 1900 carrier frequency. For ARFCN values not associated with either of these bands, the indicator has no meaning.";
          type erienmnrmlrat:enum-BandIndicator;
        }
        leaf arfcnValueGeranDl {
          mandatory true;
          description "The new DL frequency for this cell.";
          type erienmnrmlrat:ddt-ExternalGeranCell_changeFrequency_arfcnValueGeranDl;
        }
      }
    }
  } // end 'grouping moc-ExternalGeranCell'
  grouping moc-AnrPciConflictDrxProfile-keys {
    description "Key(s) for MOC AnrPciConflictDrxProfile";
    leaf id {
      erienmyext:no-notification;
      description "The value component of the RDN.";
      mandatory true;
      yexte:ecim-name anrPciConflictDrxProfileId;
      type string;
    }
  } // end 'grouping moc-AnrPciConflictDrxProfile-keys'
  grouping moc-AnrPciConflictDrxProfile {
    description "DRX profiles, DRX parameters to map with ANR PCI conflict CGI reading.\n\nThe RDN of this MO is AnrPciConflictDrxProfile=1.";
    leaf anrPciConflictOnDurationTimer {
      description "The number of consecutive PDCCH subframes at DRX Cycle initialization. Attribute is only used to read CGI for ANR PCI conflict cell. TS36.331 ch. 6.3.2, RRC parameter onDurationTimer.";
      yexte:takes-effect "Object unlocked";
      type erienmnrmlrat:enum-OnDurationTimer;
      default PSF5;
    }
    leaf anrPciConflictDrxInactivityTimer {
      description "The number of consecutive PDCCH subframes after successfully decoding a PDCCH that indicates an initial UL or DL user data transmission for this UE. Attribute is only used to read CGI for ANR PCI conflict cell. TS36.331 ch. 6.3.2, RRC parameter drx-InactivityTimer.";
      yexte:takes-effect "Object unlocked";
      type erienmnrmlrat:enum-DrxInactivityTimer;
      default PSF20;
    }
    leaf anrPciConflictLongDrxCycle {
      description "Value longDrxCycle indicates the number of subframes. Attribute is only used to read CGI for ANR PCI conflict.";
      yexte:takes-effect "Object unlocked";
      type erienmnrmlrat:enum-LongDrxCycle;
      default SF320;
    }
  } // end 'grouping moc-AnrPciConflictDrxProfile'
  grouping moc-AdditionalCoreNetwork-keys {
    description "Key(s) for MOC AdditionalCoreNetwork";
    leaf id {
      erienmyext:no-notification;
      description "The value component of the RDN.";
      mandatory true;
      yexte:ecim-name additionalCoreNetworkId;
      type string;
    }
  } // end 'grouping moc-AdditionalCoreNetwork-keys'
  grouping moc-AdditionalCoreNetwork {
    description "MO contains information of additional core network configuration.";
    leaf upS1IpAddressRef {
      description "Refers to the IpAccessHostEt or AddressIPv4/AddressIPv6 instance to use for configuring the IP address for S1 plane connections of the PLMNs in plmnList.";
      yexte:disturbances "Changing this attribute can affect traffic";
      yexte:takes-effect "Node restart";
      erienmyext:enm-type MOREF;
      type string;
    }
    leaf sctpS1Ref {
      description "Refers to the SCTP instance that is used to configure the SCTP host for S1 connections of the PLMNs in plmnList.";
      yexte:disturbances "Changing this attribute can affect traffic";
      yexte:takes-effect "Node restart";
      erienmyext:enm-type MOREF;
      type string;
    }
    leaf dnsSelectionS1Ref {
      description "Controls DNS selection for S1 lookup for PLMNs in plmnList. If not set,\nDNS queries use DNS servers located in OAM network.\nIt can be set to reference a DnsClient, and DNS queries are resolved using referenced DnsClient (typically using DNS server on transport network).";
      yexte:disturbances "Changing this attribute can affect start(restart) duration";
      yexte:precondition "To enable this attribute DNS servers must support EDNS0.";
      erienmyext:enm-type MOREF;
      type string;
    }
    leaf-list reservedBy {
      min-elements 0;
      config false;
      description "List of MO instances that reserve this MO instance.";
      yexte:dependencies "MO can not be deleted if it is reserved.";
      notife:notifiable-state-data true;
      erienmyext:enm-type MOREF;
      type string;
    }
    list plmnList {
      min-elements 1;
      max-elements 5;
      key auto-generated-struct-key;
      leaf auto-generated-struct-key {
        type uint16;
        description "This leaf has been injected to allow for struct instances in a sequence to be ordered.";
        mandatory true;
      }
      description "Lists PLMN IDs served by additional CN. Attribute is used to identify local S1 and X2 IP interfaces for an additional core network. Additional CN can contain up to 5 PLMNs other than primary PLMN.";
      erienmyext:enm-type STRUCT;
      uses erienmnrmlrat:struct-PlmnIdentity;
    } // end 'list plmnList'
    leaf upX2IpAddressRef {
      description "Refers to the IpAccessHostEt or AddressIPv4/AddressIPv6 instance to use for configuring the IP address for X2 user plane connections of the PLMNs in plmnList.";
      yexte:disturbances "Changing this attribute can affect traffic";
      yexte:takes-effect "Node restart";
      erienmyext:enm-type MOREF;
      type string;
    }
  } // end 'grouping moc-AdditionalCoreNetwork'
  grouping moc-TimerProfile-keys {
    description "Key(s) for MOC TimerProfile";
    leaf id {
      erienmyext:no-notification;
      description "The value component of the RDN.";
      mandatory true;
      yexte:ecim-name timerProfileId;
      type string;
    }
  } // end 'grouping moc-TimerProfile-keys'
  grouping moc-TimerProfile {
    description "Contains internal eNodeB timer profiles to be mapped to different QCIs.";
    leaf tWaitForRrcConnReest {
      description "Waiting time for the RRC message RRC Connection Reestablishment Request upon detecting Radio Link Failure.\nUsed by the RBS.";
      mandatory true;
      yexte:takes-effect "New connection";
      type erienmnrmlrat:ddt-Lrat_TimerProfile_tWaitForRrcConnReest;
    }
    leaf-list reservedBy {
      min-elements 0;
      config false;
      description "Contains a list of managed object instances that reserves this managed object instance.";
      yexte:dependencies "The MO cannot be deleted if it is reserved.";
      notife:notifiable-state-data true;
      erienmyext:enm-type MOREF;
      type string;
    }
    leaf tRrcConnectionReconfiguration {
      description "Waiting time for the RRC message RRC Connection Reconfiguration Complete.\nUsed by the RBS.";
      mandatory true;
      yexte:takes-effect "New connection";
      type erienmnrmlrat:ddt-Lrat_TimerProfile_tRrcConnectionReconfiguration;
    }
    leaf tRrcConnReest {
      description "Waiting time for the RRC message RRC Connection Reestablishment Complete.\nUsed by the RBS.";
      mandatory true;
      yexte:takes-effect "New connection";
      type erienmnrmlrat:ddt-Lrat_TimerProfile_tRrcConnReest;
    }
    leaf tRelocOverall {
      description "Supervision timer of the outgoing S1/X2/intra-eNodeB handover execution procedure according to 3GPP TS 36.413 and TS 36.423.\nIf the feature Multi-Target RRC Connection Re-establishment is active this timer also supervises the Context Fetch procedure.";
      mandatory true;
      yexte:disturbances "Low values can stop outgoing HO.";
      yexte:takes-effect "New connection";
      type erienmnrmlrat:ddt-Lrat_TimerProfile_tRelocOverall;
    }
  } // end 'grouping moc-TimerProfile'
  grouping moc-CellSleepFunction-keys {
    description "Key(s) for MOC CellSleepFunction";
    leaf id {
      erienmyext:no-notification;
      description "The value component of the RDN.";
      mandatory true;
      yexte:ecim-name cellSleepFunctionId;
      type string;
    }
  } // end 'grouping moc-CellSleepFunction-keys'
  grouping moc-CellSleepFunction {
    description "Contains configuration parameters for function Cell Sleep Mode.\nThe RDN of this MO is CellSleepFunction=1. ";
    leaf sleepMode {
      description "Cell sleep mode status for the cell.";
      yexte:disturbances "Changing this attribute to ACTIVATED allows the cell to enter sleep state when sleep criteria is met when within the sleepStartTime and sleepEndTime interval.";
      type erienmnrmlrat:enum-ActivationVals;
      default DEACTIVATED;
    }
    leaf sleepEndTime {
      description "RBS daily end time (UTC time) to stop cell sleep detection or switching.\nFormat in ASCII-code: HH:MM where HH is in range [00..23] and MM is in range [00..59].\n";
      type erienmnrmlrat:ddt-Lrat_CellSleepFunction_sleepEndTime;
      default 05:00;
    }
    leaf covCellWakeUpMonitorDurTimer {
      description "Minimum duration for coverage cell to satisfy the configured load thresholds before the capacity cell can wake-up. Used in feature Cell sleep mode.";
      type erienmnrmlrat:ddt-Lrat_CellSleepFunction_covCellWakeUpMonitorDurTimer;
      default 15;
    }
    leaf capCellRrcConnSleepThreshold {
      description "Number of active RRC connections. The capacity cell must be below this to enter sleep state.";
      yexte:disturbances "Low values can cause cells with traffic to go into sleep mode.";
      type erienmnrmlrat:ddt-Lrat_CellSleepFunction_capCellRrcConnSleepThreshold;
      default 5;
    }
    leaf capCellSleepProhibitInterval {
      description "Time interval when sleep state is prohibited for capacity cell. If 0, prohibition is disabled for related cell. When related cell is in prohibition state, only value 0 can be set.";
      type erienmnrmlrat:ddt-Lrat_CellSleepFunction_capCellSleepProhibitInterval;
      default 24;
    }
    leaf isCleanupHitRateTable {
      description "Indicates if hit rate table is cleaned up when related capacity cell wakes up due to suspected coverage hole and automatic coverage cell discovery is enabled.";
      type boolean;
      default true;
    }
    leaf covCellRrcReestWakeUpThr {
      description "Difference threshold for RRC Connection Re-establishment rate between normal and sleep statistics. If threshold is exceeded coverage cell wakes up all capacity cells. Value 100 means monitoring for RRC Connection Re-establishment is disabled.";
      type erienmnrmlrat:ddt-Lrat_CellSleepFunction_covCellRrcReestWakeUpThr;
      default 100;
    }
    leaf covCellUeCtxtRelMin {
      description "Minimum required samples of UE Context Release to calculate UE Lost rate for normal and sleep statistics.";
      type erienmnrmlrat:ddt-Lrat_CellSleepFunction_covCellUeCtxtRelMin;
      default 200;
    }
    leaf capCellDlPrbSleepThreshold {
      description "DL PRB Usage percentage threshold.  The capacity cell must be below this  to enter sleep state.";
      yexte:disturbances "Low values can cause cells with traffic to go into sleep mode.";
      type erienmnrmlrat:ddt-Lrat_CellSleepFunction_capCellDlPrbSleepThreshold;
      default 10;
    }
    leaf covCellRrcConnWakeUpThreshold {
      description "Active RRC connections threshold. At least one of the coverage cells must exceed this number of active RRC connections to wake-up this capacity cell.";
      yexte:disturbances "High values can cause cells not to wake up from sleep mode.";
      type erienmnrmlrat:ddt-Lrat_CellSleepFunction_covCellRrcConnWakeUpThreshold;
      default 30;
    }
    leaf wakeUpWaitTimer {
      description "Time before eNodeB wakes up remaining capacity cells. Value 0 disables wake-up attempt.";
      type erienmnrmlrat:ddt-Lrat_CellSleepFunction_wakeUpWaitTimer;
      default 0;
    }
    leaf isAllowedMsmOnCovCell {
      description "Defines if MIMO sleep with \"SWITCH\" or \"SOFT_SWITCH\" mode is allowed in the coverage cell. The \"ADVANCED_SWITCH\" mode is not dependent on this attribute.";
      type boolean;
      default true;
    }
    leaf coverageCellDiscovery {
      description "Indicates if automatic coverage cells detection is enabled.\nIf true, EUtranCellRelations with sleepModeCovCellCandidate=AUTO are evaluated as coverage cell for sleep mode support. EUtranCellRelations found applicable as coverage cells have sleepModeCoverageCell=true. EUtranCellRelations with sleepModeCovCellCandidate =ALLOWED are always evaluated.\nIf false, only EUtranCellRelations with sleepModeCovCellCandidate =ALLOWED are included as coverage cells for sleep mode support.\n";
      type boolean;
      default false;
    }
    leaf covCellDlPrbWakeUpThreshold {
      description "DL PRB usage percentage threshold. At least one of the coverage cells must exceed this threshold to wake-up the capacity cell.";
      yexte:disturbances "High values can cause cells not to wake up from sleep mode.";
      type erienmnrmlrat:ddt-Lrat_CellSleepFunction_covCellDlPrbWakeUpThreshold;
      default 25;
    }
    leaf covCellUeLostWakeUpThr {
      description "Difference threshold for UE Lost rate between normal and sleep statistics. If threshold is exceeded coverage cell wakes up all capacity cells. Value 100 means monitoring for UE Lost is disabled.";
      type erienmnrmlrat:ddt-Lrat_CellSleepFunction_covCellUeLostWakeUpThr;
      default 100;
    }
    leaf covCellRrcConnEstAttMin {
      description "Minimum required samples of RRC Connection Establishment Attempt to calculate RRC Connection Re-establishment rate for normal and sleep statistics.";
      type erienmnrmlrat:ddt-Lrat_CellSleepFunction_covCellRrcConnEstAttMin;
      default 200;
    }
    leaf capCellMobReasNotSleepThr {
      description "Threshold value for number of incoming X2 inter-frequency handovers with cause \"Handover Desirable for Radio Reasons\" from neighbor cells with coverage frequency. If incoming X2 inter-frequency handovers exceeds threshold, it is considered related capacity cell is providing basic coverage support and entering sleep state is prevented.";
      type erienmnrmlrat:ddt-Lrat_CellSleepFunction_capCellMobReasNotSleepThr;
      default -1;
    }
    leaf covCellLatestStatsAdaRatio {
      description "Ratio indicating weight of latest data for normal statistics calculation.";
      type erienmnrmlrat:ddt-Lrat_CellSleepFunction_covCellLatestStatsAdaRatio;
      default 60;
    }
    leaf sleepState {
      config false;
      description "Indicates if Cell Sleep Mode takes effect. The cell is deactivated. Energy saving mode starts.";
      notife:notifiable-state-data true;
      type erienmnrmlrat:enum-ActivationVals;
    }
    leaf sleepProhibitStartTime {
      config false;
      description "Start time for sleep state prohibition. Format: YYYY-MM-DD HH:MM:SS. If empty, related capacity cell is not prohibited from entering sleep state. Otherwise, sleep state is prohibited till capCellSleepProhibitInterval expires or prohibition is disabled.";
      notife:notifiable-state-data true;
      type erienmnrmlrat:ddt-Lrat_CellSleepFunction_sleepProhibitStartTime;
    }
    leaf sleepStartTime {
      description "RBS daily start time (UTC time) to perform cell sleep detection or switching.\nFormat in ASCII-code: HH:MM where HH is in range [00..23] and MM is in range [00..59].";
      type erienmnrmlrat:ddt-Lrat_CellSleepFunction_sleepStartTime;
      default 02:00;
    }
    leaf capCellSleepMonitorDurTimer {
      description "Minimum duration for this cell to satisfy the configured load thresholds before entering sleep state. Used in the Cell Sleep Mode feature.";
      type erienmnrmlrat:ddt-Lrat_CellSleepFunction_capCellSleepMonitorDurTimer;
      default 15;
    }
    leaf wakeUpLastHoTime {
      description "Maximum time for last handover attempt before eNodeB wakes up capacity cells.";
      type erienmnrmlrat:ddt-Lrat_CellSleepFunction_wakeUpLastHoTime;
      default 2;
    }
  } // end 'grouping moc-CellSleepFunction'
  grouping moc-ReportConfigEUtraBestCellAnr-keys {
    description "Key(s) for MOC ReportConfigEUtraBestCellAnr";
    leaf id {
      erienmyext:no-notification;
      description "The value component of the Relative Distinguished Name (RDN).";
      mandatory true;
      yexte:ecim-name reportConfigEUtraBestCellAnrId;
      type string;
    }
  } // end 'grouping moc-ReportConfigEUtraBestCellAnr-keys'
  grouping moc-ReportConfigEUtraBestCellAnr {
    description "The ANR delta report configuration settings for the A3 event measurements as compared to mobility provided in the parent MO class.\n\nThe RDN of this MO is ReportConfigEUtraBestCellAnr=1.";
    leaf a3offsetAnrDelta {
      description "The offset value for eventA3. Dependent on triggerQuantityA3 on MO ReportConfigEUtraBestCell and is a delta towards a3offset on triggerQuantityA3, The a3offset used in the ANR measure is calculated as a3offset (on ReportConfigEUtraBestCell) - a3offset AnrDelta\n";
      yexte:takes-effect "New connection";
      yexte:dependencies "Not pure dependence towards parameter on ReportConfigEUtraBestCell Mo, but there should be a check that this attribute and corresponding attribute on ReportConfigEUtraBestCell MO together sends out a valid number to the UE ";
      type erienmnrmlrat:ddt-Lrat_ReportConfigEUtraBestCellAnr_a3offsetAnrDelta;
      default 3;
    }
    leaf hysteresisA3 {
      description "The hysteresis value for eventA3.";
      yexte:takes-effect "New connection";
      type erienmnrmlrat:ddt-Lrat_ReportConfigEUtraBestCellAnr_hysteresisA3;
      default 10;
    }
    leaf timeToTriggerA3 {
      description "The time to trigger value for eventA3.";
      yexte:takes-effect "New connection";
      type erienmnrmlrat:ddt-Lrat_ReportConfigEUtraBestCellAnr_timeToTriggerA3;
      default 640;
    }
  } // end 'grouping moc-ReportConfigEUtraBestCellAnr'
  grouping moc-ExternalGNodeBFunction-keys {
    description "Key(s) for MOC ExternalGNodeBFunction";
    leaf id {
      erienmyext:no-notification;
      description "The value component of the RDN.";
      mandatory true;
      yexte:ecim-name externalGNodeBFunctionId;
      type string;
    }
  } // end 'grouping moc-ExternalGNodeBFunction-keys'
  grouping moc-ExternalGNodeBFunction {
    description "This managed object represents an GNodeB.";
    leaf gNodeBIdLength {
      yexte:restricted;
      description "Length of gNodeBId bit string representation.";
      yexte:dependencies "If gNodeBId bit representation exceeds 22 bits, the value of gNodeBIdLength must be at least the minimum bit length that can accommodate gNodeBId.\ngNodeBId =< (2^gNodeBIdLength)-1\n3GPP defines NCGI as a bit string of size 36.\nNCGI is gNodeBId (22-32 bits) + localCellId(4-14 bits).\nThis parameter is required to differentiate, eg, 0..0100001 between:\n - Node 1 (31 bits) with cell 1.\n - Node 2 (32 bits) with cell 1.";
      type erienmnrmlrat:ddt-Lrat_ExternalGNodeBFunction_gNodeBIdLength;
      default 22;
    }
    leaf userLabel {
      description "User-defined alphanumeric label, maximum 128 characters including spaces.";
      type erienmnrmlrat:ddt-Lrat_ExternalGNodeBFunction_userLabel;
    }
    container gNodeBPlmnId {
      description "The Public Land Mobile Network (PLMN) ID of the node. The PLMN ID consists of:\n\n1. MobileCountryCode, MCC, 3 digits\n2. MobileNetworkCode, MNC, 2 or 3 digits (the correct number of digits is set in the mncLength member of this Struct).\n\nExample: If MCC=125 and MNC=46, then plmnId=12546.\nNote: The value (MCC=001, MNC=01) indicates that the PLMN is not initiated. The value can not be used as a valid PLMN Identity.";
      erienmyext:enm-type STRUCT;
      uses erienmnrmlrat:struct-PlmnIdentity;
    } // end 'container gNodeBPlmnId'
    leaf gNBId {
      status deprecated {
        yexte:status-information "Since 18.Q3. Planned to be removed.";
      }
      yexte:restricted;
      description "The ID of an RBS within a Public Land Mobile Network (PLMN).";
      type erienmnrmlrat:ddt-Lrat_ExternalGNodeBFunction_gNBId;
      default -1;
    }
    leaf gNodeBId {
      yexte:restricted;
      description "The ID of an RBS within a Public Land Mobile Network (PLMN).";
      mandatory true;
      yexte:dependencies "gNodeBId =< (2^gNodeBIdLength)-1\nIf gNodeBId bit representation exceeds 22 bits, the value of gNodeBIdLength must be the minimum length that can accommodate gNodeBId, if none provided.";
      type erienmnrmlrat:ddt-Lrat_ExternalGNodeBFunction_gNodeBId;
    }
  } // end 'grouping moc-ExternalGNodeBFunction'
  grouping moc-ReportConfigSCellA1A2-keys {
    description "Key(s) for MOC ReportConfigSCellA1A2";
    leaf id {
      erienmyext:no-notification;
      description "The value component of the Relative Distinguished Name (RDN).";
      mandatory true;
      yexte:ecim-name reportConfigSCellA1A2Id;
      type string;
    }
  } // end 'grouping moc-ReportConfigSCellA1A2-keys'
  grouping moc-ReportConfigSCellA1A2 {
    description "This managed object contains the report configuration settings for A2/A1 measurements on the frequency of any serving SCell when this cell is used as PCell.\n\nThe RDN of this MO is ReportConfigSCellA1A2=1.";
    leaf hysteresisA1A2Rsrq {
      description "The hysteresis value for RSRQ in events A1 and A2 measurements.\nChanged value may take effect related to the next SCell configuration during the ongoing connection.";
      yexte:takes-effect "Ongoing connection";
      type erienmnrmlrat:ddt-Lrat_ReportConfigSCellA1A2_hysteresisA1A2Rsrq;
      default 15;
    }
    leaf hysteresisA1A2RsrpBidir {
      status deprecated {
        yexte:status-information "Since 17.Q2. Planned to be removed.";
      }
      description "Hysteresis value for RSRP in events A1 and A2 measurements below which UL CA is not configured.";
      yexte:takes-effect "Changed value may take effect related to the next SCell configuration during the ongoing connection.";
      yexte:dependencies "When a1a2ThresholdRsrpBidir is less than or equal to a1a2ThresholdRsrp, the capability to remove UL separately from DL is disabled.";
      type erienmnrmlrat:ddt-Lrat_ReportConfigSCellA1A2_hysteresisA1A2RsrpBidir;
      default 20;
    }
    leaf a1a2ThresholdRsrpBidir {
      description "RSRP threshold value for events A1 and A2 below which UL CA is not configured.";
      yexte:takes-effect "Changed value may take effect related to the next SCell configuration during the ongoing connection.";
      yexte:dependencies "hysteresisA1A2RsrpBidirectional applies. When a1a2ThresholdRsrpBidir is less than or equal to a1a2ThresholdRsrp, the capability to remove UL separately from DL is disabled.";
      type erienmnrmlrat:ddt-Lrat_ReportConfigSCellA1A2_a1a2ThresholdRsrpBidir;
      default -140;
    }
    leaf triggerQuantityA1A2 {
      description "The quantity that triggers the eventA2 and eventA1 for SCell measurements.";
      yexte:takes-effect "Ongoing connection";
      type erienmnrmlrat:enum-TriggerQuantity;
      default RSRP;
    }
    leaf hysteresisA1A2RsrpBidirectional {
      description "Hysteresis value for RSRP in events A1 and A2 measurements below which UL CA is not configured.";
      yexte:takes-effect "New connection. Also during ongoing connection, related to next SCell configuration during the connection.";
      yexte:dependencies "When a1a2ThresholdRsrpBidir is less than or equal to a1a2ThresholdRsrp, the capability to remove UL separately from DL is disabled.";
      type erienmnrmlrat:ddt-Lrat_ReportConfigSCellA1A2_hysteresisA1A2RsrpBidirectional;
      default 20;
    }
    leaf timeToTriggerA2 {
      description "The time-to-trigger value for measurement in event A2.\nChanged value may take effect related to the next SCell configuration during the ongoing connection.";
      yexte:takes-effect "Ongoing connection";
      type erienmnrmlrat:ddt-Lrat_ReportConfigSCellA1A2_timeToTriggerA2;
      default 40;
    }
    leaf a1a2ThresholdRsrq {
      description "The Reference Signal Received Quality (RSRQ) threshold value for events A1 and A2.\nChanged value may take effect related to the next SCell configuration during the ongoing connection.";
      yexte:takes-effect "Ongoing connection";
      type erienmnrmlrat:ddt-Lrat_ReportConfigSCellA1A2_a1a2ThresholdRsrq;
      default -165;
    }
    leaf hysteresisA1A2Rsrp {
      description "The hysteresis value for RSRP in events A1 and A2 measurements for SCell.";
      yexte:takes-effect "Ongoing connection";
      type erienmnrmlrat:ddt-Lrat_ReportConfigSCellA1A2_hysteresisA1A2Rsrp;
      default 10;
    }
    leaf timeToTriggerA1 {
      description "The time-to-trigger value for measurement in event A1.\nChanged value may take effect related to the next SCell configuration during the ongoing connection.";
      yexte:takes-effect "Ongoing connection";
      type erienmnrmlrat:ddt-Lrat_ReportConfigSCellA1A2_timeToTriggerA1;
      default 40;
    }
    leaf a1a2ThresholdRsrp {
      description "The Reference Signal Received Power (RSRP) threshold value for events A1 and A2.\nChanged value may take effect related to the next SCell configuration during the ongoing connection.";
      yexte:takes-effect "Ongoing connection";
      type erienmnrmlrat:ddt-Lrat_ReportConfigSCellA1A2_a1a2ThresholdRsrp;
      default -126;
    }
  } // end 'grouping moc-ReportConfigSCellA1A2'
  grouping moc-MbmsService-keys {
    description "Key(s) for MOC MbmsService";
    leaf id {
      erienmyext:no-notification;
      description "The value component of the Relative Distinguished Name (RDN).";
      mandatory true;
      yexte:ecim-name mbmsServiceId;
      type string;
    }
  } // end 'grouping moc-MbmsService-keys'
  grouping moc-MbmsService {
    description "MO represents configuration related to MBMS bearer service. If Autoconfiguration of LTE Broadcast Subframes\nis used, this MO will be created by the system.";
    leaf userLabel {
      erienmyext:no-notification;
      description "Label for free use.";
      type erienmnrmlrat:ddt-Lrat_MbmsService_userLabel;
    }
    leaf syncSequenceLength {
      status deprecated {
        yexte:status-information "Since L16B. Replaced by PmchMch::syncSequenceLength. Planned to be removed.";
      }
      description "The synchronization sequence length used for MBMS data on the M1 interface.";
      yexte:takes-effect "New connection";
      yexte:dependencies "The syncSequenceLength must be smaller than or equal to the\nmchSchedulingPeriod in the MO class PmchMch.";
      type erienmnrmlrat:ddt-Lrat_MbmsService_syncSequenceLength;
      default 8;
    }
    leaf createdBy {
      erienmyext:no-notification;
      config false;
      description "Whether MbmsService is created by operator or by system.";
      type erienmnrmlrat:enum-CreatedBy;
    }
    list tmgiList {
      min-elements 1;
      max-elements 10;
      key auto-generated-struct-key;
      leaf auto-generated-struct-key {
        type uint16;
        description "This leaf has been injected to allow for struct instances in a sequence to be ordered.";
        mandatory true;
      }
      description "List of temporary mobile group identities. Set by system if Autoconfiguration of LTE Broadcast Subframes is used.";
      erienmyext:enm-type STRUCT;
      uses erienmnrmlrat:struct-Tmgi;
    } // end 'list tmgiList'
    leaf logicalChannelIdentity {
      description "The logical channel identity.";
      mandatory true;
      yexte:takes-effect "New connection";
      type erienmnrmlrat:ddt-Lrat_MbmsService_logicalChannelIdentity;
    }
    leaf-list availabilityStatus {
      min-elements 0;
      config false;
      description "The availability status. It contains details about operationalState. This attribute is set by the application in the RBS.";
      notife:notifiable-state-data true;
      type erienmnrmlrat:enum-AvailStatus;
    }
    leaf operationalState {
      config false;
      description "The operational state.";
      notife:notifiable-state-data true;
      type erienmnrmlrat:enum-OperState;
    }
  } // end 'grouping moc-MbmsService'
  grouping moc-AmoFunction-keys {
    description "Key(s) for MOC AmoFunction";
    leaf id {
      erienmyext:no-notification;
      description "The value component of the RDN.";
      mandatory true;
      yexte:ecim-name amoFunctionId;
      type string;
    }
  } // end 'grouping moc-AmoFunction-keys'
  grouping moc-AmoFunction {
    description "Contains parameters for Automated Mobility Optimization function.\n\nThe RDN of this MO is AmoFunction=1.";
    leaf allowInterVendorX2Signal {
      description "Whether or not AMO function allows to send X2AP RLF Indication and X2AP Handover Report signals to other vendor eNodeB.";
      type boolean;
      default true;
    }
    leaf amoAllowedInterVendor {
      description "Whether or not AMO function is allowed for inter-vendor cell relations.";
      type boolean;
      default true;
    }
  } // end 'grouping moc-AmoFunction'
  grouping moc-GUtranSyncSignalFrequency-keys {
    description "Key(s) for MOC GUtranSyncSignalFrequency";
    leaf id {
      erienmyext:no-notification;
      description "The value component of the RDN.";
      mandatory true;
      yexte:ecim-name gUtranSyncSignalFrequencyId;
      type string;
    }
  } // end 'grouping moc-GUtranSyncSignalFrequency-keys'
  grouping moc-GUtranSyncSignalFrequency {
    description "Contains information of a specific GUtran frequency.";
    leaf userLabel {
      description "Label for free use.";
      type erienmnrmlrat:ddt-Lrat_GUtranSyncSignalFrequency_userLabel;
    }
    leaf gscn {
      config false;
      description "Synchronization Channel Number. Defines frequency of synchronization channel portion of RF carrier.";
      notife:notifiable-state-data true;
      type erienmnrmlrat:ddt-Lrat_GUtranSyncSignalFrequency_gscn;
    }
    leaf-list reservedBy {
      min-elements 0;
      config false;
      description "List of MO instances that reserve this MO instance.";
      notife:notifiable-state-data true;
      erienmyext:enm-type MOREF;
      type string;
    }
    leaf band {
      config false;
      description "5G-RAN Operating Band.";
      notife:notifiable-state-data true;
      type erienmnrmlrat:ddt-Lrat_GUtranSyncSignalFrequency_band;
    }
    leaf arfcn {
      config false;
      description "NR ARFCN associated with the synchronization signal frequency.";
      notife:notifiable-state-data true;
      type erienmnrmlrat:ddt-Lrat_GUtranSyncSignalFrequency_arfcn;
    }
  } // end 'grouping moc-GUtranSyncSignalFrequency'
  grouping moc-PlmnInfo-keys {
    description "Key(s) for MOC PlmnInfo";
    leaf id {
      erienmyext:no-notification;
      description "The value component of the RDN.";
      mandatory true;
      yexte:ecim-name plmnInfoId;
      type string;
    }
  } // end 'grouping moc-PlmnInfo-keys'
  grouping moc-PlmnInfo {
    description "PLMN specific configuration parameters.";
    container actualPlmn {
      description "PLMN that plmnWhiteList is applied to.";
      erienmyext:enm-type STRUCT;
      uses erienmnrmlrat:struct-PlmnIdentity;
    } // end 'container actualPlmn'
    list plmnWhiteList {
      min-elements 0;
      max-elements 6;
      key auto-generated-struct-key;
      leaf auto-generated-struct-key {
        type uint16;
        description "This leaf has been injected to allow for struct instances in a sequence to be ordered.";
        mandatory true;
      }
      description "Lists all PLMN IDs that are available for outgoing handover toward EUTRAN, UTRAN or GERAN cell and X2 setup.";
      erienmyext:enm-type STRUCT;
      uses erienmnrmlrat:struct-WhiteListPlmnIdentity;
    } // end 'list plmnWhiteList'
  } // end 'grouping moc-PlmnInfo'
  grouping moc-ReportConfigInterRatLb-keys {
    description "Key(s) for MOC ReportConfigInterRatLb";
    leaf id {
      erienmyext:no-notification;
      description "Value component of the RDN";
      mandatory true;
      yexte:ecim-name reportConfigInterRatLbId;
      type string;
    }
  } // end 'grouping moc-ReportConfigInterRatLb-keys'
  grouping moc-ReportConfigInterRatLb {
    description "The MO contains the report configuration settings for UE measurements that are initiated for Inter-RAT load balancing actions.\n\nThe RDN of this MO is ReportConfigInterRatLb=1.";
    leaf utranB1ThresholdRscp {
      description "RSCP threshold value for the event B1 measurement for Load based IRAT handover to UTRAN.";
      yexte:dependencies "Only used when UeMeasControl::measQuantityUtraFDD is set to RSCP.";
      type erienmnrmlrat:ddt-Lrat_ReportConfigInterRatLb_utranB1ThresholdRscp;
      default -24;
    }
    leaf utranHysteresisB1 {
      description "Hysteresis value for the event B1 measurement";
      type erienmnrmlrat:ddt-Lrat_ReportConfigInterRatLb_utranHysteresisB1;
      default 10;
    }
    leaf utranB1ThresholdEcNo {
      description "Ratio of energy per modulation bit to noise spectral density in the ThresholdUTRA, threshold value for event B1.\nNot applicable for UTRA TDD.";
      yexte:dependencies "Only used when UeMeasControl::measQuantityUtraFDD is set to ECNO.";
      type erienmnrmlrat:ddt-Lrat_ReportConfigInterRatLb_utranB1ThresholdEcNo;
      default -240;
    }
  } // end 'grouping moc-ReportConfigInterRatLb'
  grouping moc-Cdma2000CellRelation-keys {
    description "Key(s) for MOC Cdma2000CellRelation";
    leaf id {
      erienmyext:no-notification;
      description "The value component of the Relative Distinguished Name (RDN).\n";
      mandatory true;
      yexte:ecim-name cdma2000CellRelationId;
      type string;
    }
  } // end 'grouping moc-Cdma2000CellRelation-keys'
  grouping moc-Cdma2000CellRelation {
    description "This Managed Object represents a mobility relation between a EUtranCellFDD or an EUtranCellTDD and an Cdma2000Cell. It contains parameters that are specific for this relation.\n";
    leaf userLabel {
      description "Label for free use.\n";
      type erienmnrmlrat:ddt-Lrat_Cdma2000CellRelation_userLabel;
    }
    leaf includeInSystemInformation {
      description "Indicates if the CDMA2000 cell shall be included in System Information or not.\nWhen the includeInSystemInformation is set to false, the CDMA2000 cell is not included in SIB8.\nA maximum of 16 CDMA2000 cells can be included per frequency.\nA maximum of 32 CDMA2000 cells can be included in SIB8.";
      type boolean;
      default true;
    }
    leaf externalCdma2000CellRef {
      yexte:restricted;
      description "Reference to a ExternalCdma2000Cell.\n";
      mandatory true;
      erienmyext:enm-type MOREF;
      type string;
    }
    leaf includeInSystemInformationRel9 {
      description "Indicates if the CDMA2000 cell shall be included in the Release 9 part of System Information or not.\nWhen the includeInSystemInformationRel9 is set to false, the CDMA2000 cell is not included in the Release 9 part of SIB8.\nA maximum of 16 CDMA2000 cells can be included per frequency in the Release 9 part.\nA total maximum of 32 CDMA2000 cells can be included in SIB8.";
      yexte:dependencies "In 3GPP rel9, the possiblity to add 16 additional CDMA2000 cells on the same frequency, was added. The additional CDMA2000 cells are controled by the parameter includeInSystemInformationRel9.";
      type boolean;
      default false;
    }
  } // end 'grouping moc-Cdma2000CellRelation'
  grouping moc-NbIotCell-keys {
    description "Key(s) for MOC NbIotCell";
    leaf id {
      erienmyext:no-notification;
      description "The value component of the RDN.";
      mandatory true;
      yexte:ecim-name nbIotCellId;
      type string;
    }
  } // end 'grouping moc-NbIotCell-keys'
  grouping moc-NbIotCell {
    description "This MO represents a Nb-Iot cell and contains parameters needed by the cell.";
    leaf-list attachWithoutPDNConnectivityList {
      min-elements 0;
      max-elements 6;
      description "For the list of PLMN IDs in the cell, indicates that ATTACH without PDN connectivity is supported. Provided in NB-SIB1.";
      yexte:takes-effect "Next cell unlock";
      yexte:dependencies "The list must have the same number of entries as plmnIdList.";
      type boolean;
    }
    leaf-list plmnReservedList {
      min-elements 0;
      max-elements 6;
      description "For the list of PLMN IDs in the cell, indicates if they are reserved for operator use. The list must have the same number of entries as plmnIdList. The PLMN ID appearing in plmnIdList[x] is reserved when plmnReservedList[x] is set to true. Provided in NB-SIB1.";
      yexte:disturbances "Changing this attribute can cause loss of traffic.";
      yexte:takes-effect "Next cell unlock";
      yexte:dependencies "The list must have the same number of entries as plmnIdList.";
      type boolean;
    }
    container mappingInfo {
      description "SI message to which each NB-SIB is mapped.";
      erienmyext:enm-type STRUCT;
      uses erienmnrmlrat:struct-MappingInfoNbSIBs;
    } // end 'container mappingInfo'
    leaf-list plmnAlarmSupprList {
      min-elements 0;
      max-elements 6;
      description "The list of PLMN IDs in the cell indicates if they are suppressed alarms\n- PLMN Service Degraded or\n- PLMN Service Unavailable\nwhen PLMN is not available in the cell.\nThe PLMN ID appearing in plmnIdList[x] is suppressed when plmnAlarmSupprList[x] is true.\nIf the configured PLMN ID is not a served PLMN ID, then the alarm is suppressed independent of the configured settings.";
      yexte:takes-effect "Next cell unlock";
      yexte:dependencies "The length of this list must be the same as the list in plmnIdList.";
      type boolean;
    }
    leaf-list pciConflict {
      min-elements 0;
      max-elements 5;
      status deprecated {
        yexte:status-information "Since L17A. Planned to be removed.";
      }
      description "A PCI confusion exists if a source cell has relations to two neighbor cells where both neighbor cells have the same PCI and frequency. A PCI collision exists if a source cell has a relation to a neighbor cell where both the source cell and neighbor cell have the same PCI and frequency.";
      type erienmnrmlrat:enum-PciConflict;
    }
    leaf physicalLayerCellId {
      description "Physical layer cell ID.\nIf NbIot PCI is different from host cell PCI, NbIot PCI must follow NBPCI mod 6 = WBPCI mod 6, otherwise UEs do not know host cell CRS position.";
      mandatory true;
      yexte:disturbances "Changing this attribute can cause loss of traffic.";
      yexte:takes-effect "Next cell unlock";
      type erienmnrmlrat:ddt-Lrat_NbIotCell_physicalLayerCellId;
    }
    list plmnIdentityList {
      min-elements 0;
      max-elements 6;
      key auto-generated-struct-key;
      leaf auto-generated-struct-key {
        type uint16;
        description "This leaf has been injected to allow for struct instances in a sequence to be ordered.";
        mandatory true;
      }
      description "Lists the PLMN IDs served by at least one MME. The PLMN ID is defined in the attribute eNodeBPlmnId in the parent ENodeBFunction. Information item included in SIB1.";
      status deprecated {
        yexte:status-information "Since L17A. Replaced by plmnIdList. Planned to be removed.";
      }
      erienmyext:enm-type STRUCT;
      uses erienmnrmlrat:struct-PlmnIdentity;
    } // end 'list plmnIdentityList'
    list plmnList {
      min-elements 0;
      max-elements 6;
      key auto-generated-struct-key;
      leaf auto-generated-struct-key {
        type uint16;
        description "This leaf has been injected to allow for struct instances in a sequence to be ordered.";
        mandatory true;
      }
      description "Lists the PLMN IDs configured for the cell. If shared NW is disabled only the first PLMN in the list is considered.";
      status deprecated {
        yexte:status-information "Since 17.Q2. Replaced by plmnIdList. Planned to be removed.";
      }
      erienmyext:enm-type STRUCT;
      uses erienmnrmlrat:struct-PlmnIdentity;
    } // end 'list plmnList'
    list activePlmnList {
      min-elements 0;
      max-elements 6;
      key auto-generated-struct-key;
      leaf auto-generated-struct-key {
        type uint16;
        description "This leaf has been injected to allow for struct instances in a sequence to be ordered.";
        mandatory true;
      }
      description "Lists the PLMN IDs served by at least one MME. PLMN IDs from plmnIdList also appear in this list. The list may include up to 6 PLMNs.";
      erienmyext:enm-type STRUCT;
      uses erienmnrmlrat:struct-PlmnIdentityRO;
    } // end 'list activePlmnList'
    container siRepetition {
      description "Radio frames in SI window used for SI message transmission. Values range from every second radio frame up to every 16th radio frame. They start from first radio frame of SI window used for SI transmission. Applicable to all SI messages.";
      status deprecated {
        yexte:status-information "Since 17.Q2. Planned to be removed.";
      }
      erienmyext:enm-type STRUCT;
      uses erienmnrmlrat:struct-SIRepetitionNB;
    } // end 'container siRepetition'
    container siPeriodicity {
      description "SI message periodicity. SI message is not transmitted unless SIB is mapped to it.";
      status deprecated {
        yexte:status-information "Since 17.Q2. Planned to be removed.";
      }
      erienmyext:enm-type STRUCT;
      uses erienmnrmlrat:struct-SIPeriodicityNB;
    } // end 'container siPeriodicity'
    leaf cellRange {
      description "Defines the maximum distance from the base station where a connection to a NB-IoT UE can be setup and/or maintained.";
      yexte:disturbances "Changes may affect traffic.";
      yexte:takes-effect "Next cell unlock";
      type erienmnrmlrat:ddt-Lrat_NbIotCell_cellRange;
      default 15;
    }
    list pciConflictCell {
      min-elements 0;
      max-elements 5;
      key auto-generated-struct-key;
      leaf auto-generated-struct-key {
        type uint16;
        description "This leaf has been injected to allow for struct instances in a sequence to be ordered.";
        mandatory true;
      }
      description "Indicates the CGI of the other cell that is involved in the PCI collision/confusion. This value is only valid if the attribute pciConflict is \"YES\" or \"YES_CONFLICTING_CELL\".";
      status deprecated {
        yexte:status-information "Since L17A. Planned to be removed.";
      }
      erienmyext:enm-type STRUCT;
      uses erienmnrmlrat:struct-Cgi;
    } // end 'list pciConflictCell'
    leaf cellBarred {
      description "Indicates if the cell is barred and should not be accessible to random UEs.";
      yexte:disturbances "Changing this attribute to BARRED blocks all traffic in the cell.";
      yexte:takes-effect "Next cell unlock";
      type erienmnrmlrat:enum-CellBarred;
      default NOT_BARRED;
    }
    leaf-list additionalSpectrumEmissionValues {
      min-elements 0;
      max-elements 8;
      config false;
      description "A list of network signaling values, where each value corresponds to the frequency band on the same position in additionalFreqBandList. Enables additional spectrum emission requirements according to 3GPP TS 36.101, table 6.2.4-1. The content of this list is based on spectrumEmissionReqMapping. This list will be broadcasted in NB-SIB2 as multiBandInfoList.";
      notife:notifiable-state-data true;
      type erienmnrmlrat:enum-NetworkSignallingValue;
    }
    leaf administrativeState {
      description "The administrative state.\nNote: Only LOCKED or UNLOCKED is permitted to this attribute since Soft Lock is not supported in NbIotCell.";
      yexte:disturbances "Changing this attribute to LOCKED causes loss of traffic. Changing this attribute can cause all unlocked NBIoT cells to change administrativeState to LOCKED and then UNLOCKED. This happens when one of the following thresholds is crossed: 18 EUTRAN cells + 1 NBIoT cell or 9 NBIoT cells.";
      type erienmnrmlrat:enum-AdmState;
      default LOCKED;
    }
    list frequencyInfo {
      min-elements 0;
      max-elements 8;
      key auto-generated-struct-key;
      leaf auto-generated-struct-key {
        type uint16;
        description "This leaf has been injected to allow for struct instances in a sequence to be ordered.";
        mandatory true;
      }
      description "Array of inter frequency related information.";
      erienmyext:enm-type STRUCT;
      uses erienmnrmlrat:struct-NbIotFrequencyInfo;
    } // end 'list frequencyInfo'
    leaf enableMfbi {
      description "When set this enables MFBI functionality for NB IoT.";
      yexte:disturbances "Changing this attribute can cause loss of traffic.";
      yexte:takes-effect "Next cell unlock";
      type boolean;
      default false;
    }
    leaf tac {
      description "Tracking Area Code for the Nb-Iot cell. Information item included in SIB1.";
      mandatory true;
      yexte:disturbances "Changing this attribute may affect traffic.";
      yexte:takes-effect "Next cell unlock";
      type erienmnrmlrat:ddt-Lrat_NbIotCell_tac;
    }
    leaf qHyst {
      description "Hysteresis value for ranking criteria. Included in NB-SIB3.";
      yexte:takes-effect "Next cell unlock";
      type erienmnrmlrat:ddt-Lrat_NbIotCell_qHyst;
      default 0;
    }
    leaf siWindowLength {
      description "Length of SI window during which each SI message is transmitted. Applies to all SI messages.";
      yexte:takes-effect "Next cell unlock";
      type erienmnrmlrat:ddt-Lrat_NbIotCell_siWindowLength;
      default 160;
    }
    leaf sInterSearchThreshold {
      description "Cell Reselection Threshold (inter-frequency measurements). Provided in NB-SIB3.";
      yexte:takes-effect "Next cell unlock";
      type erienmnrmlrat:ddt-Lrat_NbIotCell_sInterSearchThreshold;
      default 0;
    }
    leaf nbIotCellType {
      yexte:restricted;
      description "The Nb-Iot cell type determines the cell deployment, i.e. the allocation of PRBs. A Nb-Iot Cell with inband deployment allocated its PRBs from an EUtranCellFDD. A guard band cell gets its PRBs from the guard bands of an EUtranCellFDD. The standalone Nb-Iot cell is deployed independently of EUtranCellFDD:s.";
      mandatory true;
      type erienmnrmlrat:enum-NbIotCellType;
    }
    leaf-list prbNumber {
      min-elements 0;
      max-elements 76;
      status deprecated {
        yexte:status-information "Since L17A. Planned to be removed.";
      }
      description "PRB numbers used by the Nb-Iot Cell (inband or guardband deployment)\nThe six PRBs in the middle of the EUtranCellFDD may not be reserved.\nNegative numbers may be used for guardband PRBs in the lower frequency range.";
      yexte:disturbances "Changing this attribute will affect the resource allocation of the cell.";
      yexte:takes-effect "Cell lock/unlock";
      yexte:precondition "Only applicable for inband or guardband deployment. The NbIotCell Mo must be locked.";
      type erienmnrmlrat:ddt-Lrat_NbIotCell_prbNumber;
    }
    leaf allocatedUlPrb {
      status deprecated {
        yexte:status-information "Since 18.Q3. Replaced by ulAllocatedPrb. Planned to be removed.";
      }
      config false;
      description "Which uplink PRB index is allocated to NB-IOT cell.";
      yexte:dependencies "Only applicable in inband and guardband deployment.";
      notife:notifiable-state-data true;
      type erienmnrmlrat:ddt-Lrat_NbIotCell_allocatedUlPrb;
    }
    leaf freqBand {
      config false;
      description "The primary frequency band the cell belongs to.";
      notife:notifiable-state-data true;
      type erienmnrmlrat:ddt-Lrat_NbIotCell_freqBand;
    }
    leaf dlNonAnchPrbNum {
      description "Number of supported downlink non-anchor carriers of NB-IoT cell.";
      yexte:takes-effect "Next cell unlock";
      yexte:dependencies "Only applicable for inband and guardband deployment.";
      type erienmnrmlrat:ddt-Lrat_NbIotCell_dlNonAnchPrbNum;
      default 0;
    }
    leaf tTatDedicatedNbCe2 {
      description "Time alignment timer, used for supervision and control of uplink synchronization in NB IoT cell for CE Level 2. Value 0 means infinity.";
      yexte:takes-effect "Next cell unlock";
      type erienmnrmlrat:ddt-Lrat_NbIotCell_tTatDedicatedNbCe2;
      default 0;
    }
    leaf-list dlAllocatedPrb {
      min-elements 1;
      max-elements 8;
      erienmyext:no-notification;
      config false;
      description "NB-IoT cell downlink PRB index. Element 0 means anchor downlink PRB index. Elements 1-7 mean non-anchor downlink PRB index.\nUndefined value: 255";
      yexte:dependencies "Only applicable for inband and guardband deployment.";
      type erienmnrmlrat:ddt-Lrat_NbIotCell_dlAllocatedPrb;
    }
    leaf cellId {
      yexte:restricted;
      description "RBS internal ID attribute for NB-IoT cell. Must be unique across all cell types in RBS. Together with Node ID and PLMN, this is a universally unique cell ID.";
      mandatory true;
      type erienmnrmlrat:ddt-Lrat_NbIotCell_cellId;
    }
    leaf networkSignallingValue {
      description "Enables additional spectrum emission requirements according to 3GPP TS 36.101, table 6.2.4-1.";
      yexte:disturbances "Changing this attribute can cause loss of traffic.";
      yexte:takes-effect "Next cell unlock";
      type erienmnrmlrat:enum-NetworkSignallingValue;
      default NS_01;
    }
    leaf-list additionalFreqBandList {
      min-elements 0;
      max-elements 8;
      config false;
      description "A list of additional frequency bands the cell belongs to, not including the frequency band indicated by the EARFCN value of the cell (primary frequency band). The list is automatically set by the eNB. These additional frequency bands are broadcasted to the UEs in NB-SIB1.";
      notife:notifiable-state-data true;
      type erienmnrmlrat:ddt-Lrat_NbIotCell_additionalFreqBandList;
    }
    leaf allocatedPrbIndex {
      status deprecated {
        yexte:status-information "Since 18.Q3. Replaced by dlAllocatedPrb. Planned to be removed.";
      }
      config false;
      description "Which downlink PRB index is allocated to NB-IOT cell.";
      yexte:dependencies "Only applicable for inband and guardband deployment.";
      notife:notifiable-state-data true;
      type erienmnrmlrat:ddt-Lrat_NbIotCell_allocatedPrbIndex;
    }
    leaf ulAnchPrbIndex {
      description "Uplink anchor carrier PRB index used by NB-IoT cell. Common for inband and guardband deployment.\nFor inband deployment, the PRB index is inside of the PRB value range of the EUtranCellFDD host cell (0 to the cell's highest PRB index).\nFor guardband deployment, the PRB index is outside of the PRB value range of the EUtranCellFDD host cell (below 0 or above the cell's highest PRB index). 5 MHz is not supported.\nIf this attribute is set to default value, system allocates the uplink anchor carrier.";
      yexte:takes-effect "Next cell unlock";
      yexte:dependencies "Only applicable for inband and guardband deployment.";
      type erienmnrmlrat:ddt-Lrat_NbIotCell_ulAnchPrbIndex;
      default 255;
    }
    leaf pZeroNominalNPusch {
      description "The nominal component of the UE transmit power for Physical Uplink Shared Channel (N-PUSCH).";
      yexte:takes-effect "Next cell unlock";
      type erienmnrmlrat:ddt-Lrat_NbIotCell_pZeroNominalNPusch;
      default -103;
    }
    leaf gbPrbIndexUl {
      status deprecated {
        yexte:status-information "Since 18.Q3. Replaced by ulAnchPrbIndex. Planned to be removed.";
      }
      description "Uplink PRB index used by Nb-IoT Cell guardband deployment.\nFor guardband deployment, PRB index is outside of PRB value range of EUtranCellFDD host cell (below 0 or above highest PRB index of cell). For above 0, real prbindex depends on LTE carrier bandwidth. For example, for 10Mhz bandwidth, 1 means PRB 49+1=50.\nSupported range is -1, 1. Other values are not accepted.";
      yexte:disturbances "Changing this attribute can cause loss of traffic. Affects the resource allocation of the GB cell.";
      yexte:takes-effect "Next cell unlock";
      yexte:dependencies "Only takes effect when NbIoTCell::nbIotCellType = NBIOT_GUARDBAND";
      type erienmnrmlrat:ddt-Lrat_NbIotCell_gbPrbIndexUl;
      default 1;
    }
    leaf useHostCellPci {
      description "Indicates if host cell PCI is used as Nb-IoT PCI. If false, physicalLayerCellId is used as Nb-IoT PCI.\nIf true, host cell PCI is used and physicalLayerCellId is ignored.";
      yexte:disturbances "Changing this attribute can cause loss of traffic.";
      yexte:takes-effect "Next cell unlock";
      yexte:dependencies "Only applicable when NbIoTCell::nbIotCellType = NBIOT_GUARDBAND.";
      type boolean;
      default true;
    }
    leaf operationalState {
      config false;
      description "The operational state. This attribute is set by the application in the RBS.";
      notife:notifiable-state-data true;
      type erienmnrmlrat:enum-OperState;
    }
    leaf qQualMin {
      description "The minimum required quality level (RSRQ) in the cell in dB.\nCorresponds to Qqualmin in TS 36.304, sent in NB-SIB1. Value 0 means that the lowest possible value is used for Qqualmin.";
      yexte:takes-effect "Next cell unlock";
      type erienmnrmlrat:ddt-Lrat_NbIotCell_qQualMin;
      default -34;
    }
    leaf ulNonAnchPrbNum {
      description "Number of supported uplink non-anchor carriers of NB-IoT cell.";
      yexte:takes-effect "Next cell unlock";
      yexte:dependencies "Only applicable for inband and guardband deployment.";
      type erienmnrmlrat:ddt-Lrat_NbIotCell_ulNonAnchPrbNum;
      default 0;
    }
    leaf userLabel {
      description "Label for free use.";
      type erienmnrmlrat:ddt-Lrat_NbIotCell_userLabel;
    }
    leaf gbPrbIndexDl {
      status deprecated {
        yexte:status-information "Since 18.Q3. Replaced by dlAnchPrbIndex. Planned to be removed.";
      }
      description "Downlink PRB index used by the Nb-IoT Cell guard band deployment.\nFor guardband deployment, the PRB index is outside of the PRB value range of the EUtranCellFDD host cell (below 0 or above the cell's highest PRB index). For above 0, the real prbindex is dependent on the LTE carrier BW, e.g. for 10Mhz BW 1 means PRB 49+1=50. There are 3 vacant sub-carriers in-between the edge LTE PRB and the guardband NB-IoT PRB for 5MHz and 15 MHz host cells on each side to guarantee that the center frequency of the guardband cell is on a 100Khz raster (in this release 5 MHz is not supported).";
      yexte:disturbances "Changing this attribute can cause loss of traffic. Affects the resource allocation of the GB cell.";
      yexte:takes-effect "Next cell unlock";
      yexte:dependencies "Only takes effect when NbIoTCell::nbIotCellType = NBIOT_GUARDBAND";
      type erienmnrmlrat:ddt-Lrat_NbIotCell_gbPrbIndexDl;
      default 1;
    }
    leaf eDrxAllowed {
      status deprecated {
        yexte:status-information "Since 17.Q2. Planned to be removed.";
      }
      description "Set to true when idle mode eDRX shall be allowed in the cell.";
      type boolean;
      default true;
    }
    leaf hostingDigitalUnitRef {
      config false;
      description "Shows which DU or Baseband that has baseband processing for cell.";
      notife:notifiable-state-data true;
      erienmyext:enm-type MOREF;
      type string;
    }
    leaf ceLevelNumber {
      description "Coverage Enhancement level number used in the NB IoT cell.\n(CE0) Coverage enhancement level 0.\n(CE1) Coverage enhancement level 1.\n(CE2) Coverage enhancement level 2.";
      yexte:takes-effect "Cell lock/unlock";
      yexte:dependencies "ceLevelNumber <= (cmcIndex+1)";
      type erienmnrmlrat:ddt-Lrat_NbIotCell_ceLevelNumber;
      default 3;
    }
    leaf primaryFreqBand {
      description "Defines primary frequency band for the NB-IoT cell other than host cell primary frequency band. Primary frequency band defined must contain physical frequency of the NB-IoT cell. Not applicable for stand-alone deployment, only for guard-band deployment and in-band deployment.";
      yexte:disturbances "Changing this attribute can cause loss of traffic.";
      yexte:takes-effect "Next cell unlock";
      type erienmnrmlrat:ddt-Lrat_NbIotCell_primaryFreqBand;
      default -1;
    }
    leaf preambleIniRecTargetPower {
      description "Initial preamble power value in dBm, and is broadcasted as preambleInitialReceivedTargetPower in SIB2-NB.";
      yexte:takes-effect "Next cell unlock";
      type erienmnrmlrat:ddt-Lrat_NbIotCell_preambleIniRecTargetPower;
      default -110;
    }
    leaf eutranCellRef {
      description "Reference to an EUtranCellFDD MO.";
      yexte:disturbances "Changing this attribute will affect the resource allocation of the cell.";
      yexte:takes-effect "Cell lock/unlock";
      yexte:precondition "Only applicable for inband or guardband deployment. The NbIotCell Mo must be locked.";
      erienmyext:enm-type MOREF;
      type string;
    }
    list plmnIdList {
      min-elements 0;
      max-elements 6;
      key auto-generated-struct-key;
      leaf auto-generated-struct-key {
        type uint16;
        description "This leaf has been injected to allow for struct instances in a sequence to be ordered.";
        mandatory true;
      }
      description "PLMN IDs served by at least one MME. First PLMN in list is primary PLMN ID. List can include up to 6 PLMNs. Provided in NB-SIB1.";
      erienmyext:enm-type STRUCT;
      uses erienmnrmlrat:struct-PlmnIdentity;
    } // end 'list plmnIdList'
    leaf alpha {
      description "Path loss compensation factor for NPUSCH power control, and is broadcasted as alpha in SIB2-NB.";
      yexte:disturbances "Changing this attribute can affect traffic";
      yexte:takes-effect "Next cell unlock";
      type erienmnrmlrat:ddt-Lrat_NbIotCell_alpha;
      default 10;
    }
    leaf cmcIndex {
      description "Cell Maximum Coverage (CMC).\nIf 0, good coverage, requires fewer repetitions.\nIf 1, worse coverage, requires more repetitions.\nIf 2, worst coverage, requires most repetitions.";
      yexte:takes-effect "Next cell unlock";
      yexte:dependencies "ceLevelNumber <= (cmcIndex+1)";
      type erienmnrmlrat:ddt-Lrat_NbIotCell_cmcIndex;
      default 2;
    }
    leaf tTatDedicatedNbCe1 {
      description "Time alignment timer, used for supervision and control of uplink synchronization in NB IoT cell for CE Level 1. Value 0 means infinity.";
      yexte:takes-effect "Next cell unlock";
      type erienmnrmlrat:ddt-Lrat_NbIotCell_tTatDedicatedNbCe1;
      default 0;
    }
    leaf-list availabilityStatus {
      min-elements 0;
      config false;
      description "The availability status. It contains details about operationalState.";
      notife:notifiable-state-data true;
      type erienmnrmlrat:enum-AvailStatus;
    }
    leaf qRxLevMin {
      description "The required minimum received Reference Symbol Received Power (RSRP) level in the E-UTRA frequency for cell reselection. Included in NB-SIB1.";
      yexte:takes-effect "Next cell unlock";
      type erienmnrmlrat:ddt-Lrat_NbIotCell_qRxLevMin;
      default -140;
    }
    leaf tTatDedicatedNbCe0 {
      description "Time alignment timer, used for supervision and control of uplink synchronization in NB IoT cell for CE Level 0. Value 0 means infinity.";
      yexte:takes-effect "Next cell unlock";
      type erienmnrmlrat:ddt-Lrat_NbIotCell_tTatDedicatedNbCe0;
      default 0;
    }
    leaf coverageEnhancementLevel {
      status deprecated {
        yexte:status-information "Since 17.Q2. Has no functional behavior. Planned to be removed.";
      }
      description "Nb-Iot Coverage Enhancement level.";
      yexte:takes-effect "Next cell unlock";
      type erienmnrmlrat:enum-CeLevelNbIot;
      default CE_0;
    }
    leaf pMax {
      description "Limits UE uplink transmission power in the serving cell and calculates the parameter Pcompensation (defined in 3GPP TS 36.304) for cell selection. Included in NB-SIB1. Value 1000 means the parameter is not included in system information.";
      yexte:takes-effect "Next cell unlock";
      type erienmnrmlrat:ddt-Lrat_NbIotCell_pMax;
      default 1000;
    }
    list spectrumEmissionReqMapping {
      min-elements 0;
      max-elements 64;
      key auto-generated-struct-key;
      leaf auto-generated-struct-key {
        type uint16;
        description "This leaf has been injected to allow for struct instances in a sequence to be ordered.";
        mandatory true;
      }
      description "A list which maps frequency bands to network signaling values specifying additional spectrum emissions, as described by 3GPP TS 36.101, table 6.2.4-1. A band which is not explicitly mapped to a network signaling value by this list, will use the value NS_01. This list is used to generate the value of additionalSpectrumEmissionValues.";
      erienmyext:enm-type STRUCT;
      uses erienmnrmlrat:struct-SpectrumEmissionReqMapping;
    } // end 'list spectrumEmissionReqMapping'
    leaf earfcndl {
      description "Channel number for central DL frequency. Mapping from channel number to physical frequency for specified EUTRA bands is described in 3GPP TS 36.104. Usable values depend on national, operator-specific frequency allocation and supported frequency bands in RBS. Parameter earfcndl is applicable only for standalone deployment and must have a bigger value than -1.";
      yexte:disturbances "Changing this attribute may affect traffic.";
      yexte:takes-effect "Next cell unlock";
      type erienmnrmlrat:ddt-Lrat_NbIotCell_earfcndl;
      default -1;
    }
    leaf modificationPeriodCoeff {
      status deprecated {
        yexte:status-information "Since 17.Q2. Planned to be removed.";
      }
      description "Actual modification period, expressed in number of radio frames= modificationPeriodCoeff * defaultPagingCycleNbIot. See MO Paging for more info on defaultPagingCycleNbIot. Provided in NB-SIB2.";
      yexte:takes-effect "Next cell unlock";
      type erienmnrmlrat:ddt-Lrat_NbIotCell_modificationPeriodCoeff;
      default 16;
    }
    container intraFrequencyInfo {
      description "Intra-frequency related information.";
      erienmyext:enm-type STRUCT;
      uses erienmnrmlrat:struct-NbIotIntraFrequencyInfo;
    } // end 'container intraFrequencyInfo'
    leaf physicalLayerCellIdGroup {
      status deprecated {
        yexte:status-information "Since L17A. Planned to be removed.";
      }
      description "Physical layer cell ID group.\nPhysical layer cell IDs are grouped into 168 unique physical layer cell ID groups. Each group contains 3 unique subidentities.\nUsed with physicalLayerSubCellId to calculate physical layer cell ID.";
      yexte:disturbances "Changing this attribute can cause loss of traffic.";
      type erienmnrmlrat:ddt-Lrat_NbIotCell_physicalLayerCellIdGroup;
      default 0;
    }
    leaf anchPowerBoostGainIndex {
      description "Power boosting gain index of NB-IoT cell anchor carrier, compared with the average PRB power over all carriers (both LTE and NB-IoT) in host cell.";
      yexte:takes-effect "Next cell unlock";
      type erienmnrmlrat:enum-AnchorPowerBoostIndex;
      default ANCHOR_POWER_RATIO_4_1;
    }
    leaf prbIndex {
      status deprecated {
        yexte:status-information "Since 17.Q3. Planned to be removed.";
      }
      description "Downlink PRB index used by the Nb-Iot Cell (inband or guardband deployment).\nFor guardband deployment, the PRB index is outside of the PRB value range of the EUtranCellFDD (below 0 or above the cell's highest PRB index).";
      yexte:takes-effect "Next cell unlock";
      yexte:precondition "Only applicable for inband or guardband deployment. The NbIotCell MO must be locked.";
      type erienmnrmlrat:ddt-Lrat_NbIotCell_prbIndex;
      default 255;
    }
    leaf sIntraSearchThreshold {
      description "Cell Reselection Threshold (intra-frequency measurements). Provided in NB-SIB3.";
      yexte:takes-effect "Next cell unlock";
      type erienmnrmlrat:ddt-Lrat_NbIotCell_sIntraSearchThreshold;
      default 0;
    }
    leaf-list ulAllocatedPrb {
      min-elements 1;
      max-elements 8;
      erienmyext:no-notification;
      config false;
      description "NB-IoT cell uplink PRB index. Element 0 means anchor uplink PRB index. Elements 1-7 mean non-anchor uplink PRB index.\nUndefined value: 255";
      yexte:dependencies "Only applicable for inband and guardband deployment.";
      type erienmnrmlrat:ddt-Lrat_NbIotCell_ulAllocatedPrb;
    }
    leaf earfcnul {
      description "Channel number for central UL frequency. Mapping from channel number to physical frequency for specified EUTRA bands is described in 3GPP TS 36.104. Usable values depend on national, operator-specific frequency allocation and supported frequency bands in RBS. Parameter earfcnul applicable only for standalone deployment.";
      yexte:disturbances "Changing this attribute will affect the cell frequency handling.";
      yexte:takes-effect "Next cell unlock";
      yexte:dependencies "Offset of EARFCN UL to EARFCN DL is calculated automatically as described in 3GPP TS36.104. To use calculated offset, leave earfcnul undefined. To override calculated offset, set earfcnul.";
      type erienmnrmlrat:ddt-Lrat_NbIotCell_earfcnul;
      default -1;
    }
    leaf dlAnchPrbIndex {
      description "Downlink anchor carrier PRB index used by NB-Iot cell. Common for inband and guardband deployment.\nFor inband deployment, the PRB index is inside of the PRB value range of the EUtranCellFDD host cell (0 to the cell's highest PRB index).\nFor guardband deployment, the PRB index is outside of the PRB value range of the EUtranCellFDD host cell (below 0 or above the cell's highest PRB index). 5 MHz is not supported.\nIf this attribute is set to default value, system allocates the downlink anchor carrier.";
      yexte:takes-effect "Next cell unlock";
      yexte:dependencies "Only applicable for inband and guardband deployment.";
      type erienmnrmlrat:ddt-Lrat_NbIotCell_dlAnchPrbIndex;
      default 255;
    }
    leaf-list sectorCarrierRef {
      min-elements 0;
      max-elements 12;
      description "Reference list to instances of SectorCarrier MOs.";
      yexte:disturbances "Changing this attribute can cause loss of traffic. Affects resource allocation of cell.";
      yexte:takes-effect "For standalone: Next Nb-IoT cell unlock\nFor inband and guardband: Next Nb-IoT cell unlock after next host LTE cell unlock";
      yexte:dependencies "Applicable in standalone deployment. For inband and guardband deployment, only applicable when host LTE combined cell is configured with two sector carriers with 2T2R.";
      erienmyext:enm-type MOREF;
      type string;
    }
  } // end 'grouping moc-NbIotCell'
  grouping moc-ParameterChangeRequests-keys {
    description "Key(s) for MOC ParameterChangeRequests";
    leaf id {
      erienmyext:no-notification;
      description "The value component of the Relative Distinguished Name (RDN).";
      mandatory true;
      yexte:ecim-name parameterChangeRequestsId;
      type string;
    }
  } // end 'grouping moc-ParameterChangeRequests-keys'
  grouping moc-ParameterChangeRequests {
    description "Contains list of parameter change requests produced by open loop SON functions.\n\nThe RDN of this MO is ParameterChangeRequests=1.";
    list parameterChangeRequestList {
      min-elements 0;
      max-elements 250;
      key auto-generated-struct-key;
      leaf auto-generated-struct-key {
        type uint16;
        description "This leaf has been injected to allow for struct instances in a sequence to be ordered.";
        mandatory true;
      }
      description "The complete list of outstanding parameter change requests.";
      erienmyext:enm-type STRUCT;
      uses erienmnrmlrat:struct-ParameterChangeRequestRO;
    } // end 'list parameterChangeRequestList'
    container latestUpdate {
      description "The latest changed parameter change request.";
      erienmyext:enm-type STRUCT;
      uses erienmnrmlrat:struct-ParameterChangeRequestRO;
    } // end 'container latestUpdate'
    action approve {
      description "Approves a set of pending change request. ";
      input {
        leaf-list pcrList {
          min-elements 0;
          description "A list of integers matching the seqNo of the change requests. Any integer not matching a pending change request will be ignored.";
          type int32;
        }
      }
    }
    action reject {
      description "Rejects a set of pending change request.";
      input {
        leaf-list pcrList {
          min-elements 0;
          description "A list of integers matching the seqNo of the change requests. Any integer not matching a pending change request will be ignored.";
          type int32;
        }
      }
    }
  } // end 'grouping moc-ParameterChangeRequests'
  grouping moc-MdtConfiguration-keys {
    description "Key(s) for MOC MdtConfiguration";
    leaf id {
      erienmyext:no-notification;
      description "The value component of the RDN.";
      mandatory true;
      yexte:ecim-name mdtConfigurationId;
      type string;
    }
  } // end 'grouping moc-MdtConfiguration-keys'
  grouping moc-MdtConfiguration {
    description "Contains the parameters for the Minimization of Drive Tests (MDT).\n\nThe RDN of this MO is MdtConfiguration=1.";
    leaf a2ThresholdRsrqMdt {
      description "RSRQ threshold value for eventA2 that triggers the MDT UE measurement.";
      yexte:takes-effect "New connection";
      type erienmnrmlrat:ddt-Lrat_MdtConfiguration_a2ThresholdRsrqMdt;
      default -195;
    }
    leaf maxReportCellsA2Mdt {
      description "Maximum number of cells to include in the measurement report for the eventA2 measurement.";
      yexte:takes-effect "New connection";
      type erienmnrmlrat:ddt-Lrat_MdtConfiguration_maxReportCellsA2Mdt;
      default 4;
    }
    leaf a2ThresholdRsrpMdt {
      description "RSRP threshold value for eventA2 that triggers the MDT UE measurement.";
      yexte:takes-effect "New connection";
      type erienmnrmlrat:ddt-Lrat_MdtConfiguration_a2ThresholdRsrpMdt;
      default -140;
    }
    leaf reportQuantityA2Mdt {
      description "The quantities to include in the measurement report for the MDT eventA2 measurement.\nThe value 0 - SAME_AS_TRIGGER_QUANTITY means that the same quantity as triggerQuantityA2Mdt is included in the measurement report.\nThe value 1 - BOTH means that both Reference Symbol Received Power (RSRP) and Reference Symbol Received Quality (RSRQ) quantities are included in the measurement report.";
      yexte:takes-effect "New connection";
      type erienmnrmlrat:enum-ReportQuantity;
      default BOTH;
    }
    leaf timeToTriggerA2Mdt {
      description "The time-to-trigger value for the MDT eventA2 measurement.";
      yexte:takes-effect "New connection";
      type erienmnrmlrat:ddt-Lrat_MdtConfiguration_timeToTriggerA2Mdt;
      default 640;
    }
    leaf hysteresisA2Mdt {
      description "The hysteresis value for the MDT eventA2 measurement.";
      yexte:takes-effect "New connection";
      type erienmnrmlrat:ddt-Lrat_MdtConfiguration_hysteresisA2Mdt;
      default 10;
    }
    leaf reportingTrigger {
      description "Reporting trigger used for UE side MDT measurement.";
      yexte:takes-effect "New connection";
      type erienmnrmlrat:enum-MdtReportingTrigger;
      default PERIODICAL;
    }
    leaf triggerQuantityA2Mdt {
      description "The Reference Signal Received Power (RSRP) or Reference Signal Received Quality (RSRQ) quantity that triggers the MDT eventA2.";
      yexte:takes-effect "New connection";
      type erienmnrmlrat:enum-TriggerQuantity;
      default RSRP;
    }
    leaf positioningMethod {
      description "Positioning method used to obtain UE location information.";
      yexte:takes-effect "New connection";
      type erienmnrmlrat:enum-PositioningMethod;
      default GNSS;
    }
    leaf reportIntervalMdt {
      description "Report interval between the periodical measurements used for UE side MDT measurement.";
      yexte:takes-effect "New connection";
      type erienmnrmlrat:enum-ReportInterval;
      default MS_10240;
    }
    leaf reportAmountMdt {
      description "Number of MDT measurements to be taken for periodical reporting.\nValue 0 means that reports are sent as long as the event is fulfilled.";
      yexte:takes-effect "New connection";
      type erienmnrmlrat:ddt-Lrat_MdtConfiguration_reportAmountMdt;
      default 16;
    }
    leaf measGapAllowedMdt {
      description "Whether or not measurement gap configuration is allowed for EUTRAN inter-frequency measurements.";
      yexte:takes-effect "New connection";
      type boolean;
      default true;
    }
  } // end 'grouping moc-MdtConfiguration'
  grouping moc-ReportConfigB2Cdma20001xRtt-keys {
    description "Key(s) for MOC ReportConfigB2Cdma20001xRtt";
    leaf id {
      erienmyext:no-notification;
      description "The value component of the RDN.";
      mandatory true;
      yexte:ecim-name reportConfigB2Cdma20001xRttId;
      type string;
    }
  } // end 'grouping moc-ReportConfigB2Cdma20001xRtt-keys'
  grouping moc-ReportConfigB2Cdma20001xRtt {
    description "This managed object contains report configuration settings for the B2 event for CDMA2000 1xRTT measurements, used when searching for a suitable target cell when SRVCC is triggered for the UE. The B2 event is used to detect when a CDMA2000 1xRTT cell becomes better than threshold2, and serving cell becomes worse than threshold1. The actual threshold values used can be adjusted by frequency relation related offsets if the feature Multi-Layer Service-Triggered Mobility (MLSTM) is enabled.\n\nThe RDN of this MO is ReportConfigB2Cdma20001xRtt=1.";
    leaf b2Threshold1Rsrp {
      description "The Reference Signal Received Power (RSRP) threshold1 value for eventB2.";
      yexte:takes-effect "New connection";
      yexte:dependencies "Only used if triggerQuantityB2 is set to RSRP.";
      type erienmnrmlrat:ddt-Lrat_ReportConfigB2Cdma20001xRtt_b2Threshold1Rsrp;
      default -140;
    }
    leaf b2Threshold1Rsrq {
      description "The Reference Signal Received Quality (RSRQ) threshold1 value for eventB2.";
      yexte:takes-effect "New connection";
      yexte:dependencies "Only used if triggerQuantityB2 is set to RSRQ.";
      type erienmnrmlrat:ddt-Lrat_ReportConfigB2Cdma20001xRtt_b2Threshold1Rsrq;
      default -195;
    }
    leaf triggerQuantityB2 {
      description "The quantity for threshold1 that is sent to the UE, and is used together with threshold2 to trigger the eventB2.";
      yexte:takes-effect "New connection";
      type erienmnrmlrat:enum-TriggerQuantity;
      default RSRP;
    }
    leaf hysteresisB2RsrqOffset {
      description "Offset to obtain the Hysteresis for B2 measurement for trigger quantity RSRQ. hysteresisB2Rsrq = hysteresisB2 + hysteresisB2RsrqOffset";
      yexte:takes-effect "New connection";
      yexte:dependencies "Feature Mobility Control at Poor Coverage must be active.";
      type erienmnrmlrat:ddt-Lrat_ReportConfigB2Cdma20001xRtt_hysteresisB2RsrqOffset;
      default 0;
    }
    leaf timeToTriggerB2Rsrq {
      description "Time-to-trigger value for event B2 with trigger quantity RSRQ. If set to -1, this attribute is not used for report configuration.";
      yexte:takes-effect "New connection";
      yexte:dependencies "Feature Mobility Control at Poor Coverage must be active.";
      type erienmnrmlrat:ddt-Lrat_ReportConfigB2Cdma20001xRtt_timeToTriggerB2Rsrq;
      default -1;
    }
    leaf hysteresisB2 {
      description "The hysteresis value for the event B2 measurement.";
      yexte:takes-effect "New connection";
      type erienmnrmlrat:ddt-Lrat_ReportConfigB2Cdma20001xRtt_hysteresisB2;
      default 10;
    }
    leaf b2Threshold2Cdma20001xRtt {
      description "The Signal Quality in the thresholdCDMA2000, threshold2 value for eventB2.";
      yexte:takes-effect "New connection";
      type erienmnrmlrat:ddt-Lrat_ReportConfigB2Cdma20001xRtt_b2Threshold2Cdma20001xRtt;
      default -75;
    }
    leaf timeToTriggerB2 {
      description "Time-to-trigger value for event B2 measurements. If timeToTriggerB2Rsrq is -1, this attribute is used for both RSRP and RSRQ. But if not set to -1, this attribute is used only for RSRP.";
      yexte:takes-effect "New connection";
      type erienmnrmlrat:ddt-Lrat_ReportConfigB2Cdma20001xRtt_timeToTriggerB2;
      default 640;
    }
  } // end 'grouping moc-ReportConfigB2Cdma20001xRtt'
  grouping moc-ReportConfigEUtraIntraFreqPm-keys {
    description "Key(s) for MOC ReportConfigEUtraIntraFreqPm";
    leaf id {
      erienmyext:no-notification;
      description "The value component of the Relative Distinguished Name (RDN).\n";
      mandatory true;
      yexte:ecim-name reportConfigEUtraIntraFreqPmId;
      type string;
    }
  } // end 'grouping moc-ReportConfigEUtraIntraFreqPm-keys'
  grouping moc-ReportConfigEUtraIntraFreqPm {
    description "This managed object contains the Report Configuration settings for UE measurements on EUTRA intra frequencies initiated by PM.\n";
    leaf triggerQuantityPm {
      description "The Reference Signal Received Power (RSRP) or Reference Signal Received Quality (RSRQ) quantity that triggers the PM-initiated E-UTRA measurements.";
      yexte:takes-effect "New connection";
      type erienmnrmlrat:enum-TriggerQuantity;
      default RSRP;
    }
    leaf timeToTriggerPm {
      description "Time during which specific event criteria must be met to trigger a measurement report for PM-Initiated UE Measurements. Used only when measSelectionEUtraPm is set to EVENT_A1, EVENT_A2, EVENT_A3, EVENT_A4 or EVENT_A5.";
      yexte:takes-effect "New connection";
      type erienmnrmlrat:ddt-Lrat_ReportConfigEUtraIntraFreqPm_timeToTriggerPm;
      default 640;
    }
    leaf a3OffsetPm {
      description "The offset value for eventA3, for PM Initiated UE Measurements.\nOnly used if measSelectionEUtraPm is set to EVENT_A3.\n";
      yexte:takes-effect "New connection";
      type erienmnrmlrat:ddt-Lrat_ReportConfigEUtraIntraFreqPm_a3OffsetPm;
      default 5;
    }
    leaf a3ReportOnLeavePm {
      description "Indicates that the UE initiates the measurement reporting procedure when the leaving condition is met for a cell. Used only when measSelectionEUtraPm is set to EVENT_A3.";
      yexte:takes-effect "New connection";
      type boolean;
      default false;
    }
    leaf a1ThresholdRsrpPm {
      description "The Reference Signal Received Power (RSRP) threshold value for eventA1 for PM-Initiated UE Measurements. Used only when triggerQuantityPm is set to RSRP and measSelectionEUtraPm is set to EVENT_A1.";
      yexte:takes-effect "New connection";
      type erienmnrmlrat:ddt-Lrat_ReportConfigEUtraIntraFreqPm_a1ThresholdRsrpPm;
      default -140;
    }
    leaf reportAmountPm {
      description "The number of periodical reports for PM-Initiated UE Measurements.\nValue 0 means that reports are sent as long as the event is fulfilled.";
      yexte:takes-effect "New connection";
      type erienmnrmlrat:ddt-Lrat_ReportConfigEUtraIntraFreqPm_reportAmountPm;
      default 0;
    }
    leaf measSelectionEUtraPm {
      description "The type of measurement for which this MO is currently configured. The options A1-A5 correspond to respective thresholds/offsets that trigger these events.\nSelecting PERIODICAL results in periodical measurement reports with no specific trigger. PERIODICAL measurement reporting is limited to reporting the strongest cells.";
      yexte:takes-effect "New connection";
      type erienmnrmlrat:enum-MeasSelectionEUtra;
      default PERIODICAL;
    }
    leaf a1ThresholdRsrqPm {
      description "The Reference Signal Received Quality (RSRQ) threshold value for eventA1 for PM-Initiated UE Measurements. Used only when triggerQuantityPm is set to RSRQ and measSelectionEUtraPm is set to EVENT_A1.";
      yexte:takes-effect "New connection";
      type erienmnrmlrat:ddt-Lrat_ReportConfigEUtraIntraFreqPm_a1ThresholdRsrqPm;
      default -195;
    }
    leaf a2ThresholdRsrpPm {
      description "The Reference Signal Received Power (RSRP) threshold value for eventA2 for PM-Initiated UE Measurements. Used only when triggerQuantityPm is set to RSRP and measSelectionEUtraPm is set to EVENT_A2.";
      yexte:takes-effect "New connection";
      type erienmnrmlrat:ddt-Lrat_ReportConfigEUtraIntraFreqPm_a2ThresholdRsrpPm;
      default -140;
    }
    leaf reportIntervalPm {
      description "The interval for event-triggered periodical reporting for PM-Initiated UE Measurements.";
      yexte:takes-effect "New connection";
      type erienmnrmlrat:enum-ReportInterval;
      default MIN_1;
    }
    leaf a2ThresholdRsrqPm {
      description "The Reference Signal Received Quality (RSRQ) threshold value for eventA2 for PM-Initiated UE Measurements. Used only when triggerQuantityPm is set to RSRQ and measSelectionEUtraPm is set to EVENT_A2.";
      yexte:takes-effect "New connection";
      type erienmnrmlrat:ddt-Lrat_ReportConfigEUtraIntraFreqPm_a2ThresholdRsrqPm;
      default -195;
    }
    leaf reportQuantityPm {
      description "The quantities to include in the measurement report for PM-Initiated UE Measurements.\nThe value 0, sameAsTriggerQuantity, means that the same quantity as triggerQuantityPm is included in the measurement report.\nThe value 1, both, means that both Reference Signal Received Power (RSRP) and Reference Signal Received Quality (RSRQ) quantities are included in the measurement report.";
      yexte:takes-effect "New connection";
      type erienmnrmlrat:enum-ReportQuantity;
      default BOTH;
    }
    leaf hysteresisPm {
      description "The hysteresis value for the condition triggering the entering and leaving measurement report for PM-Initiated UE Measurements. Used only when measSelectionEUtraPm is set to EVENT_A1, EVENT_A2, EVENT_A3, EVENT_A4 or EVENT_A5.";
      yexte:takes-effect "New connection";
      type erienmnrmlrat:ddt-Lrat_ReportConfigEUtraIntraFreqPm_hysteresisPm;
      default 10;
    }
    leaf-list reservedBy {
      min-elements 0;
      config false;
      description "Contains a list of MO instances that reserve this MO instance.\n";
      yexte:dependencies "The managed object cannot be deleted if it is reserved.";
      notife:notifiable-state-data true;
      erienmyext:enm-type MOREF;
      type string;
    }
    leaf a5ThresholdRsrqPm1 {
      description "The Reference Signal Received Quality (RSRQ) threshold 1 value for eventA5 for PM-Initiated UE Measurements. Used only when triggerQuantityPm is set to RSRQ and measSelectionEUtraPm is set to EVENT_A5.";
      yexte:takes-effect "New connection";
      type erienmnrmlrat:ddt-Lrat_ReportConfigEUtraIntraFreqPm_a5ThresholdRsrqPm1;
      default -195;
    }
    leaf maxReportCellsPm {
      description "Maximum number of cells to include in the measurement report for the PM Initiated UE Measurements.\n";
      yexte:takes-effect "New connection";
      type erienmnrmlrat:ddt-Lrat_ReportConfigEUtraIntraFreqPm_maxReportCellsPm;
      default 4;
    }
    leaf a4ThresholdRsrpPm {
      description "The Reference Signal Received Power (RSRP) threshold value for eventA4 for PM-Initiated UE Measurements. Used only when triggerQuantityPm is set to RSRP and measSelectionEUtraPm is set to EVENT_A4.";
      yexte:takes-effect "New connection";
      type erienmnrmlrat:ddt-Lrat_ReportConfigEUtraIntraFreqPm_a4ThresholdRsrpPm;
      default -140;
    }
    leaf a5ThresholdRsrpPm1 {
      description "The Reference Signal Received Power (RSRP) threshold 1 value for eventA5 for PM-Initiated UE Measurements. Used only when triggerQuantityPm is set to RSRP and measSelectionEUtraPm is set to EVENT_A5.";
      yexte:takes-effect "New connection";
      type erienmnrmlrat:ddt-Lrat_ReportConfigEUtraIntraFreqPm_a5ThresholdRsrpPm1;
      default -140;
    }
    leaf a5ThresholdRsrqPm2 {
      description "The Reference Signal Received Quality (RSRQ) threshold 2 value for eventA5 for PM-Initiated UE Measurements. Used only when triggerQuantityPm is set to RSRQ and measSelectionEUtraPm is set to EVENT_A5.";
      yexte:takes-effect "New connection";
      type erienmnrmlrat:ddt-Lrat_ReportConfigEUtraIntraFreqPm_a5ThresholdRsrqPm2;
      default -195;
    }
    leaf a4ThresholdRsrqPm {
      description "The Reference Signal Received Quality (RSRQ) threshold value for eventA4 for PM-Initiated UE Measurements. Used only when triggerQuantityPm is set to RSRQ and measSelectionEUtraPm is set to EVENT_A4.";
      yexte:takes-effect "New connection";
      type erienmnrmlrat:ddt-Lrat_ReportConfigEUtraIntraFreqPm_a4ThresholdRsrqPm;
      default -195;
    }
    leaf a5ThresholdRsrpPm2 {
      description "The Reference Signal Received Power (RSRP) threshold 2 value for eventA5 for PM-Initiated UE Measurements. Used only when triggerQuantityPm is set to RSRP and measSelectionEUtraPm is set to EVENT_A5.";
      yexte:takes-effect "New connection";
      type erienmnrmlrat:ddt-Lrat_ReportConfigEUtraIntraFreqPm_a5ThresholdRsrpPm2;
      default -140;
    }
  } // end 'grouping moc-ReportConfigEUtraIntraFreqPm'
  grouping moc-BandCombCompression-keys {
    description "Key(s) for MOC BandCombCompression";
    leaf id {
      erienmyext:no-notification;
      description "The value component of the RDN.";
      mandatory true;
      yexte:ecim-name bandCombCompressionId;
      type string;
    }
  } // end 'grouping moc-BandCombCompression-keys'
  grouping moc-BandCombCompression {
    description "Compression of CA combinations. Attributes take effect only if license for Carrier Aggregation is present and the feature is active.\n\nThe RDN of this MO is BandCombCompression=1.";
    leaf requestedBandCombCompression {
      description "Controls which UEs are used to query the UE band combination support. Determines size of UE band combination report. UE must support at least release 11.";
      yexte:takes-effect "At next UE capability refresh.";
      type erienmnrmlrat:enum-RequestedBandCombCompression;
      default R11_REQUESTED_BAND_COMBO;
    }
    leaf requestMaxCCsDL {
      description "Request for UE capability enquiry message of maximum number of CCs in DL for which UE is requested to provide supported CA band combinations and non-Carrier Aggregation bands. If set to 0 or 1, then indication is not sent to UE. UE must support at least release 13.";
      yexte:takes-effect "At next UE capability refresh.";
      type erienmnrmlrat:ddt-Lrat_BandCombCompression_requestMaxCCsDL;
      default 0;
    }
    leaf-list requestedFreqBandsFiltered {
      min-elements 0;
      max-elements 16;
      description "List of frequency bands requested in UE Capability Enquiry for CA band combinations information. If list is empty, it is controlled by Network Requested band combination signaling feature. Invalid band numbers are ignored. If provided list does not contain at least 1 LAA band and LAA is activated and operational, then LAA band will be automatically added to the list. If list has maximum number of elements, then last one will be replaced. UE must support at least release 11.";
      yexte:takes-effect "At next UE capability refresh.";
      type erienmnrmlrat:ddt-Lrat_BandCombCompression_requestedFreqBandsFiltered;
    }
    leaf requestMaxCCsUL {
      description "Request for UE capability enquiry message of maximum number of CCs in UL for which UE is requested to provide supported Carrier Aggregation band combinations and non-Carrier Aggregation bands. If set to 0 or 1, then indication is not send to UE. UE must support at least release 13.";
      yexte:takes-effect "At next UE capability refresh.";
      type erienmnrmlrat:ddt-Lrat_BandCombCompression_requestMaxCCsUL;
      default 0;
    }
    action populateRequestedFreqBandsFiltered {
      description "Checks for which E-UTRAN frequency relation exists E-UTRAN cell relation with SCell candidate allowed. Populates bands in requestedFreqBandsFiltered. Any previous content of requestedFreqBandsFiltered is removed.";
    }
  } // end 'grouping moc-BandCombCompression'
  grouping moc-UserProfile-keys {
    description "Key(s) for MOC UserProfile";
    leaf id {
      erienmyext:no-notification;
      description "The value component of the RDN.";
      mandatory true;
      yexte:ecim-name userProfileId;
      type string;
    }
  } // end 'grouping moc-UserProfile-keys'
  grouping moc-UserProfile {
    description "A combination of attributes specifies which SCI profile a given bearer should be assigned.";
    leaf-list spidList {
      min-elements 0;
      max-elements 20;
      description "Which SPID values are included in user profile. Empty list means all are included.";
      yexte:disturbances "Changing this attribute can affect traffic.";
      yexte:takes-effect "New connection";
      type erienmnrmlrat:ddt-Lrat_UserProfile_spidList;
    }
    leaf-list reservedBy {
      min-elements 0;
      config false;
      description "List of MO instances that reserve this MO instance.";
      yexte:dependencies "MO can not be deleted if it is reserved.";
      notife:notifiable-state-data true;
      erienmyext:enm-type MOREF;
      type string;
    }
    list plmnList {
      min-elements 0;
      max-elements 6;
      key auto-generated-struct-key;
      leaf auto-generated-struct-key {
        type uint16;
        description "This leaf has been injected to allow for struct instances in a sequence to be ordered.";
        mandatory true;
      }
      description "Which PLMNs are included in user profile. Empty list means all are included.";
      erienmyext:enm-type STRUCT;
      uses erienmnrmlrat:struct-PlmnIdentity;
    } // end 'list plmnList'
    leaf userProfileName {
      description "Name of user profile.";
      yexte:takes-effect "New connection";
      type string;
      default "";
    }
    leaf-list arpList {
      min-elements 0;
      max-elements 15;
      description "Which ARP values are included in user profile. Empty list means all are included.";
      yexte:disturbances "Changing this attribute can affect traffic.";
      yexte:takes-effect "New connection";
      type erienmnrmlrat:ddt-Lrat_UserProfile_arpList;
    }
  } // end 'grouping moc-UserProfile'
  grouping moc-ReportConfigB1GUtra-keys {
    description "Key(s) for MOC ReportConfigB1GUtra";
    leaf id {
      erienmyext:no-notification;
      description "The value component of the RDN.";
      mandatory true;
      yexte:ecim-name reportConfigB1GUtraId;
      type string;
    }
  } // end 'grouping moc-ReportConfigB1GUtra-keys'
  grouping moc-ReportConfigB1GUtra {
    description "Contains report configuration settings for event B1 GUtra measurements.\n\nThe RDN of this MO is ReportConfigB1GUtra=1.";
    leaf timeToTriggerB1 {
      description "Time-to-trigger value for event B1.";
      yexte:takes-effect "New connection";
      type erienmnrmlrat:ddt-Lrat_ReportConfigB1GUtra_timeToTriggerB1;
      default 0;
    }
    leaf triggerQuantityB1 {
      description "The quantity that triggers the event B1.";
      yexte:takes-effect "New connection";
      type erienmnrmlrat:enum-TriggerQuantityGUtra;
      default SS_RSRP;
    }
    leaf b1Threshold {
      description "Threshold value for event B1.";
      yexte:takes-effect "New connection";
      type erienmnrmlrat:ddt-Lrat_ReportConfigB1GUtra_b1Threshold;
      default 0;
    }
    leaf hysteresisB1 {
      description "Hysteresis value for event B1 measurement.";
      yexte:takes-effect "New connection";
      type erienmnrmlrat:ddt-Lrat_ReportConfigB1GUtra_hysteresisB1;
      default 0;
    }
  } // end 'grouping moc-ReportConfigB1GUtra'
  grouping moc-AdmissionControl-keys {
    description "Key(s) for MOC AdmissionControl";
    leaf id {
      erienmyext:no-notification;
      description "The value component of the Relative Distinguished Name (RDN).";
      mandatory true;
      yexte:ecim-name admissionControlId;
      type string;
    }
  } // end 'grouping moc-AdmissionControl-keys'
  grouping moc-AdmissionControl {
    description "Contains parameters for admission control function.\n\nThe RDN of this MO is AdmissionControl=1.";
    leaf zzzTemp4 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 1";
      yexte:takes-effect "Cell lock/unlock";
      type erienmnrmlrat:ddt-Lrat_AdmissionControl_zzzTemp4;
      default -1;
    }
    leaf zzzTemp5 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 1";
      yexte:takes-effect "Cell lock/unlock";
      type erienmnrmlrat:ddt-Lrat_AdmissionControl_zzzTemp5;
      default -1;
    }
    leaf admResourceMinQciPrio {
      description "Lowest QCI priority (highest numerical value) for DRBs included into monitoring of radio resources considered in GBR bearer admission control.\nFor any value of this parameter, bearer admission control also takes into account resource usage from non-DRB traffic with higher priority than DRBs, e.g. Signaling Radio Bearers. If this parameter is set to 0, only the resource usage for traffic with priority higher than DRBs is monitored.";
      yexte:takes-effect "Cell lock/unlock";
      type erienmnrmlrat:ddt-Lrat_AdmissionControl_admResourceMinQciPrio;
      default 5;
    }
    leaf zzzTemp2 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 1";
      yexte:takes-effect "Cell lock/unlock";
      type erienmnrmlrat:ddt-Lrat_AdmissionControl_zzzTemp2;
      default -1;
    }
    leaf zzzTemp3 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 1";
      yexte:takes-effect "Cell lock/unlock";
      type erienmnrmlrat:ddt-Lrat_AdmissionControl_zzzTemp3;
      default -1;
    }
    leaf zzzTemp1 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 1";
      yexte:takes-effect "Cell lock/unlock";
      type erienmnrmlrat:ddt-Lrat_AdmissionControl_zzzTemp1;
      default -1;
    }
    leaf zzzTemp8 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp8;
      default 1000;
    }
    leaf zzzTemp9 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp9;
      default 1000;
    }
    leaf admNrRrcDifferentiationThr {
      description "Highest allowed fraction of non-privileged RRC connections that might be admitted without ARP based differentiation. When fraction of RRC connected users versus available capacity exceeds this threshold, only RRC connections that setup bearers with high ARP priority are admitted. Other RRC connections may only be admitted if preemption is possible. The fraction is given with respect to the maximum capacity after privileged access resource reservation has been subtracted.";
      yexte:takes-effect "Cell lock/unlock";
      type erienmnrmlrat:ddt-Lrat_AdmissionControl_admNrRrcDifferentiationThr;
      default 750;
    }
    leaf zzzTemp6 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp6;
      default 1000;
    }
    leaf arpBasedPreEmptionState {
      description "Activates or deactivates the Allocation and Retention Priority (ARP) based pre-emption function.\nThe value of the attribute is irrelevant when no valid license key is installed for the Differentiated Admission Control feature.";
      yexte:takes-effect "Cell lock/unlock";
      type erienmnrmlrat:enum-ActivationVals;
      default DEACTIVATED;
    }
    leaf zzzTemp7 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp7;
      default 1000;
    }
    leaf admNrRbDifferentiationThr {
      description "Highest allowed fraction of radio bearers not reserved for privileged access connections that might be admitted without ARP based differentiation. When fraction of active radio bearers versus available capacity exceeds this threshold, only bearer requests with high ARP priority are admitted. Other bearer requests may only be admitted if preemption is possible. The fraction is given with respect to the maximum capacity after privileged access resource reservation has been subtracted.";
      yexte:takes-effect "Cell lock/unlock";
      type erienmnrmlrat:ddt-Lrat_AdmissionControl_admNrRbDifferentiationThr;
      default 750;
    }
    leaf limitSrNonPa {
      description "Number of Scheduling Request resources in limitation pool for privileged access connections per cell.";
      yexte:takes-effect "Next cell unlock";
      yexte:dependencies "Threshold for allocation of an additional PUCCH format 1 PRB pair by dynamic PUCCH must be higher than number of resources in limitation pool.\n(EUtranCellFDD/EUtranCellTDD::allocThrPucchFormat1 > limitSrNonPa)";
      type erienmnrmlrat:ddt-Lrat_AdmissionControl_limitSrNonPa;
      default 0;
    }
    leaf paArpOverride {
      description "The eNB interprets Allocation Retention Priority Levels, received from the Core Network, between 1 and paArpOverride (inclusive) as Privileged Access.\nThe value zero will disable Privileged Access ARP override.\n";
      yexte:disturbances "Changing this attribute can impact accessibility at high load.";
      type erienmnrmlrat:ddt-Lrat_AdmissionControl_paArpOverride;
      default 7;
    }
    leaf zzzTemp20 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp20;
      default 1000;
    }
    leaf zzzTemp21 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp21;
      default 1000;
    }
    leaf srBbmPaUsersPreallocation {
      description "Indicates if Scheduling Request (SR) resources preallocation for privileged access connections is activated in eNodeB.";
      yexte:takes-effect "Next cell unlock";
      type boolean;
      default false;
    }
    leaf ulAdmDifferentiationThr {
      description "If both Dynamic GBR Admission Control and Differentiated Admission Control are licensed and activated:\nSets the highest allowed uplink radio resource utilization ratio for the GBR bearers with lower ARP priority in radio bearer admission. Applies to each resource considered by Dynamic GBR Admission Control.\nIf Dynamic GBR Admission Control is licensed and activated but Differentiated Admission Control is not licensed or not activated:\nSets the highest allowed uplink radio resource utilization ratio for the GBR bearers in radio bearer admission. Applies to each resource considered by Dynamic GBR Admission Control.";
      yexte:takes-effect "Cell lock/unlock";
      yexte:dependencies ulAdmDifferentiationThr<=ulAdmOverloadThr;
      type erienmnrmlrat:ddt-Lrat_AdmissionControl_ulAdmDifferentiationThr;
      default 500;
    }
    leaf dlMbmsGbrRatio {
      description "This parameter sets the wanted downlink resource utilization ratio of Mbms-Gbr bearers on transport network. The value given in this parameter specifies the Mbms-Gbr part of the total bandwidth. The parameter will be used by the Admission Control to balance Gbr, Mbms-Gbr and Non-Gbr use of resources.\nUnit: 0.001\n";
      yexte:takes-effect "Cell lock/unlock";
      yexte:dependencies "The downlink transport network bandwidth for LTE needs to be configured into attribute AdmissionControl::dlTransNwBandwidth.";
      type erienmnrmlrat:ddt-Lrat_AdmissionControl_dlMbmsGbrRatio;
      default 200;
    }
    leaf resourceReservationForDifferentiation {
      description "Sets the resource reservation used for ARP based differentiation. The value of this attribute is irrelevant when no valid license key is installed for the Differentiated Admission Control feature.";
      yexte:takes-effect "Cell lock/unlock";
      type erienmnrmlrat:ddt-Lrat_AdmissionControl_resourceReservationForDifferentiation;
      default 5;
    }
    leaf resourceReservationForPAState {
      description "Activates or deactivates the Resource Reservation for Priviliged Access.";
      yexte:disturbances "Changing this attribute can impact accessibility at high load.";
      yexte:takes-effect "Cell lock/unlock";
      type erienmnrmlrat:enum-ActivationVals;
      default DEACTIVATED;
    }
    leaf nrOfRbReservationsPerPaConn {
      description "Number of Radio Bearers to be reserved per privileged access connection. This includes SRB1, SRB2 and DRBs.";
      yexte:takes-effect "Cell lock/unlock";
      yexte:dependencies "Applicable only if resourceReservationForPAState is set to ACTIVATED.";
      type erienmnrmlrat:ddt-Lrat_AdmissionControl_nrOfRbReservationsPerPaConn;
      default 4;
    }
    leaf nrOfPaConnReservationsPerCell {
      description "Number of privileged access connections to be reserved per cell.";
      yexte:takes-effect "Cell lock/unlock";
      yexte:dependencies "Applicable only if resourceReservationForPAState is set to ACTIVATED.";
      type erienmnrmlrat:ddt-Lrat_AdmissionControl_nrOfPaConnReservationsPerCell;
      default 1;
    }
    leaf zzzTemp19 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp19;
      default 1000;
    }
    leaf zzzTemp17 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp17;
      default 1000;
    }
    leaf zzzTemp18 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp18;
      default 1000;
    }
    leaf zzzTemp15 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp15;
      default 1000;
    }
    leaf zzzTemp16 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp16;
      default 1000;
    }
    leaf zzzTemp13 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp13;
      default 1000;
    }
    leaf zzzTemp14 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp14;
      default 1000;
    }
    leaf zzzTemp11 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp11;
      default 1000;
    }
    leaf ulAdmOverloadThr {
      description "Sets the highest allowed uplink radio resource utilization ratio for admission of a GBR radio bearer. Applies to each resource considered by Dynamic GBR Admission Control. Resource utilization is checked against this threshold for all new, re-established or incoming handover GBR bearer requests.";
      yexte:takes-effect "Cell lock/unlock";
      yexte:dependencies ulAdmOverloadThr>=ulAdmDifferentiationThr;
      type erienmnrmlrat:ddt-Lrat_AdmissionControl_ulAdmOverloadThr;
      default 950;
    }
    leaf diffAdmCtrlFilteringEnabled {
      description "Enables filtering profiles for additional level of Differentiated Admission Control on eNodeB level.\nWhen enabled, parameters in MO DiffAdmCtrlFilteringProfile take effect.";
      yexte:disturbances "Changing this attribute can cause loss of traffic.";
      type boolean;
      default false;
    }
    leaf zzzTemp12 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp12;
      default 1000;
    }
    leaf dlAdmDifferentiationThr {
      description "If both Dynamic GBR Admission Control and Differentiated Admission Control are licensed and activated:\nSets the highest allowed downlink radio resource utilization ratio for the GBR bearers with lower ARP priority in radio bearer admission. Applies to each resource considered by Dynamic GBR Admission Control.\nIf Dynamic GBR Admission Control is licensed and activated but Differentiated Admission Control is not licensed or not activated:\nSets the highest allowed downlink radio resource utilization ratio for the GBR bearers in radio bearer admission. Applies to each resource considered by Dynamic GBR Admission Control.";
      yexte:takes-effect "Cell lock/unlock";
      yexte:dependencies dlAdmDifferentiationThr<=dlAdmOverloadThr;
      type erienmnrmlrat:ddt-Lrat_AdmissionControl_dlAdmDifferentiationThr;
      default 500;
    }
    leaf ulTransNwBandwidth {
      description "Uplink transport network bandwidth for LTE. Not used for Baseband.";
      yexte:takes-effect "Cell lock/unlock";
      yexte:dependencies "Only takes effect in DU radio node.";
      type erienmnrmlrat:ddt-Lrat_AdmissionControl_ulTransNwBandwidth;
      default 1000;
    }
    leaf zzzTemp10 {
      description "Temporary attributes are intended for temporary solutions, and their usage may vary depending on the installed software. It is strongly recommended to only set the attributes that correspond to a desired functionality and leave all other temporary attributes set to default value. Information in the descriptions about what attributes are in use may be overridden by the information in CPI Info documents. Note that a later release may use another attribute to control the functionality previously provided by a temporary attribute, or may remove the functionality altogether. In these cases, the change is documented in the NIR.\nUnit: 0.001";
      yexte:takes-effect "Cell lock/unlock";
      type erienmnrmlrat:ddt-Lrat_AdmissionControl_zzzTemp10;
      default 1000;
    }
    leaf dlAdmOverloadThr {
      description "Sets the highest allowed downlink radio resource utilization ratio for admission of a GBR radio bearer. Applies to each resource considered by Dynamic GBR Admission Control. Resource utilization is checked against this threshold for all new, re-established or incoming handover GBR bearer requests.";
      yexte:takes-effect "Cell lock/unlock";
      yexte:dependencies dlAdmOverloadThr>=dlAdmDifferentiationThr;
      type erienmnrmlrat:ddt-Lrat_AdmissionControl_dlAdmOverloadThr;
      default 950;
    }
    leaf nrOfPrevPreempPaRbReservation {
      description "Number of PA Radio Bearers that can be allocated in the preventive preemption pool.";
      yexte:takes-effect "Next cell unlock";
      yexte:dependencies "Applicable only if resourceReservationForPAState is ACTIVATED.";
      type erienmnrmlrat:ddt-Lrat_AdmissionControl_nrOfPrevPreempPaRbReservation;
      default 0;
    }
    leaf dlTransNwBandwidth {
      description "Downlink transport network bandwidth for LTE. Not used for Baseband.";
      yexte:takes-effect "Cell lock/unlock";
      yexte:dependencies "Only takes effect in DU radio node.";
      type erienmnrmlrat:ddt-Lrat_AdmissionControl_dlTransNwBandwidth;
      default 1000;
    }
    leaf lbAtoThresholdLevel2 {
      description "When the usage for a monitored system resource has exceeded this threshold then Admission-Triggered Offload (ATO) Level 2 is triggered.";
      yexte:disturbances "Changing this attribute can affect traffic.";
      yexte:dependencies "lbAtoThresholdLevel1=<lbAtoThresholdLevel2<min(ulAdmDifferentiationThr, dlAdmDifferentiationThr)";
      type erienmnrmlrat:ddt-Lrat_AdmissionControl_lbAtoThresholdLevel2;
      default 45;
    }
    leaf lbAtoThresholdLevel1 {
      description "When the usage for a monitored system resource has exceeded this threshold then Admission-Triggered Offload (ATO) Level 1 is triggered.";
      yexte:disturbances "Changing this attribute can affect traffic.";
      yexte:dependencies "lbAtoThresholdLevel1=<lbAtoThresholdLevel2<min(ulAdmDifferentiationThr, dlAdmDifferentiationThr)";
      type erienmnrmlrat:ddt-Lrat_AdmissionControl_lbAtoThresholdLevel1;
      default 30;
    }
  } // end 'grouping moc-AdmissionControl'
  grouping moc-EUtranCellRelation-keys {
    description "Key(s) for MOC EUtranCellRelation";
    leaf id {
      erienmyext:no-notification;
      description "The value component of the Relative Distinguished Name (RDN).\n";
      mandatory true;
      yexte:ecim-name eUtranCellRelationId;
      type string;
    }
  } // end 'grouping moc-EUtranCellRelation-keys'
  grouping moc-EUtranCellRelation {
    description "This managed object represents the handover relationship between two neighboring EUTRAN cells.\n";
    leaf includeInSystemInformation {
      description "Indicates if the referred cell is included in System Information.\nWhen the attribute is set to false, the cell is not included in either freqNeighList or blackCellList in SIB4 or SIB5.";
      type boolean;
      default true;
    }
    leaf sleepModeCovCellCandidate {
      description "Sleep Mode Coverage Cell candidate status.\nIndicates if related cell can be used as coverage cell for Cell Sleep Mode.";
      type erienmnrmlrat:enum-CovCellCandidate;
      default AUTO;
    }
    leaf isHoAllowed {
      description "Specifies if handover between the cells in this relation is allowed.\n";
      yexte:disturbances "Changing this attribute to false stops outgoing HO.";
      type boolean;
      default true;
    }
    leaf amoState {
      config false;
      description "Describes AMO function enabling state. RBS system sets the value.";
      yexte:dependencies "Depends on the operator configuration of AmoFunction::amoAllowedInterVendor, EUtranFreqRelation::amoAllowed, EUtranCellRelation::amoAllowed and the type of cell relation.";
      notife:notifiable-state-data true;
      type erienmnrmlrat:enum-AmoStateVals;
    }
    leaf sleepModeCoverageCell {
      config false;
      description "Indicates if related cell is a coverage cell for Cell Sleep Mode support.";
      notife:notifiable-state-data true;
      type boolean;
    }
    leaf covCellRrcConnWakeUpThreshold {
      erienmyext:no-notification;
      config false;
      description "Minimum number of RRC connections needed to wake-up the capacity cell. Sent by the capacity cell.";
      type erienmnrmlrat:ddt-Lrat_EUtranCellRelation_covCellRrcConnWakeUpThreshold;
    }
    leaf neighborCellRef {
      yexte:restricted;
      description "Reference to an instance of EUtranCellFDD, ExternalEUtranCellFDD, EUtranCellTDD or ExternalEUtranCellTDD managed object.\n";
      mandatory true;
      erienmyext:enm-type MOREF;
      type string;
    }
    leaf lbCovIndicated {
      description "Determines if the cell relation has high hitRate towards the source cell.\nThe attribute is automatically updated when the feature Overlaid Cell Detection is operable.";
      type boolean;
      default false;
    }
    leaf ieNBUlCompCoopCellAllowed {
      description "Whether external cell is allowed to be used as cooperating cell candidates for inter-eNodeB UL CoMP.";
      yexte:takes-effect "Next tunnel setup";
      type boolean;
      default true;
    }
    leaf eranExternalUlCompGroupAvail {
      config false;
      description "Whether external cell belongs to Elastic RAN external UL Comp Group for each serving cell.";
      yexte:dependencies "Depends on feature license and success of Elastic RAN UL CoMP tunnels in EranInterMeLink, which is decided by the values of TermPointToENB::eranUlCompSwCompatibility and ExternalEUtranCellFDD::remoteCellStateEranUlComp (or ExternalEUtranCellTDD::remoteCellStateIEranUlComp).\nAlso depends on remote cell configuration, following conditions must be compatible with serving cell.\n- Same Frame Structure and Duplex mode\n- Same DL&UL EARFCN and UL Bandwidth for FDD\n- Same DL EARFCN, Bandwidth, Subframe Assignment for TDD";
      notife:notifiable-state-data true;
      type erienmnrmlrat:enum-EranExternalUlCompGroupAvail;
    }
    leaf isRemoveAllowed {
      description "Indicates if the Automated Neighbor Relations (ANR) function is allowed to remove this object. It does not restrict operator removal of the object. Objects created by ANR have this parameter set to true initially.";
      type boolean;
      default false;
    }
    leaf esCellCaConfigurationAvail {
      erienmyext:no-notification;
      config false;
      description "If indicated cell is currently able to serve as ESCell.\n- The ExternalEUtranCellFDD::remoteCellState (or ExternalEUtranCellTDD::remoteCellState) must be operState ENABLED.\n- Inter-eNodeB CA license must be active and baseband-to-baseband GTPU tunnel connection between ESCell and this eNodeB must be enabled. Or\n- Elastic RAN license must be active and baseband-to-baseband connections must be enabled.\nIf not, no UEs are configured with this candidate. NOTE: UEs already configured with this cell can retain the configuration.\nIf SCell is not external, this attribute is NOT_APPLICABLE.";
      yexte:dependencies "Depends on feature license and success of tunnels in TermPointToLbm (for the IeNB-CA feature only), TermPointToENB::interEnbSwCompatibilityState and on ExternalEUtranCellFDD::remoteCellState (or ExternalEUtranCellTDD::remoteCellState).";
      type erienmnrmlrat:enum-EScellState;
    }
    leaf qOffsetCellEUtran {
      description "Offset value applied to a specific cell in idle mode mobility state.\n";
      type erienmnrmlrat:ddt-Lrat_EUtranCellRelation_qOffsetCellEUtran;
      default 0;
    }
    container mobilityStatus {
      description "Mobility status information for EUTRAN cell relation. When struct member mobilityStatus.available is set to false, no HO is performed on EUTRAN cell relation. Reason why HO is not allowed on EUTRAN cell relation is shown on mobilityStatus.reason.";
      erienmyext:enm-type STRUCT;
      uses erienmnrmlrat:struct-MobilityStatusRO;
    } // end 'container mobilityStatus'
    leaf isHoAllowedBr {
      description "Specifies if CAT-M Connected Mode Mobility between the cells in this relation is allowed.";
      yexte:disturbances "Changing this attribute to false stops outgoing HO for CAT-M UE.";
      type boolean;
      default true;
    }
    leaf crsAssistanceInfoPriority {
      description "Priority of neighbor cell whose CRS Assistance Information is sent to UE. For values between 1 and 100, the smaller the value, the higher the neighbor cell is prioritized for selection. Value 0 means the CRS Assistance Information of this neighbor cell is not sent.\nNote: This attribute is valid only for FDD cells.";
      yexte:takes-effect "New connection";
      type erienmnrmlrat:ddt-Lrat_EUtranCellRelation_crsAssistanceInfoPriority;
      default 0;
    }
    leaf amoAllowed {
      description "Whether or not AMO function is allowed. Used to turn off AMO function on cell relation level.";
      type boolean;
      default true;
    }
    leaf timeOfCreation {
      erienmyext:no-notification;
      config false;
      description "Indicates the time and date when the MO was created.\nFormat: YYYY-MM-DD HH:MM:SS";
      type erienmnrmlrat:ddt-Lrat_EUtranCellRelation_timeOfCreation;
    }
    leaf sleepModeCapacityCell {
      config false;
      description "Indicates if related cell is a dependent capacity cell for Cell Sleep Mode support.";
      notife:notifiable-state-data true;
      type boolean;
    }
    leaf hoSuccLevel {
      config false;
      description "Handover statistics status information. Each value corresponds to the status of the handover statistics.";
      yexte:takes-effect "Ongoing connection";
      notife:notifiable-state-data true;
      type erienmnrmlrat:enum-HoStatisticsStatus;
    }
    leaf sCellPriority {
      description "Used for selecting an SCell within a frequency carrier. The SCell with highest priority is selected during initial blind SCell selection. 0 means lowest priority. -1 means the cell is excluded from blind SCell selection.";
      yexte:takes-effect "New connection";
      yexte:dependencies "Only applicable when CarrierAggregationFunction::dynamicSCellSelectionMethod == PRIORITIZED.";
      type erienmnrmlrat:ddt-Lrat_EUtranCellRelation_sCellPriority;
      default 7;
    }
    leaf loadBalancing {
      description "This attribute indicates whether Inter-Frequency Load Balancing is ALLOWED or NOT_ALLOWED or if Inter-Frequency Offload shall be applied from the current cell to the cell indicated by the cell relation.";
      type erienmnrmlrat:enum-LoadBalancingVals;
      default NOT_ALLOWED;
    }
    leaf timeOfLastModification {
      config false;
      description "Indicates the time and date when the MO was last modified.\nFormat: YYYY-MM-DD HH:MM:SS";
      notife:notifiable-state-data true;
      type erienmnrmlrat:ddt-Lrat_EUtranCellRelation_timeOfLastModification;
    }
    leaf covCellDlPrbWakeUpThreshold {
      erienmyext:no-notification;
      config false;
      description "DL PRB usage percentage threshold. At least one of the coverage cells must exceed this threshold to wake-up the capacity cell.";
      type erienmnrmlrat:ddt-Lrat_EUtranCellRelation_covCellDlPrbWakeUpThreshold;
    }
    leaf externalUlCompGroupAvail {
      erienmyext:no-notification;
      config false;
      description "Whether external cell belongs to external UL Comp Group for each serving cell.";
      yexte:dependencies "Depends on feature license and success of UL CoMP tunnels in TermPointToLbm, which is decided by the values of TermPointToENB::interEnbUlCompSwCompatibility and ExternalEUtranCellFDD::remoteCellStateInterEnbUlComp (or ExternalEUtranCellTDD::remoteCellStateInterEnbUlComp) and EUtranCellRelation::ieNBUlCompCoopCellAllowed.\nAlso depends on remote cell configuration, following conditions must be compatible with serving cell.\n- Same Frame Structure and Duplex mode\n- Same DL&UL EARFCN and UL Bandwidth for FDD\n- Same DL EARFCN, Bandwidth, Subframe Assignment for TDD";
      type erienmnrmlrat:enum-ExternalUlCompGroupAvail;
    }
    leaf cellIndividualOffsetEUtranQci1 {
      description "Cell Individual Offset for QCI1. Used when UE with QCI1 bearer is in connected mode. This attribute can be modified by SON functions.";
      yexte:takes-effect "New connection";
      type erienmnrmlrat:ddt-Lrat_EUtranCellRelation_cellIndividualOffsetEUtranQci1;
      default 0;
    }
    leaf sCellCandidate {
      description "SCell candidate status.\nThe value indicates whether the cell indicated by parameter cellrelation can be used as SCell for UEs using this cell as their PCell. The SCell can be either local to the eNodeB, or on a remote eNodeB.";
      yexte:takes-effect "Changed value will take effect in relation to the next SCell configuration during the ongoing connection.";
      type erienmnrmlrat:enum-SCellCandidate;
      default AUTO;
    }
    leaf createdBy {
      config false;
      description "Indicates whether the MO has been created by the Automated Neighbor Relations (ANR) function or operator or X2";
      notife:notifiable-state-data true;
      type erienmnrmlrat:enum-CreatedByEutran;
    }
    leaf cellIndividualOffsetEUtran {
      description "Offset value for the neighbor cell. Used when UE is in connected mode. This attribute can be modified by SON functions.";
      yexte:takes-effect "New connection.";
      type erienmnrmlrat:ddt-Lrat_EUtranCellRelation_cellIndividualOffsetEUtran;
      default 0;
    }
    leaf lastModification {
      config false;
      description "Indicates whether the MO was last modified by the Automated Neighbor Relations (ANR) function or operator or X2 and if the MO is to be deleted who triggered the deletion";
      notife:notifiable-state-data true;
      type erienmnrmlrat:enum-LastModificationEutran;
    }
    leaf incomingLoadBalancing {
      config false;
      description "Determines if feature Overlaid Cell Detection has qualified this cell relation as an overlaid neighbor, i.e. high-hitRate, on the corresponding frequency relation.\nThe value \"true\" means the neighbor cell is encouraged to initiate load balancing towards the source cell.\nThe value \"false\" means no specific preferences exist.";
      notife:notifiable-state-data true;
      type boolean;
    }
    leaf lbBnrAllowed {
      description "Specifies if the feature Best Neighbor Relations for Intra-LTE Load Management is allowed to automatically change the loadBalancing attribute for this EUtran cell relation.";
      type boolean;
      default true;
    }
    leaf coverageIndicatorBr {
      description "Coverage area of cell indicated by relation, compared to this cell. Coverage area is approximately the same (overlap), it fully covers this cell, or it is fully contained in this cell for CAT-M UE.";
      yexte:takes-effect "New connection";
      type erienmnrmlrat:enum-SupportedCoverage;
      default NONE;
    }
    leaf coverageIndicator {
      description "Indicates whether the coverage area of the cell indicated by the relation has approximately the same coverage area (overlap) as this cell, or whether it fully covers this cell, or if it is fully contained in this cell.";
      yexte:disturbances "Changes may affect traffic";
      type erienmnrmlrat:enum-SupportedCoverage;
      default NONE;
    }
    leaf covCellWakeupMonitorDurTimer {
      erienmyext:no-notification;
      config false;
      description "Minimum duration for coverage cell to satisfy configured load thresholds before the capacity cell can wake-up. Used in feature Cell Sleep Mode.";
      type erienmnrmlrat:ddt-Lrat_EUtranCellRelation_covCellWakeupMonitorDurTimer;
    }
    leaf isShuttingdownSCellAllowed {
      status deprecated {
        yexte:status-information "Since 17.Q2. Has no functional behavior. Planned to be removed.";
      }
      description "Indicates whether a shutting down cell can be chosen as SCell or not.";
      type boolean;
      default true;
    }
    leaf eranUlCompCoopCellAllowed {
      description "Whether external cell is allowed to be used as cooperating cell candidates for Elastic RAN UL CoMP.";
      yexte:takes-effect "Next tunnel setup";
      type boolean;
      default true;
    }
  } // end 'grouping moc-EUtranCellRelation'
  grouping moc-EUtranCellTDD-keys {
    description "Key(s) for MOC EUtranCellTDD";
    leaf id {
      erienmyext:no-notification;
      description "The value component of the Relative Distinguished Name (RDN).\n";
      mandatory true;
      yexte:ecim-name eUtranCellTDDId;
      type string;
    }
  } // end 'grouping moc-EUtranCellTDD-keys'
  grouping moc-EUtranCellTDD {
    description "This MO represents a TDD cell and contains parameters needed by the cell. It also contains parameters for the mandatory common channels. The cell need to have the same duplex mode (FDD or TDD) as the already existing intra-RBS cells, if any.\n";
    leaf ns05LowBandSchedMode {
      description "Controls if the low band can be allocated to NS_05 UEs. When ns05LowBandSchedMode is configured to 'ALWAYS_PROHIBIT', the low band cannot be allocated to the NS_05 UEs. When ns05LowBandSchedMode is configured to 'ALWAYS_AVAILABLE', the low band can always be allocated to the NS_05 UEs. When ns05LowBandSchedMode is configured to 'ADAPTIVE_AVAILABLE_BY_REPEATER_DETECTION', the low band can only be allocated to the NS_05 UEs which are detected as not in repeater zone.";
      yexte:dependencies "Only takes effect if:\n- license for NS 05 Additional Maximum Power Reduction Support is present and the feature is active, and\n- attribute networkSignallingValue in MOC EUtranCellFDD/TDD is NS_05.";
      type erienmnrmlrat:enum-Ns05LBSchedMode;
      default ALWAYS_PROHIBIT;
    }
    leaf ulInterferenceManagementActive {
      description "Specifies if uplink interference management is enabled or disabled.";
      yexte:takes-effect "Object unlocked";
      type boolean;
      default true;
    }
    leaf iuaMaxResourcePerCell {
      status deprecated {
        yexte:status-information "Since 18.Q3. Replaced by InstantUplinkAccess::iuaCellResourceLimit. Planned to be removed.";
      }
      description "Maximum percentage of UL PRBs and SEs that are used by IUA at cell level. The actual number of resources per cell depends on iuaMaxResourcePerBbm.";
      type erienmnrmlrat:ddt-Lrat_EUtranCellTDD_iuaMaxResourcePerCell;
      default 20;
    }
    leaf physicalLayerCellId {
      config false;
      description "Physical-layer cell ID.";
      yexte:dependencies "Equal to 3 x physicalLayerCellIdGroup + physicalLayerSubCellId.";
      notife:notifiable-state-data true;
      type erienmnrmlrat:ddt-Lrat_EUtranCellTDD_physicalLayerCellId;
    }
    leaf hpueCaSwitchThres {
      description "SINR threshold for triggering a switch to high power UE.";
      type erienmnrmlrat:ddt-Lrat_EUtranCellTDD_hpueCaSwitchThres;
      default -150;
    }
    leaf nonCaF3SelectionThreshold {
      status deprecated {
        yexte:status-information "Since 17.Q1. Planned to be removed.";
      }
      description "Controls number of non-carrier aggregation TDD UEs configured with PUCCH format3 as DL HARQ ACK/NACK feedback mode.\nNote: PUCCH Format3 resources can be shared with CA users. Then attribute value depends on maximum number of carrier aggregation users that are configured with PUCCH Format3 resources.";
      yexte:takes-effect "New connection";
      type erienmnrmlrat:ddt-Lrat_EUtranCellTDD_nonCaF3SelectionThreshold;
      default 100;
    }
    leaf ulHarqVolteBlerTarget {
      description "The UL BLER target to be used for VoLTE UEs. This BLER target will be used for all UL transmissions for UEs that have a QCI1 bearer configured. If a UE does not have QCI1 bearer configured the normal UL BLER target will be used.";
      yexte:takes-effect "Object unlocked";
      type erienmnrmlrat:ddt-Lrat_EUtranCellTDD_ulHarqVolteBlerTarget;
      default 5;
    }
    leaf extGUtranCellRef {
      description "Reference to an instance of ExternalGUtranCell. If set, indicated GUTRAN cell must have coverage over this cell.";
      yexte:takes-effect "New connection";
      erienmyext:enm-type MOREF;
      type string;
    }
    leaf pdcchOuterLoopInitialAdj {
      description "The initial value for PDCCH outer loop adjustment for UEs that do not have any secondary cell configured and do not have any bearer mapped to a QCI with serviceType of VoIP. In TDD, this parameter applies only to UEs which are configured with HARQ-ACK bundling.";
      yexte:takes-effect "Object unlocked";
      type erienmnrmlrat:ddt-Lrat_EUtranCellTDD_pdcchOuterLoopInitialAdj;
      default -70;
    }
    leaf dummyCdmaBandClass {
      description "Dummy CDMA frequency band in the MobilityParametersCDMA2000 information element that can be used to force registration each time the UE moves across LTE and CDMA 1xRTT networks. This can be achieved by setting both this parameter to a dummy band class that is not used in the native CDMA 1xRTT network and by setting the powerUpReg flag to TRUE in SIB-8. The default value of 99 or UNDEFINED_VALUE means the value configured in Cdma2000FreqBand::cdmaBandClass is sent in the MobilityParametersCDMA2000 information element which is the same value as the one  sent in SIB-8.";
      yexte:takes-effect "New connection";
      type erienmnrmlrat:enum-HrpdBandClass;
      default UNDEFINED_VALUE;
    }
    leaf cellBarred {
      description "Indicates if the cell is barred and should not be accessible to random UEs.";
      yexte:disturbances "Changing this attribute to BARRED blocks all traffic in the cell.";
      type erienmnrmlrat:enum-CellBarred;
      default NOT_BARRED;
    }
    leaf-list additionalSpectrumEmissionValues {
      min-elements 0;
      max-elements 8;
      config false;
      description "A list of network signaling values, where each value corresponds to the frequency band on the same position in additionalFreqBandList. Enables additional spectrum emission requirements according to 3GPP TS 36.101, table 6.2.4-1 when the feature Multiple Frequency Band Indicators is enabled in the cell. The content of this list is based on spectrumEmissionReqMapping. This list will be broadcasted in SIB2 as multiBandInfoList.";
      notife:notifiable-state-data true;
      type erienmnrmlrat:enum-NetworkSignallingValue;
    }
    leaf cceDynUeAdmCtrlOverloadThr {
      description "Highest allowed control channel element radio resource utilization ratio for admission of a non-privileged UE. Resource utilization is checked against this threshold for all new, re-established, or incoming handover RRC connections.";
      yexte:disturbances "Changing this attribute can affect the following:\n- the number of RRC-connected users\n- cell throughput and the number of rejected non-privileged RRC connection requests\n- rejected non-privileged RRC connection re-establishment requests and rejected\n  non-privileged incoming handover requests.";
      yexte:dependencies "cceDynUeAdmCtrlOverloadThr >= cceDynUeAdmCtrlRetDiffThr";
      type erienmnrmlrat:ddt-Lrat_EUtranCellTDD_cceDynUeAdmCtrlOverloadThr;
      default 600;
    }
    leaf dlDynUeAdmCtrlRetDiffThr {
      description "Highest allowed DL radio resource utilization ratio for admission of a new non-privileged UE. Applies to each DL resource considered by Dynamic UE Admission Control. Resource utilization is checked against this threshold for all new RRC connections.";
      yexte:disturbances "Changing this attribute can affect the following:\n- the number of RRC-connected users\n- cell throughput and the number of rejected non-privileged RRC connection requests.";
      yexte:dependencies "dlDynUeAdmCtrlRetDiffThr =< dlDynUeAdmCtrlOverloadThr";
      type erienmnrmlrat:ddt-Lrat_EUtranCellTDD_dlDynUeAdmCtrlRetDiffThr;
      default 500;
    }
    leaf preambleInitialReceivedTargetPower {
      description "Initial preamble power value in dBm, according to 3GPP specification 36.331 and 36.321.";
      yexte:takes-effect "Cell lock/unlock";
      type erienmnrmlrat:ddt-Lrat_EUtranCellTDD_preambleInitialReceivedTargetPower;
      default -110;
    }
    leaf enableUeAssistedSigReduction {
      description "Enable or disable the UE-Assisted Signaling Reduction feature.";
      yexte:takes-effect "Object unlocked";
      type boolean;
      default true;
    }
    leaf dynUeAdmCtrlEnabled {
      description "Enable Dynamic UE Admission Control at cell level.";
      yexte:disturbances "Changing this attribute can affect the following:\n- the number of RRC-connected users\n- cell throughput and the number of rejected non-privileged RRC connection requests\n- rejected non-privileged RRC connection re-establishment requests and rejected\n  non-privileged incoming handover requests.";
      yexte:takes-effect "Cell lock/unlock";
      yexte:dependencies "Only relevant if the license for Dynamic UE Admission Control is present and the feature is active.";
      type boolean;
      default false;
    }
    leaf cellSubscriptionCapacity {
      description "Normalized subscription capacity of the cell. The value represents the total capacity of the cell used for traffic load balancing purposes.";
      yexte:disturbances "Low values reduce cell capacity.";
      type erienmnrmlrat:ddt-Lrat_EUtranCellTDD_cellSubscriptionCapacity;
      default 1000;
    }
    leaf plmnPabBarringPriorityLevel {
      config false;
      description "Current PLMN priority level based on PLMN Progressive Access Barring algorithm.";
      notife:notifiable-state-data true;
      type erienmnrmlrat:enum-AcBarringPlmnPriorityLevel;
    }
    leaf maxSoftLockBackoffTime {
      description "Indicates a maximum handover backoff time. The value is applied to inhibit further handover attempts to a EUTRAN target cell that rejects incoming handover for soft-lock of cell.";
      type erienmnrmlrat:ddt-Lrat_EUtranCellTDD_maxSoftLockBackoffTime;
      default 90;
    }
    leaf acBarringPlmnPabEnabled {
      description "Enables Prioritized PLMN Progressive Access Barring in cell.";
      yexte:disturbances "Changing this attribute can cause loss of traffic.";
      type boolean;
      default false;
    }
    leaf outOfCoverageThreshold {
      description "Threshold for when UE is considered to be Out Of Coverage (OOC). If the number of OOC trigger events is greater than or equal to the threshold, the UE is in the OOC state; if the number of OOC trigger events is less than the threshold, the UE is not in the OOC state.";
      yexte:takes-effect "Cell lock/unlock";
      type erienmnrmlrat:ddt-Lrat_EUtranCellTDD_outOfCoverageThreshold;
      default 20;
    }
    leaf freqBand {
      config false;
      description "The primary frequency band the cell belongs to according to its defined EARFCN.";
      notife:notifiable-state-data true;
      type erienmnrmlrat:ddt-Lrat_EUtranCellTDD_freqBand;
    }
    leaf plmn1AbConfProfileRef {
      description "Reference to an instance of PlmnAbConfProfile. Points to the PLMN Access Barring configuration profile.";
      yexte:disturbances "Changing this attribute can cause loss of traffic.";
      yexte:dependencies "References plmn1AbConfProfileRef, plmn2AbConfProfileRef and plmn3AbConfProfileRef must point to unique PlmnAbConfProfile MO instance.";
      erienmyext:enm-type MOREF;
      type string;
    }
    leaf ailgAutoRestartEnabled {
      description "If set to true, AILG is automatically restarted when:\n- cell disabled followed by cell enabled, for example at node start or restart.";
      yexte:takes-effect "Object disabled/enabled";
      type boolean;
      default false;
    }
    leaf cellCapMaxCellSubCap {
      description "Maximum value for the estimated cell capacity.";
      yexte:dependencies "cellCapMinCellSubCap < cellCapMaxCellSubCap";
      type erienmnrmlrat:ddt-Lrat_EUtranCellTDD_cellCapMaxCellSubCap;
      default 1500;
    }
    leaf loadBasedCaEnabled {
      description "Enables Load-Based CA SCell Handling.";
      yexte:takes-effect "Next cell unlock";
      yexte:dependencies "Only relevant if license for Load-Based CA SCell Handling is present and feature is active.";
      type boolean;
      default false;
    }
    container eutranCellCoverage {
      description "Models the cell coverage area used for UE positioning. The cell coverage area is defined by the cell bearing, cell opening angle and cell radius.\n\nThis attribute has no operational impact.";
      erienmyext:enm-type STRUCT;
      uses erienmnrmlrat:struct-EutranCellArea;
    } // end 'container eutranCellCoverage'
    leaf measGapShareSchemeCeABr {
      description "Measurement gap sharing scheme for CAT-M UE. Values based on 3GPP 36.133 table 8.13.2.1.1.1-2.";
      yexte:takes-effect "New connection";
      type erienmnrmlrat:enum-MeasGapShareScheme;
      default SCHEME_ZERO;
    }
    leaf servOrPrioIFHoSetupBearer {
      description "Determines whether a bearer that fulfills the criteria for the feature Service- or Priority-Triggered Inter-Frequency Handover is set up, or rejected in UE .";
      type boolean;
      default true;
    }
    leaf filterUeDlThpTimeThr {
      description "Defines DRB transport time threshold for counter pmUeThpDlMbbFilteredDistr. UE session with DRB transport time less than this threshold is filtered out.";
      yexte:takes-effect "Next ROP";
      type erienmnrmlrat:ddt-Lrat_EUtranCellTDD_filterUeDlThpTimeThr;
      default 50;
    }
    leaf elcEnabled {
      description "Enables Ericsson Lean Carrier functionality in the cell.";
      yexte:takes-effect "Object unlocked";
      yexte:dependencies "Only relevant if the licence for ELC is present and the feature is active.";
      type boolean;
      default false;
    }
    leaf rtpTimeout {
      description "Enables operator configuration of the RTP timeout value at the eNodeB at a cell level that corresponds to the RTP timeout value get set at the IMS layer.";
      type erienmnrmlrat:ddt-Lrat_EUtranCellTDD_rtpTimeout;
      default 10;
    }
    leaf uncertSemiMajor {
      description "Semi-major axis of uncertainty. The uncertainty (r) is derived from the uncertainty code (k) by:\nr = 10 * ((1.1^k) - 1).";
      type erienmnrmlrat:ddt-Lrat_EUtranCellTDD_uncertSemiMajor;
      default 0;
    }
    leaf uncertSemiMinor {
      description "Semi-minor axis of uncertainty. The uncertainty (r) is derived from the uncertainty code (k) by:\nr = 10 * ((1.1^k) - 1).";
      type erienmnrmlrat:ddt-Lrat_EUtranCellTDD_uncertSemiMinor;
      default 0;
    }
    leaf ulImprovedUeSchedLastEnabled {
      description "Whether or not UL scheduler is enabled to force allocation of PRBs to Data-Aware, UL-Scheduling UEs last.";
      type boolean;
      default true;
    }
    leaf prsPeriod {
      description "The period of Positioning Reference Signal (PRS) occasions. Valid periods include 160 ms, 320 ms, 640 ms and 1280 ms.\nprsPeriod is used to calculate the prsConfigIndex to avoid PRS sub-frame collisions with SIB1 sub-frames.";
      yexte:takes-effect "Object unlocked";
      type erienmnrmlrat:enum-PrsPerVals;
      default PP160;
    }
    list commonSFAllocList {
      min-elements 0;
      max-elements 8;
      key auto-generated-struct-key;
      leaf auto-generated-struct-key {
        type uint16;
        description "This leaf has been injected to allow for struct instances in a sequence to be ordered.";
        mandatory true;
      }
      description "Shows the subframes that are reserved for MBSFN in DL.";
      erienmyext:enm-type STRUCT;
      uses erienmnrmlrat:struct-SubFrameConfigRO;
    } // end 'list commonSFAllocList'
    leaf lbabBarringPriorityLevel {
      config false;
      description "Current barring priority level based on Progressive Access Barring or PLMN-Specific Access Barring algorithms.";
      yexte:dependencies "Only takes effect when feature Progressive Access Barring is activated.";
      notife:notifiable-state-data true;
      type erienmnrmlrat:enum-AcBarringPriorityLevel;
    }
    leaf operationalState {
      config false;
      description "The operational state.  This attribute is set by the application in the RBS.\n";
      notife:notifiable-state-data true;
      type erienmnrmlrat:enum-OperState;
    }
    leaf servOrPrioTriggeredErabAction {
      description "Specifies the action performed when a S1AP:E-RAB SETUP REQUEST arrives and both the feature Service or Priority-Triggered Inter-Frequency Handover is active and the conditions for the bearer request are fulfilled.";
      yexte:takes-effect "New connection";
      yexte:dependencies "This attribute only takes effect when attribute servOrPrioTriggeredIFHo has value 'QCI'.";
      type erienmnrmlrat:enum-ServOrPrioTriggeredErabActionType;
      default REJECT;
    }
    leaf pdcchOuterLoopUpStep {
      description "PDCCH outer loop up step size for UEs that do not have any secondary cell configured and do not have any bearer mapped to a QCI with serviceType of VoIP. In TDD, this parameter applies only to UEs which are configured with HARQ-ACK bundling.";
      yexte:takes-effect "Object unlocked";
      type erienmnrmlrat:ddt-Lrat_EUtranCellTDD_pdcchOuterLoopUpStep;
      default 8;
    }
    leaf ssacBarringForMMTELVideoPresent {
      status deprecated {
        yexte:status-information "Since 17.Q3. Replaced by AcBarringPresence.acBarringForMmtelVideoPresence in EUtranCellFDD/EUtranCellTDD::acBarringPresence. Planned to be removed.";
      }
      description "Specifies presence of Information Element ssac-BarringForMMTEL-Video-r9 in SIB2.";
      yexte:disturbances "Changing this attribute can block video calls in the cell.";
      type boolean;
      default false;
    }
    leaf externalCdma20001xRttCellRef {
      erienmyext:no-notification;
      description "Reference to an ExternalCdma20001xRttCell";
      erienmyext:enm-type MOREF;
      type string;
    }
    leaf puschMaxNrOfPrbsPerUe {
      description "Maximum number of physical resource blocks allowed on PUSCH for each UE.";
      yexte:takes-effect "Object unlocked";
      yexte:dependencies "This parameter only takes effect if the feature PUCCH Overdimensioning is activated.";
      type erienmnrmlrat:ddt-Lrat_EUtranCellTDD_puschMaxNrOfPrbsPerUe;
      default 100;
    }
    leaf latitude {
      description "The degree of latitude of the transmitter antenna position.\nIn case of Combined Cell (multi-sector cell):\n   For indoor system, antenna of any sector.\n   For outdoor system,antenna of macro sector.";
      type erienmnrmlrat:ddt-Lrat_EUtranCellTDD_latitude;
      default 0;
    }
    container ssacBarringForMMTELVoice {
      description "Service specific access class barring parameters for MMTEL voice originating calls.\nInformation broadcasted in SIB2.";
      erienmyext:enm-type STRUCT;
      uses erienmnrmlrat:struct-AcBarringConfig;
    } // end 'container ssacBarringForMMTELVoice'
    leaf noOfPucchFormat1PrbPairsPerFrame {
      erienmyext:no-notification;
      config false;
      description "PRB usage for PUCCH Format1. Based on PUCCH SR, CFI and Carrier Aggregation user configuration.";
      type erienmnrmlrat:ddt-Lrat_EUtranCellTDD_noOfPucchFormat1PrbPairsPerFrame;
    }
    leaf sCellHandlingAtVolteCall {
      description "SCell handling during VoLTE calls.";
      yexte:takes-effect "New connection";
      type erienmnrmlrat:enum-SCellHandlingWithVolte;
      default KEEP_SCELLS;
    }
    leaf eDrxAllowed {
      description "Set to true when idle mode eDRX shall be allowed in the cell.";
      yexte:takes-effect "Next cell unlock";
      type boolean;
      default false;
    }
    leaf covTriggerdBlindHoAllowed {
      description "Says whether a blind Handover from this cell can be initiated when a UE reports bad coverage, or not. Note that even if the value is True, the eNB will only initiate a blind handover if it finds a suitable cell.";
      type boolean;
      default true;
    }
    leaf sCellHpueEnabled {
      status deprecated {
        yexte:status-information "Since 17.Q3. Has no functional behavior. Planned to be removed.";
      }
      description "Whether or not SCell selection for high power UE that is not capable of CA simultaneously is enabled.";
      type boolean;
      default true;
    }
    leaf prsConfigIndex {
      description "The Positioning Reference Signal (PRS) index value for the cell defines the periodicity of the PRS occasions and the PRS subframe offset, as defined in 3GPP TS 36.211. The value -1 (default) means that this parameter will not be used for setting the PRS period and prsSubframeOffset. Instead the parameter prsPeriod shall be used to directly set the PRS period while prsSubframeOffset will be set by the system to guarantee non collision with SIB1.";
      yexte:takes-effect "Object unlocked";
      type erienmnrmlrat:ddt-Lrat_EUtranCellTDD_prsConfigIndex;
      default -1;
    }
    container acBarringForMoData {
      description "Access class barring parameters for mobile originating calls.\nInformation broadcasted in SIB2.";
      erienmyext:enm-type STRUCT;
      uses erienmnrmlrat:struct-AcBarringConfig;
    } // end 'container acBarringForMoData'
    leaf-list additionalPlmnReservedList {
      min-elements 0;
      max-elements 5;
      description "For the list of PLMN IDs in the cell, indicates if they are reserved for operator use. The list must have the same number of entries as additonalPlmnList. The PLMN ID appearing in additionalPlmnList[x] is reserved when additionalPlmnListReserved[x] is set to true.";
      yexte:disturbances "Changing this attribute can cause loss of traffic.";
      yexte:dependencies "The length of this list must be the same as the list in addtionalPlmnList.";
      type boolean;
      default false;
      default false;
      default false;
      default false;
      default false;
    }
    leaf eranUlCompUserSelSinrThr {
      description "SINR threshold for Elastic RAN UL CoMP user selection.";
      yexte:dependencies "Must be used together with eranUlCompUserSelSinrHys.";
      type erienmnrmlrat:ddt-Lrat_EUtranCellTDD_eranUlCompUserSelSinrThr;
      default 150;
    }
    leaf cceDynUeAdmCtrlRetDiffThr {
      description "Highest allowed control channel element radio resource utilization ratio for admission of a new non-privileged UE. Resource utilization is checked against this threshold for all new RRC connections.";
      yexte:disturbances "Changing this attribute can affect the following:\n- the number of RRC-connected users\n- cell throughput and the number of rejected non-privileged RRC connection requests.";
      yexte:dependencies "cceDynUeAdmCtrlRetDiffThr =< cceDynUeAdmCtrlOverloadThr";
      type erienmnrmlrat:ddt-Lrat_EUtranCellTDD_cceDynUeAdmCtrlRetDiffThr;
      default 500;
    }
    leaf subframeAssignment {
      description "The assignment of uplink and downlink subframes for the TDD frame structure (called UL/DL configuration in 3GPP TS 36.211). All TDD cells in the same DU or Baseband, or same frequency band, or specific frequency band combinations where one frequency band overlaps with another (e.g. Band 38 and Band 41) must have the same uplink and downlink subframe assignment.";
      mandatory true;
      yexte:disturbances "Changes may affect traffic.";
      yexte:takes-effect "Object unlocked";
      yexte:dependencies "For cellRange greater than 15 subframeAssignment must be set to 1.";
      type erienmnrmlrat:ddt-Lrat_EUtranCellTDD_subframeAssignment;
    }
    leaf otdoaCheckEnabled {
      description "Determines if the OTDOA functionality should be considered in the feature Service or Priority-Triggered Inter-Frequency Handover.";
      yexte:takes-effect "New connection";
      type boolean;
      default false;
    }
    leaf pdcchTargetBlerPCell {
      description "PDCCH target error rate for primary cells in case of carrier aggregation. This applies to UEs that have at least one secondary cell configured and do not have any bearer mapped to a QCI with serviceType of VoIP. In TDD, this parameter is not used.";
      yexte:takes-effect "Object unlocked";
      type erienmnrmlrat:ddt-Lrat_EUtranCellTDD_pdcchTargetBlerPCell;
      default 22;
    }
    leaf modificationPeriodCoeff {
      description "The modification period, expressed in number of radio frames = modificationPeriodCoeff * defaultPagingCycle. See MO Paging for information about defaultPagingCycle.";
      yexte:takes-effect "When EUtranCellFDD/TDD object is unlocked";
      yexte:dependencies "modificationPeriodCoeff * defaultPagingCycle must be equal or less than 1024 radio frames. See MO Paging for information about defaultPagingCycle.";
      type erienmnrmlrat:ddt-Lrat_EUtranCellTDD_modificationPeriodCoeff;
      default 2;
    }
    leaf physicalLayerCellIdGroup {
      description "Physical layer cell ID group.\nPhysical layer cell IDs are grouped into 168 unique physical layer cell ID groups. Each group contains 3 unique subidentities.\nUsed with physicalLayerSubCellId to calculate physical layer cell ID.";
      mandatory true;
      yexte:disturbances "Changes may affect traffic.";
      type erienmnrmlrat:ddt-Lrat_EUtranCellTDD_physicalLayerCellIdGroup;
    }
    list additionalMultipleNSPmax {
      min-elements 0;
      max-elements 8;
      key auto-generated-struct-key;
      leaf auto-generated-struct-key {
        type uint16;
        description "This leaf has been injected to allow for struct instances in a sequence to be ordered.";
        mandatory true;
      }
      description "The attribute in broadcast in SIB1 as multiBandInfoList-v10j0. A list of additionalPmax and additionalSpectrumEmission values. If E-UTRAN includes multiBandInfoList-v10j0, it includes the same number of entries, and listed in the same order, as in multiBandInfoList.";
      erienmyext:enm-type STRUCT;
      uses erienmnrmlrat:struct-MultipleNSPmaxListRO;
    } // end 'list additionalMultipleNSPmax'
    leaf ptmCellProfileRef {
      description "Reference to an instance of PtmCellProfile that contains configuration for the cell.\nIf not set, PTM is disabled on the cell.";
      yexte:disturbances "Changing this attribute can affect traffic.";
      erienmyext:enm-type MOREF;
      type string;
    }
    leaf timeOfLastModification {
      description "Indicates the time and date when the MO was last modified.\nFormat: YYYY-MM-DD HH:MM:SS";
      type erienmnrmlrat:ddt-Lrat_EUtranCellTDD_timeOfLastModification;
      default "";
    }
    leaf deallocThrPucchFormat1 {
      description "Threshold in terms of number of remaining SR resources available for the cell. Above this threshold, deallocTimerPucchFormat1 for deallocation of a PUCCH format 1 PRB pair is triggered. Occurs if  feature Dynamic PUCCH  is activated.";
      type erienmnrmlrat:ddt-Lrat_EUtranCellTDD_deallocThrPucchFormat1;
      default 100;
    }
    leaf uncertAltitude {
      description "The uncertainty altitude (h) expressed in meters is derived from the uncertainty altitude (k) by h = 45*((1.025)^k - 1).";
      type erienmnrmlrat:ddt-Lrat_EUtranCellTDD_uncertAltitude;
      default 0;
    }
    leaf ulBlerTargetEnabled {
      description "Turns feature Configurable UL BLER Target on and off.";
      type boolean;
      default false;
    }
    leaf-list reservedBy {
      min-elements 0;
      config false;
      description "Contains a list of managed object instances that reserves this managed object instance.\n";
      yexte:dependencies "The managed object cannot be deleted if it is reserved.";
      notife:notifiable-state-data true;
      erienmyext:enm-type MOREF;
      type string;
    }
    leaf tUeBlockingTimer {
      description "Length of time eNodeB rejects traffic requests from non-privileged UEs when detecting high procedure latency. Used in Procedure Latency Supervision. Privileged traffic, such as High Priority Access (HPA) and Emergency, is never rejected due to high procedure latency conditions.";
      yexte:takes-effect "Next cell unlock";
      type erienmnrmlrat:ddt-Lrat_EUtranCellTDD_tUeBlockingTimer;
      default 200;
    }
    leaf incrPrioServingFreqActive {
      status deprecated {
        yexte:status-information "Since 17.Q3. Has no functional behavior. Planned to be removed.";
      }
      description "Specifies whether or not the function to set the serving frequency as sticky carrier is active in the current cell.";
      yexte:disturbances "Changing this attribute can affect traffic.";
      type boolean;
      default false;
    }
    leaf qciTableRef {
      description "Refers to an instance of QciTable and assigns a QciTable to a cell. The QciTable defines Quality of Service Class Indicator (QCI) to use in the cell.\nRefers to the QciTable instance corresponding to Local Distinguished Name (LDN) = ManagementElement=1, ENodeBFunction=1, QciTable=default";
      yexte:takes-effect "New connection.";
      yexte:dependencies "It is assumed that the QciTable MO has been created.";
      erienmyext:enm-type MOREF;
      type string;
    }
    leaf prsMutingPattern {
      config false;
      description "Used for storing the calculated muting pattern for the cell. This parameter cannot be manually set.";
      yexte:takes-effect "Object unlocked";
      notife:notifiable-state-data true;
      type erienmnrmlrat:ddt-Lrat_EUtranCellTDD_prsMutingPattern;
    }
    leaf-list sectorCarrierRef {
      min-elements 0;
      max-elements 12;
      description "Reference to a list of instances of SectorCarrier MO.";
      yexte:disturbances "Change can affect traffic";
      yexte:takes-effect "Object disabled/enabled";
      erienmyext:enm-type MOREF;
      type string;
    }
    list mappingInfoBr {
      min-elements 0;
      max-elements 2;
      key auto-generated-struct-key;
      leaf auto-generated-struct-key {
        type uint16;
        description "This leaf has been injected to allow for struct instances in a sequence to be ordered.";
        mandatory true;
      }
      description "SI message to which each SIB is mapped.\nNote: SIB2 is always mapped to SI message 1 according to 3GPP TS 36.331.";
      status deprecated {
        yexte:status-information "Since 17.Q4. Planned to be removed.";
      }
      erienmyext:enm-type STRUCT;
      uses erienmnrmlrat:struct-MappingInfoSIBsBr;
    } // end 'list mappingInfoBr'
    leaf qRxLevMinOffset {
      description "The offset applied to the signaled Qrxlevmin. Corresponds to parameter Qrxlevminoffset in 3GPP TS 36.304. Value 1000 means it is not sent and the UE sets Qrxlevminoffset=0dB.";
      type erienmnrmlrat:ddt-Lrat_EUtranCellTDD_qRxLevMinOffset;
      default 1000;
    }
    leaf rateShapingActive {
      description "Indicates if End-user bitrate shaping functionality is activated in this cell.";
      yexte:takes-effect "Cell lock/unlock";
      yexte:dependencies "Only relevant if the license for End-user bitrate shaping is present and the feature is active.";
      type boolean;
      default false;
    }
    container loadBasedCaMsrThr {
      description "High and low MSR thresholds for Load-Based CA SCell Handling.";
      erienmyext:enm-type STRUCT;
      uses erienmnrmlrat:struct-LoadBasedCaMsrThr;
    } // end 'container loadBasedCaMsrThr'
    leaf tm7ModeSwitchingEnabled {
      description "Enables dynamic switching between TM7 and TM3.";
      yexte:dependencies "Only takes effect if radio equipment supports AAS functionality.";
      type boolean;
      default false;
    }
    list activePlmnList {
      min-elements 0;
      max-elements 6;
      key auto-generated-struct-key;
      leaf auto-generated-struct-key {
        type uint16;
        description "This leaf has been injected to allow for struct instances in a sequence to be ordered.";
        mandatory true;
      }
      description "Lists the PLMN IDs served by at least one MME. The PLMN ID is defined in the attribute eNodeBPlmnId in the parent ENodeBFunction. PLMN IDs from additionalPlmnList also appear in this list. The list may include up to 6 PLMNs.";
      erienmyext:enm-type STRUCT;
      uses erienmnrmlrat:struct-PlmnIdentityRO;
    } // end 'list activePlmnList'
    leaf filterUeDlThpVolThr {
      description "Defines PDCP volume threshold for counter pmUeThpDlMbbFilteredDistr. UE session with PDCP volume less than this threshold is filtered out.";
      yexte:takes-effect "Next ROP";
      type erienmnrmlrat:ddt-Lrat_EUtranCellTDD_filterUeDlThpVolThr;
      default 100;
    }
    leaf pdcchTargetBlerVolte {
      description "PDCCH target error rate for UEs with any bearer mapped to a QCI with serviceType of VoIP. In TDD, this parameter applies only to UEs which are configured with HARQ-ACK bundling.";
      yexte:takes-effect "Object unlocked";
      type erienmnrmlrat:ddt-Lrat_EUtranCellTDD_pdcchTargetBlerVolte;
      default 22;
    }
    leaf cellRange {
      description "The maximum distance from the base station where a connection to a UE can be setup and maintained.";
      yexte:disturbances "Changes may affect traffic.";
      yexte:takes-effect "Object unlocked";
      yexte:dependencies "For cellRange greater than 15 subframeAssignment must be set to 1. The round trip time at the cellRange together with switching time must be less than the time available in special subframe.";
      type erienmnrmlrat:ddt-Lrat_EUtranCellTDD_cellRange;
      default 15;
    }
    container siPeriodicity {
      description "The periodicity of System Information (SI) messages. If a System Information Block (SIB) is not mapped to a SI message, the SI message is not transmitted.";
      erienmyext:enm-type STRUCT;
      uses erienmnrmlrat:struct-PeriodicitySI;
    } // end 'container siPeriodicity'
    list pciConflictCell {
      min-elements 0;
      max-elements 5;
      key auto-generated-struct-key;
      leaf auto-generated-struct-key {
        type uint16;
        description "This leaf has been injected to allow for struct instances in a sequence to be ordered.";
        mandatory true;
      }
      description "Indicates the CGI of the other cell that is involved in the PCI collision/confusion. This value is only valid if the attribute pciConflict is \"YES\" or \"YES_CONFLICTING_CELL\".";
      erienmyext:enm-type STRUCT;
      uses erienmnrmlrat:struct-Cgi;
    } // end 'list pciConflictCell'
    leaf ailgActive {
      config false;
      description "The state of the feature Air Interface Load Generator. Indicates if it is running or stopped.";
      notife:notifiable-state-data true;
      type boolean;
    }
    container mappingInfoCe {
      description "SI message to which each SIB is mapped.\nNote: SIB2 is always mapped to SI message 1 according to 3GPP TS 36.331.";
      erienmyext:enm-type STRUCT;
      uses erienmnrmlrat:struct-MappingInfoSIBsBr;
    } // end 'container mappingInfoCe'
    leaf dlPowerRatio {
      description "Ratio of downlink output power.\nValue less than 100 reduces cell TX power from the initially configured cell TX power. After value is changed, cell TX power changes with rate dlPowerChangeRate.";
      yexte:disturbances "Changing this attribute can cause loss of traffic.";
      yexte:precondition "Setting this attribute is not allowed when dlPowerState is CHANGING.";
      yexte:dependencies "Only relevant if the license for Soft Reduction of Cell Tx Power is present and the feature is active.";
      type erienmnrmlrat:ddt-Lrat_EUtranCellTDD_dlPowerRatio;
      default 100;
    }
    leaf administrativeState {
      description "The administrative state.\n";
      yexte:disturbances "Changing this attribute to LOCKED or SHUTTINGDOWN causes loss of traffic. Changing this attribute can cause all unlocked NBIoT cells to change administrativeState to LOCKED and then UNLOCKED. This happens when one of the following thresholds is crossed: 18 EUTRAN cells + 1 NBIoT cell or 9 NBIoT cells.";
      type erienmnrmlrat:enum-AdmState;
      default LOCKED;
    }
    leaf lbabThreshTimeHigh {
      description "Time period to measure RRC Connection Reject Ratio against threshold lbabThreshRejectRateHigh.";
      yexte:dependencies "Only takes effect when Load-Based Access Barring is activated.";
      type erienmnrmlrat:ddt-Lrat_EUtranCellTDD_lbabThreshTimeHigh;
      default 30;
    }
    leaf dynLoadCtrlMinNewConn {
      description "Minimum number of initial accesses and incoming handovers allowed during Cell Connection Intensity Window.\nIf dynLoadCtrlMinNewConn above what supported by hardware, hardware maximum value will be used.";
      yexte:takes-effect "Next cell unlock";
      yexte:dependencies "Applicable only when serviceState = OPERABLE for Dynamic Load Control.";
      type erienmnrmlrat:ddt-Lrat_EUtranCellTDD_dynLoadCtrlMinNewConn;
      default 1;
    }
    leaf advCellSupAction {
      description "Controls which recovery actions to be performed when ACS detects a sleeping cell.";
      type erienmnrmlrat:enum-AdvCellSupActions;
      default NO_ACTION;
    }
    leaf pdcchAdmEnabled {
      status deprecated {
        yexte:status-information "Since L16A. Has no functional behavior. Planned to be removed.";
      }
      description "Enable the pdcch admission control feature. All rejects will be logged in counter pmCellAdmControlPdcchRej. If set to false we will not reject any Ues due to this function but the potential rejects will be logged in counter pmCellAdmControlPdcchRejMeas.";
      yexte:takes-effect "Cell lock/unlock";
      type boolean;
      default false;
    }
    leaf hoOptAdjThresholdPercQci1 {
      description "Permillage threshold for adjusted handover failure rate required to adjust cellIndividualOffsetEUtranQci1.";
      yexte:disturbances "Changing this attribute can stop outgoing HO.";
      type erienmnrmlrat:ddt-Lrat_EUtranCellTDD_hoOptAdjThresholdPercQci1;
      default 50;
    }
    leaf siWindowLength {
      description "Length of the System Information (SI) window within which each SI message is transmitted. Applies to all SI messages.\nNote:  An SI window of 1 ms may be configured only when a maximum of 5 SI messages is configured for broadcast by attribute mappingInfo, to avoid collision with SIB1 transmission in subframe #5.";
      yexte:takes-effect "When EUtranCellFDD/TDD object is unlocked";
      yexte:dependencies "siWindowLength must be 10 ms or above in case PWS SI messages are broadcasted.";
      type erienmnrmlrat:ddt-Lrat_EUtranCellTDD_siWindowLength;
      default 10;
    }
    leaf siValidityTimeBr {
      description "SI validity timer. The timer is set to 3h or 24h.";
      yexte:takes-effect "Object unlocked";
      type erienmnrmlrat:enum-ValidityTime;
      default VALIDITY_TIME_3H;
    }
    leaf noOfCrsPorts {
      config false;
      description "Number of CRS ports used for a cell that is sending CRS over air interface. -1 means undefined when a cell is not sending CRS over air interface. For example when a cell is locked or disabled.";
      notife:notifiable-state-data true;
      type erienmnrmlrat:ddt-Lrat_EUtranCellTDD_noOfCrsPorts;
    }
    leaf ulSrsEnable {
      description "Controls whether sounding shall be enabled or not for the functionality that supports sounding.";
      yexte:takes-effect "Cell lock/unlock";
      type boolean;
      default false;
    }
    leaf ulDynUeAdmCtrlRetDiffThr {
      description "Highest allowed UL radio resource utilization ratio for admission of a new non-privileged UE. Applies to each UL resource considered by Dynamic UE Admission Control. Resource utilization is checked against this threshold for all new RRC connections.";
      yexte:disturbances "Changing this attribute can affect the following:\n- the number of RRC-connected users\n- cell throughput and the number of rejected non-privileged RRC connection requests.";
      yexte:dependencies "ulDynUeAdmCtrlRetDiffThr =< ulDynUeAdmCtrlOverloadThr";
      type erienmnrmlrat:ddt-Lrat_EUtranCellTDD_ulDynUeAdmCtrlRetDiffThr;
      default 500;
    }
    leaf dynCellSubscrCap {
      erienmyext:no-notification;
      config false;
      description "Parameter that contains the automatically estimated cell capacity value. The value 0 indicates that no estimated value exists.";
      type erienmnrmlrat:ddt-Lrat_EUtranCellTDD_dynCellSubscrCap;
    }
    list additionalPlmnList {
      min-elements 0;
      max-elements 5;
      key auto-generated-struct-key;
      leaf auto-generated-struct-key {
        type uint16;
        description "This leaf has been injected to allow for struct instances in a sequence to be ordered.";
        mandatory true;
      }
      description "Lists additional PLMN IDs supported in the cell.\n\nThe list may include up to 5 PLMNs, and they must be the same in all EUtranCells in the node.";
      erienmyext:enm-type STRUCT;
      uses erienmnrmlrat:struct-PlmnIdentity;
    } // end 'list additionalPlmnList'
    leaf cbrsTxExpireTime {
      erienmyext:no-notification;
      config false;
      description "UTC time to determine when to stop transmitting on assigned spectrum. After it expires or is set to \"\", cell becomes disabled. Initial value is \"\".\nValue represents international standard for date and time representation (ISO 8601). String format is YYYY-MM-DDThh:mm:ss[.S+]Z.";
      type erienmnrmlrat:ddt-Lrat_EUtranCellTDD_cbrsTxExpireTime;
    }
    leaf lbUtranOffloadThreshold {
      description "Threshold for eNodeB\nThe value applies for offload towards UTRAN target cells. The eNodeB attempts to offload traffic from the source cell corresponding to the subscription ratio above the threshold.";
      yexte:disturbances "Changing this attribute can cause loss of traffic.";
      type erienmnrmlrat:ddt-Lrat_EUtranCellTDD_lbUtranOffloadThreshold;
      default 100;
    }
    leaf pdschTypeBGain {
      description "Sets the DL power of the PDSCH type B resource elements relatively the PDSCH type A resource elements. Values pdschTypeBGain=(0,1,2,3) define the gains (5/4,1,3/4,1/2) respectively, corresponding to the multi-antenna scenario specified in 3GPP TS 36.213.\nExample: If the pdschTypeBGain is 3 (gain=1/2), the power of the PDSCH type B resource elements is a factor 1/ 2 of the power of the PDSCH type A resource elements.\nPDSDH type A resource elements are located in symbols that do not contain cell specific reference signals (CRS). PDSCH type B resource elements are located in symbols that contain CRS.";
      yexte:takes-effect "Cell lock/unlock";
      yexte:dependencies "The pdschTypeBGain=0 (gain=5/4) is not allowed if crsGain=1.77,3.0, 4.77,6.0 dB. This combination causes over allocation of DL mean radio power and attribute pdschTypeBGain is set to 1 (gain=1).\nThe pdschTypeBGain only takes effect if the configured number of antenna ports is 2,4, or 8.  In the one port case, the power of resource elements for  PDSCH type A and B is equal.";
      type erienmnrmlrat:ddt-Lrat_EUtranCellTDD_pdschTypeBGain;
      default 0;
    }
    leaf deallocTimerPucchFormat1 {
      description "A guard time. After this time, a PUCCH format 1 PRB pair is deallocated if threshold deallocThrPucchFormat1 is still passed.";
      type erienmnrmlrat:ddt-Lrat_EUtranCellTDD_deallocTimerPucchFormat1;
      default 6000;
    }
    leaf ulSCellPriority {
      description "Relative priority in initial SCell selection for cells that can be configured with UL Carrier Aggregation. Applicable where several SCells are initially configured simultaneously. Lowest value has highest priority.";
      yexte:takes-effect "New connection";
      yexte:dependencies "Applicable when 3CC Carrier aggregation Extension Feature (FAJ 121 3084) is enabled and sCellSelectionMode is equal to UN_ACK_SIMULTANEOUS_SCELL_SELECTION or ACK_SIMULTANEOUS_SCELL_SELECTION.";
      type erienmnrmlrat:ddt-Lrat_EUtranCellTDD_ulSCellPriority;
      default 5;
    }
    leaf dlMaxMuMimoLayers {
      description "Enables downlink multiuser MIMO at cell level. The value corresponds to the maximum allowed number of co-scheduled layers. Only single user MIMO is allowed when the value is zero.";
      yexte:takes-effect "Next cell unlock";
      yexte:dependencies "Only takes effect if the cell is operating with an AAS radio.";
      type erienmnrmlrat:ddt-Lrat_EUtranCellTDD_dlMaxMuMimoLayers;
      default 0;
    }
    leaf cellId {
      yexte:restricted;
      description "RBS internal ID attribute for EUtranCell. Must be unique in the RBS. Together with the Node ID and Public Land Mobile Network (PLMN) this is a universally unique cell ID.\nRange 0-255.";
      mandatory true;
      yexte:disturbances "Changing this attribute can cause loss of traffic.";
      type erienmnrmlrat:ddt-Lrat_EUtranCellTDD_cellId;
    }
    leaf enableSinrUplinkClpc {
      description "Specifies if SINR-based UL power control can be used or not. If enabled, SNR-based closed-loop power control and SINR-based closed-loop power control can be adaptively selected.";
      yexte:dependencies "Attribute only has effect if feature Differential Uplink Power Control is activated.";
      type boolean;
      default false;
    }
    leaf srProcessingLevel {
      description "Defines how many SRs eNodeB must receive in a row in order to process it. Used together with srDetectHighThres to reduce false SR detection.";
      yexte:takes-effect "Cell lock/unlock";
      type erienmnrmlrat:enum-SrProcessingLevel;
      default NO_ADDITIONAL_SR_NEEDED;
    }
    leaf acBarringInfoPresent {
      description "Specifies presence of the following IEs:\n- ac-BarringInfo\n- ssac-BarringForMMTEL-Voice-r9\n- ssac-BarringForMMTEL-Video-r9\n- ac-BarringForCSFB-r10\n- ac-BarringSkipForMMTELVoice-r12\n- ac-BarringSkipForMMTELVideo-r12\n- ac-BarringSkipForSMS-r12 in SIB2";
      yexte:disturbances "Changing this attribute can cause loss of traffic.";
      type boolean;
      default false;
    }
    leaf lbabThreshRejectRateHigh {
      description "RRC Connection Reject Ratio threshold above which Load-Based Access Barring increases access class barring probability or Progressive Access Barring, or PLMN-Specific Access Barring proceeds to higher priority.";
      yexte:dependencies "Only takes effect when Load-Based Access Barring is activated.";
      type erienmnrmlrat:ddt-Lrat_EUtranCellTDD_lbabThreshRejectRateHigh;
      default 200;
    }
    leaf hpueCaSwitchHyst {
      description "Hysteresis of SINR threshold for triggering a switch to high power UE.";
      type erienmnrmlrat:ddt-Lrat_EUtranCellTDD_hpueCaSwitchHyst;
      default 20;
    }
    leaf interferenceThresholdSinrClpc {
      description "Threshold value for measured noise plus interference level. If measured noise plus interference is higher than interferenceThresholdSinrClpc, then SINR-based UL closed-loop power control can be considered.";
      yexte:dependencies "Threshold only has effect if attribute enableSinrUplinkClpc is true.";
      type erienmnrmlrat:ddt-Lrat_EUtranCellTDD_interferenceThresholdSinrClpc;
      default -105;
    }
    leaf primaryPlmnAlarmSuppr {
      description "Indicates if the primary PLMN ID in the cell is suppressed for alarms PLMN Service Degraded and PLMN Service Unavailable when primary PLMN is not available in the cell.\nThe primary PLMN ID is suppressed if this attribute is set to true.\nIf the configured PLMN ID is not a served PLMN ID, then the alarm is suppressed independent of the configured settings.";
      type boolean;
      default false;
    }
    leaf rwrSearchZoneAllowed {
      description "Allows for release-with-redirect in search zone when EUtranFreqRelation::mobilityAction attribute is configured as HANDOVER.";
      yexte:takes-effect "New connection";
      yexte:dependencies "Mobility control at poor coverage must be active.";
      type boolean;
      default true;
    }
    leaf liteMcsReduction {
      description "LiteMcsReduction feature mode.";
      type erienmnrmlrat:enum-LiteMcsReductionMode;
      default ON;
    }
    leaf qQualMin {
      description "Specifies the minimum required quality level (RSRQ) in the cell in dB.\nCorresponds to Qqualmin in TS 36.304, sent in SIB1. Value 0 means that it is not sent and UE applies in such case the (default) value of negative infinity for Qqualmin.";
      yexte:dependencies "The field is mandatory present if the Struct Member threshServingLowQ in SIB3 is used in systemInformationBlockType3.";
      type erienmnrmlrat:ddt-Lrat_EUtranCellTDD_qQualMin;
      default 0;
    }
    leaf gpsTimeSFN0Seconds {
      config false;
      description "The integer part of the GPS time for the most recent occurrence of SFN=0 in the cell.";
      notife:notifiable-state-data true;
      type erienmnrmlrat:ddt-Lrat_EUtranCellTDD_gpsTimeSFN0Seconds;
    }
    leaf userLabel {
      description "Label for free use.\n";
      type erienmnrmlrat:ddt-Lrat_EUtranCellTDD_userLabel;
    }
    leaf expectedMaxNoOfUsersInCell {
      description "The expected max number of UE in RRC_CONNECTED mode in the cell. Will be used at unlock of the cell to distribute cells to different cores in Digital Units and Baseband Units with a multicore Main Processor. A value of -1 indicates that measuredMaxNoOfUsersInCell will be used to control the cell distribution.";
      yexte:takes-effect "Object unlocked";
      type erienmnrmlrat:ddt-Lrat_EUtranCellTDD_expectedMaxNoOfUsersInCell;
      default -1;
    }
    leaf primaryPlmnReserved {
      description "Indicates if the primary PLMN ID in the cell is reserved for operator use. The primary PLMN ID is reserved if this attribute is set to true.";
      yexte:disturbances "Changing this attribute can block traffic in the cell.";
      yexte:dependencies "the attribute eNodeBPlmnId in the parent ENodeBFunction will hold the value of the primary PLMN ID.";
      type boolean;
      default false;
    }
    leaf dlConfigurableFrequencyStart {
      description "Specifies the start frequency offset for the allocation of resources when the downlink interference management is disabled expressed as a percentage of the configured bandwidth.";
      yexte:takes-effect "Object unlocked";
      yexte:dependencies "dlInterferenceManagementActive shall be disabled before this parameter takes effect.";
      type erienmnrmlrat:ddt-Lrat_EUtranCellTDD_dlConfigurableFrequencyStart;
      default 0;
    }
    leaf pucchOverdimensioning {
      description "Number of resource blocks outside each Physical Uplink Control Channel (PUCCH) region that are available for scheduling Physical Uplink Shared Channel (PUSCH).\nNote: Both the value of this attribute and the amount of resources allocated for PUCCH impacts where the resource allocation of the PRACH starts.";
      yexte:takes-effect "Object disabled/enabled.";
      type erienmnrmlrat:ddt-Lrat_EUtranCellTDD_pucchOverdimensioning;
      default 0;
    }
    leaf cioLowerLimitAdjBySon {
      description "Indicates the lower limit value of cellIndividualOffsetEUtran range that the SON function is allowed to adjust.";
      yexte:disturbances "Changing this attribute can stop outgoing HO.";
      type erienmnrmlrat:ddt-Lrat_EUtranCellTDD_cioLowerLimitAdjBySon;
      default -3;
    }
    leaf puschPwrOffset64qam {
      description "Power offset to the target-received PUSCH Power Spectral Density (PSD) for 64-QAM-capable UEs. Used to control the received SINR target.\nIt is used to enable maximum throughput for 64QAM, which in some configurations is not possible otherwise, see dependencies.";
      yexte:disturbances "Changes can affect traffic.";
      yexte:dependencies "Only relevant if the license for 64-QAM Uplink is present and the\nfeature is active.\nFor 2Rx, pZeroNominalPusch + puschPwrOffset64qam needs to be -100 dBm or higher to achieve maximum throughput.\npuschPwrOffset64Qam should be set to 0 when both UL 64QAM and UL MU-MIMO are enabled in eNB.";
      type erienmnrmlrat:ddt-Lrat_EUtranCellTDD_puschPwrOffset64qam;
      default 0;
    }
    leaf timePhaseMaxDeviationTddIndex {
      description "Index of max allowed time and phase deviation for time and phase synchronization of TDD cell.";
      yexte:disturbances "Changing this attribute can affect traffic.";
      yexte:dependencies "ENodeBFunction::timeAndPhaseSynchAlignment must be true.";
      type erienmnrmlrat:enum-TimePhaseMaxDeviationTddIndex;
      default TIME_PHASE_MAX_DEVIATION_TDD_IDX0;
    }
    leaf noOfPucchCqiUsers {
      description "The number of Channel Quality Indicator (CQI) resources available on the PUCCH channel.\nFor TDD Subframe Assignment 1 the recommended value is 64.";
      yexte:disturbances "Cell runs new set-up procedure. All cell-connected UEs are released and connected again.";
      type erienmnrmlrat:ddt-Lrat_EUtranCellTDD_noOfPucchCqiUsers;
      default 16;
    }
    leaf hoOptStatTime {
      description "The operational cycle of the handover optimization function.";
      type erienmnrmlrat:ddt-Lrat_EUtranCellTDD_hoOptStatTime;
      default 24;
    }
    leaf drxActive {
      description "Indicates if the DRX function in the cell is activated.";
      yexte:takes-effect "New connection";
      type boolean;
      default false;
    }
    leaf pdcchOuterLoopInitialAdjPCell {
      description "The initial value for primary cell PDCCH outer loop adjustment in case of carrier aggregation. This applies to UEs that have at least one secondary cell configured and do not have any bearer mapped to a QCI with serviceType of VoIP. In TDD, this parameter is not used.";
      yexte:takes-effect "Object unlocked";
      type erienmnrmlrat:ddt-Lrat_EUtranCellTDD_pdcchOuterLoopInitialAdjPCell;
      default -70;
    }
    leaf cfraEnable {
      description "This parameter controls if Contention Free Random Access (CFRA, known as non-contention based random access in 3GPP term) shall be enabled or not. When enabled, a portion of random access preambles should be allocated for CFRA and CFRA can be used for incoming HO and PDCCH ordered uplink re-sync.";
      yexte:takes-effect "Cell lock/unlock";
      type boolean;
      default false;
    }
    leaf lbEUtranCellOffloadCapacity {
      description "This attribute indicates the offload subscription capacity associated with the EUTRAN target cell. The value is used to moderate the offload rate to the EUTRAN target cell.";
      yexte:disturbances "Changing this attribute can cause loss of traffic.";
      type erienmnrmlrat:ddt-Lrat_EUtranCellTDD_lbEUtranCellOffloadCapacity;
      default 1000;
    }
    leaf dynUeAdmCtrlFilterConst {
      description "Time constant of the exponential-weighted moving average filter applied to the radio resource utilization ratios considered by Dynamic UE Admission Control.";
      yexte:disturbances "Changing this attribute can affect the following:\n- the number of RRC-connected users\n- cell throughput and the number of rejected non-privileged RRC connection requests\n- rejected non-privileged RRC connection re-establishment requests and rejected\n  non-privileged incoming handover requests.";
      type erienmnrmlrat:ddt-Lrat_EUtranCellTDD_dynUeAdmCtrlFilterConst;
      default 3000;
    }
    leaf enableServiceSpecificHARQ {
      description "Enable/disable service-specific HARQ on cell level. Function must have valid license.";
      yexte:takes-effect "New connection";
      type boolean;
      default false;
    }
    leaf acBarringSkipForMmtelVideo {
      description "Indicates whether or not access attempts for MMTEL video from UEs are to skip Access Class Barring functionality.";
      yexte:disturbances "Changing this attribute can block Video calls.";
      type boolean;
      default false;
    }
    leaf alpha {
      description "The pathloss compensation factor for power control of the Physical Uplink Shared Channel (PUSCH).";
      yexte:disturbances "Changing this attribute can affect traffic.";
      type erienmnrmlrat:ddt-Lrat_EUtranCellTDD_alpha;
      default 10;
    }
    leaf srDetectHighThres {
      description "Defines how many dB higher than the original SR detection threshold can be used as high SR detection threshold. Used together with srProcessingLevel to reduce false SR detection.";
      yexte:takes-effect "Cell lock/unlock";
      type erienmnrmlrat:ddt-Lrat_EUtranCellTDD_srDetectHighThres;
      default 70;
    }
    leaf interEnbUlCompUserSelSinrHys {
      description "Hysteresis of SINR threshold for inter-eNodeB UL CoMP user selection.";
      yexte:disturbances "If changed, system performance can be affected. As values get bigger, gaps for triggering Inter-eNodeB Uplink CoMP user switching get bigger.";
      yexte:dependencies "Must be used together with interEnbUlCompUserSelSinrThr.";
      type erienmnrmlrat:ddt-Lrat_EUtranCellTDD_interEnbUlCompUserSelSinrHys;
      default 10;
    }
    leaf catmMbmsDlSubframes {
      description "Controls which DL subframes are unavailable for Cat-M DL due to MBMS operation.\nFewer unavailable subframes optimize Cat-M1 DL max throughput, but change of unavailable subframes can cause Cat-M1 connection drops and temporary difficulties to page certain UEs. Avoided by less dynamic setting (lower value).\n0: Unavailable subframes due to MBMS set according to MbsfnArea::commonSFAllocList and MbsfnArea::mbsfnAreaCellRelation.\n1: Unavailable subframes due to MBMS set according to MbsfnArea::commonSFAllocList and MbsfnArea::mbsfnAreaCellRelation if any MBSFN service is active in the cell, otherwise no unavailable subframes due to MBMS.\n2: Unavailable subframes due to MBMS set according to subframes blocked by active MBSFN services.";
      yexte:takes-effect "Next cell unlock";
      type erienmnrmlrat:ddt-Lrat_EUtranCellTDD_catmMbmsDlSubframes;
      default 0;
    }
    leaf dlPowerChangeRate {
      description "Change rate for downlink output power to reach dlPowerRatio.";
      type erienmnrmlrat:ddt-Lrat_EUtranCellTDD_dlPowerChangeRate;
      default 1;
    }
    leaf-list availabilityStatus {
      min-elements 0;
      config false;
      description "The availability status. It contains details about operationalState. This attribute is set by the application in the RBS.\n";
      notife:notifiable-state-data true;
      type erienmnrmlrat:enum-AvailStatus;
    }
    leaf gpsTimeSFN0DecimalSecond {
      config false;
      description "The decimal part of the GPS time for the most recent occurrence of System Frame Number (SFN)=0 in the cell.\nUnit: 2^(-32) second";
      notife:notifiable-state-data true;
      type erienmnrmlrat:ddt-Lrat_EUtranCellTDD_gpsTimeSFN0DecimalSecond;
    }
    leaf-list validDlBrSubframes {
      min-elements 0;
      max-elements 4;
      config false;
      description "Shows valid subframes for DL BR transmissions, indicated by broadcasted SIB1-BR.\n1: Corresponding subframe is valid DL BR subframe.\n0: Corresponding subframe not valid DL BR subframe.\nFirst element in the list corresponds to radio frames satisfying SFN mod 4 = 0, the next to radio frames satisfying SFN mod 4 = 1 and so on.\nEach least significant bit represents subframe #0 of the corresponding SFN.\nIf SIB1-BR not broadcasted (Cat-M not supported in cell), list is empty.";
      notife:notifiable-state-data true;
      type erienmnrmlrat:ddt-Lrat_EUtranCellTDD_validDlBrSubframes;
    }
    leaf hoOptStatNum {
      description "The minimal number of handovers required by the handover optimization function before adjusting  handover parameters.";
      type erienmnrmlrat:ddt-Lrat_EUtranCellTDD_hoOptStatNum;
      default 200;
    }
    leaf spifhoSetupBearerAtInitialCtxtSetup {
      description "Decides if a bearer handled by the feature Service or Priority Triggered Inter-Frequency Handover (SPIFHO) is set up at Initial Context Setup even when attribute servOrPrioIFHoSetupBearer is false.";
      yexte:takes-effect "New connection";
      yexte:dependencies "The value of this attribute is only considered when the value of servOrPrioIFHoSetupBearer=false.";
      type boolean;
      default false;
    }
    leaf tReorderingAutoConfiguration {
      description "Enable automatic configuration of tReorderingDl and tReorderingUl. Configuration is based on HARQ-interval together with an offset defined by harqOffsetDl/harqOffsetUl.tReordering >= 'Max number of HARQ' * HARQ-interval + harqOffset, where closest higher or equal allowed value is used.\nThis configuration is only applied to UM bearers. AM bearers will still use tReorderingUl and tReorderingDl from QciProfilePredefined or QciProfileOperatorDefined.";
      yexte:takes-effect "New connection";
      type boolean;
      default false;
    }
    leaf bcCdma2000SysTimeType {
      config false;
      description "The actual type of CDMA2000 system time that is broadcast in SIB8.";
      notife:notifiable-state-data true;
      type erienmnrmlrat:enum-Cdma2000SysTimeVals;
    }
    leaf ns05FullBandSchedEnabled {
      description "Enables PUSCH 100 PRBs scheduling.";
      yexte:dependencies "Only takes effect if:\n- license for NS 05 Additional Maximum Power Reduction Support is present and the feature is active, and\n- attribute networkSignallingValue in MOC EUtranCellFDD/TDD is NS_05.";
      type boolean;
      default false;
    }
    leaf pdcchOuterLoopUpStepPCell {
      description "PDCCH outer loop up step size for primary cells in case of carrier aggregation. This applies to UEs that have at least one secondary cell configured and do not have any bearer mapped to a QCI with serviceType of VoIP. In TDD, this parameter is not used.";
      yexte:takes-effect "Object unlocked";
      type erienmnrmlrat:ddt-Lrat_EUtranCellTDD_pdcchOuterLoopUpStepPCell;
      default 6;
    }
    leaf primaryPsdOffset {
      description "Offset value that controls the maximum allowed difference between pZeroNominalPusch and the received power below pZeroNominalPusch in the primary sector when UL CoMP is used.";
      type erienmnrmlrat:ddt-Lrat_EUtranCellTDD_primaryPsdOffset;
      default 0;
    }
    leaf noOfPucchFormat3PrbPairsPerFrame {
      erienmyext:no-notification;
      config false;
      description "PRB usage for PUCCH Format3. Based on 3CC Carrier Aggregation user configuration.";
      type erienmnrmlrat:ddt-Lrat_EUtranCellTDD_noOfPucchFormat3PrbPairsPerFrame;
    }
    leaf ulImprovedUeAdapRetransEnabled {
      status deprecated {
        yexte:status-information "Since 17.Q3. Has no functional behavior. Planned to be removed.";
      }
      description "Whether or not UL-scheduler is enabled that uses adaptive re-transmission more frequently for data-aware UL-scheduling UEs, to reduce fragments in UL spectrum.";
      type boolean;
      default true;
    }
    leaf prsPowerBoosting {
      description "Used for selecting the different power boosting alternatives for PRS transmissions. If set to 0, a default table based on the number of PBCH antennas and transmission scheme is shown. If set to 1, 2, or 3, it results in a power boosting of 0 dB, 3 dB, or 6 dB respectively.";
      yexte:takes-effect "Object unlocked";
      type erienmnrmlrat:ddt-Lrat_EUtranCellTDD_prsPowerBoosting;
      default 0;
    }
    leaf ulPsdLoadThresholdSinrClpc {
      description "Threshold of UL transmission power per PRB. If averaged UL transmission power measurement per PRB is lower than ulPsdLoadThresholdSinrClpc over a set percentage of UL bandwidth, then SINR-based UL closed-loop power control can be considered.";
      yexte:dependencies "Threshold only has effect if attribute enableSinrUplinkClpc is true.";
      type erienmnrmlrat:ddt-Lrat_EUtranCellTDD_ulPsdLoadThresholdSinrClpc;
      default 2;
    }
    leaf prsMutingPatternLen {
      description "Used for selecting the length of the PRS muting pattern. Setting the pattern length to 1 results in deactivation of PRS muting. The muting pattern is set to \"1111111111111\" in this case. Other recommended muting pattern lengths are: 2, 4, 8, and 16 bits.";
      yexte:takes-effect "Object unlocked";
      type erienmnrmlrat:ddt-Lrat_EUtranCellTDD_prsMutingPatternLen;
      default 1;
    }
    leaf noOfEnhAdptReTxCand {
      description "Threshold used in restrict SE number that enhanced adaptive Retransmission candidates, if there are too many non-adaptive retransmission candidates, only \"noOfEnhAdptReTxCand\" numbers SE can be the enhanced adaptive retransmission queue.\nMaximum number of SEs added to the enhanced adaptive retransmission queue as candidates.\nIf set to -1, number of candidates is automatically decided by eNodeB.\nIf set to 0, no UEs added to queue and thus feature has no effect.";
      type erienmnrmlrat:ddt-Lrat_EUtranCellTDD_noOfEnhAdptReTxCand;
      default 0;
    }
    leaf enableUeAssistedAdaptiveDrx {
      description "Enable or disable the UE-Assisted Adaptive DRX feature.";
      yexte:takes-effect "Object unlocked";
      type boolean;
      default true;
    }
    leaf isDlOnly {
      description "Indicates if the cell is operated with downlink only and with no uplink.";
      yexte:disturbances "Changes may affect traffic.";
      yexte:takes-effect "Object unlocked";
      type boolean;
      default false;
    }
    leaf tTimeAlignmentTimer {
      description "A timer used for supervision and control of uplink synchronization. Special value: 0 means infinity.";
      yexte:takes-effect "Cell lock/unlock";
      type erienmnrmlrat:ddt-Lrat_EUtranCellTDD_tTimeAlignmentTimer;
      default 0;
    }
    leaf dlInterferenceManagementActive {
      description "Specifies if the downlink interference management is enabled or disabled.";
      yexte:takes-effect "Object unlocked";
      type boolean;
      default false;
    }
    leaf prsTransmisScheme {
      description "Used for selecting whether the PRS transmission must use antenna switching or pre-coder switching.";
      yexte:takes-effect "Object unlocked";
      type erienmnrmlrat:enum-TransmissionScheme;
      default ANTENNA_SWITCHING;
    }
    container ssacBarringForMMTELVideo {
      description "Service specific access class barring parameters for MMTEL video originating calls.\nInformation broadcasted in SIB2.";
      erienmyext:enm-type STRUCT;
      uses erienmnrmlrat:struct-AcBarringConfig;
    } // end 'container ssacBarringForMMTELVideo'
    leaf acBarringForEmergency {
      description "Access class barring for  Emergency, which corresponds to access class 10.";
      yexte:disturbances "Changing this attribute can block emergency calls.";
      yexte:dependencies "ac-BarringForEmergency value in SIB2 can be automatically overridden by Progressive Barring of Special Access Classes algorithm regardless of value in this attribute when its corresponding AcBarringModeEm is set to AUTO.";
      type boolean;
      default false;
    }
    leaf lbabMinBarringFactor {
      description "Minimum barring factor for Load-Based Access Barring algorithm or priority level 0 for one of the following algorithms:\n- Progressive Access Barring\n- Progressive Barring of Special Access Classes\n- PLMN-Specific Access Barring";
      yexte:dependencies "Only takes effect when feature Load-Based Access Barring or feature Progressive Access Barring is activated.";
      type erienmnrmlrat:ddt-Lrat_EUtranCellTDD_lbabMinBarringFactor;
      default 0;
    }
    leaf-list prioAdditionalFreqBandList {
      min-elements 0;
      max-elements 8;
      description "List of additional frequency bands the cell belongs to. Primary frequency band, EARFCN value of the cell, is not included. Secondary cell evaluation is done according to list order, and/or the list is broadcasted in SIB1. Highest priority band is position 0 in the list.";
      yexte:precondition "ENodeBFunction::useBandPrioritiesInSCellEval and/or ENodeBFunction::useBandPrioritiesInSib1 must be enabled.";
      yexte:dependencies "List only contains frequency bands from additionalFreqBandList.";
      type erienmnrmlrat:ddt-Lrat_EUtranCellTDD_prioAdditionalFreqBandList;
    }
    leaf-list emergencyAreaId {
      min-elements 0;
      max-elements 15;
      description "A cell that supports  broadcast of warning messages can belong to one to 15 Emergency Areas, identified by an Emergency Area Id, set by the operator.  Value -1 means identity not set.";
      type erienmnrmlrat:ddt-Lrat_EUtranCellTDD_emergencyAreaId;
      default -1;
      default -1;
      default -1;
      default -1;
      default -1;
      default -1;
      default -1;
      default -1;
      default -1;
      default -1;
      default -1;
      default -1;
      default -1;
      default -1;
      default -1;
    }
    leaf dlDynUeAdmCtrlOverloadThr {
      description "Highest allowed DL radio resource utilization ratio for admission of a non-privileged UE. Applies to each DL resource considered by Dynamic UE Admission Control. Resource utilization is checked against this threshold for all new, re-established, or incoming handover RRC connections.";
      yexte:disturbances "Changing this attribute can affect the following:\n- the number of RRC-connected users\n- cell throughput and the number of rejected non-privileged RRC connection requests\n- rejected non-privileged RRC connection re-establishment requests and rejected\n  non-privileged incoming handover requests.";
      yexte:dependencies "dlDynUeAdmCtrlOverloadThr >= dlDynUeAdmCtrlRetDiffThr";
      type erienmnrmlrat:ddt-Lrat_EUtranCellTDD_dlDynUeAdmCtrlOverloadThr;
      default 600;
    }
    leaf rxSinrTargetClpc {
      description "SINR target value for SINR-based UL closed-loop power control.";
      yexte:disturbances "Changing this attribute can cause loss of traffic.";
      yexte:dependencies "SINR target only has effect if attribute enableSinrUplinkClpc is true.";
      type erienmnrmlrat:ddt-Lrat_EUtranCellTDD_rxSinrTargetClpc;
      default 25;
    }
    leaf nrOfPreallocatedSrRes {
      config false;
      description "Number of successfully preallocated Scheduling Request resources at cell setup.\nUndefined value: -1";
      yexte:dependencies "Relation to AdmissionControl::nrOfPaConnReservationsPerCell.\nSuccessful preallocation: nrOfPreallocatedSrRes = nrOfPaConnReservationsPerCell\nPartially successful preallocation: nrOfPreallocatedSrRes < nrOfPaConnReservationsPerCell\nFailed preallocation: nrOfPreallocatedSrRes = 0\nNo preallocation attempt (default): nrOfPreallocatedSrRes = -1";
      notife:notifiable-state-data true;
      type erienmnrmlrat:ddt-Lrat_EUtranCellTDD_nrOfPreallocatedSrRes;
    }
    leaf threshServingLow {
      description "Specifies the threshold that the signal strength of the serving cell must be below for cell reselection towards a lower priority Inter-Frequency or Inter-RAT frequency.\nCorresponds to ThreshServingLowP in TS 36.304.";
      type erienmnrmlrat:ddt-Lrat_EUtranCellTDD_threshServingLow;
      default 0;
    }
    leaf dynUlResourceAllocEnabled {
      description "Enables Dynamic uplink resource allocation on cell level.";
      yexte:takes-effect "Cell lock/unlock";
      yexte:dependencies "Only relevant if license UlDynamicResourceAllocation is present and feature is active.";
      type boolean;
      default false;
    }
    container mappingInfo {
      description "The System Information (SI) message to which each System Information Block (SIB) is mapped.\n\nNote: SIB2 is always mapped to the SI message 1 according to 3GPP TS 36.331.";
      erienmyext:enm-type STRUCT;
      uses erienmnrmlrat:struct-MappingInfoSIBs;
    } // end 'container mappingInfo'
    leaf-list pciConflict {
      min-elements 0;
      max-elements 5;
      description "A PCI confusion exists if a source cell has relations to two neighbor cells where both neighbor cells have the same PCI and frequency. A PCI collision exists if a source cell has a relation to a neighbor cell where both the source cell and neighbor cell have the same PCI and frequency.";
      type erienmnrmlrat:enum-PciConflict;
    }
    leaf specialSubframePattern {
      description "The special subframe pattern configuration for Downlink Part of Time Slot (DwPTS), Guard Period (GP), and Uplink Part of Time Slot (UpPTS). All TDD cells in the same frequency band, or specific frequency band combinations where one frequency band overlaps with another (e.g. Band 38 and Band 41) must have the same special subframe pattern configuration.";
      yexte:disturbances "Changes may affect traffic.";
      yexte:takes-effect "Object unlocked";
      yexte:dependencies "specialSubframePattern = 5 can not be used in combination with nB=T4 on MO Paging, see 3GPP TS 36.213.\nThe round trip time at the cellRange together with switching time must be less than the time available in special subframe.";
      type erienmnrmlrat:ddt-Lrat_EUtranCellTDD_specialSubframePattern;
      default 7;
    }
    leaf networkSignallingValueCa {
      description "Enables additional spectrum emission requirements for CA according to 3GPP TS 36.101, table 6.2.4A-1.";
      yexte:takes-effect "Object disabled/enabled";
      type erienmnrmlrat:enum-NetworkSignallingValueCa;
      default CA_NS_31;
    }
    leaf ns05FullBandUsersInCellThres {
      description "Value of threshold to enable the PUSCH 100 PRBs scheduling. PUSCH 100 PRBs scheduling is triggered when the number of UE in RRC_CONNECTED mode in the cell is less than or equal to ns05FullBandUsersInCellThres.";
      yexte:dependencies "Only takes effect if:\n- license for NS 05 Additional Maximum Power Reduction Support is present and the feature is active, and\n- attribute networkSignallingValue in MOC EUtranCellFDD/TDD is NS_05, and\n- attribute ns05FullBandSchedEnabled in MOC EUtranCellFDD/TDD is true.";
      type erienmnrmlrat:ddt-Lrat_EUtranCellTDD_ns05FullBandUsersInCellThres;
      default 10;
    }
    leaf caPrioThreshold {
      description "The threshold number of SCells configured using prioritized SCell selection. When the number of SCells configured for UEs connected in this PCell is higher than caPrioThreshold, all frequency carriers configured for carrier aggregation are assumed to have equal priority regardless of the configured values.";
      yexte:takes-effect "Next cell unlock";
      yexte:dependencies "Only applicable when CarrierAggregationFunction::dynamicSCellSelectionMethod == PRIORITIZED.";
      type erienmnrmlrat:ddt-Lrat_EUtranCellTDD_caPrioThreshold;
      default 300;
    }
    leaf noOfUlImprovedUe {
      description "Number of data-aware UL-scheduling UEs that can be improved at allocation of PDCCH and PUSCH.";
      type erienmnrmlrat:ddt-Lrat_EUtranCellTDD_noOfUlImprovedUe;
      default 1;
    }
    leaf lbabMinBarringFactorPrio3 {
      description "Priority level 3 minimum barring factor for one of the following algorithms:\n- Progressive Access Barring\n- Progressive Barring of Special Access Classes\n- PLMN-Specific Access Barring";
      yexte:dependencies "Only takes effect when Progressive Access Barring is activated.";
      type erienmnrmlrat:ddt-Lrat_EUtranCellTDD_lbabMinBarringFactorPrio3;
      default 0;
    }
    leaf lbabMinBarringFactorPrio4 {
      description "Priority level 4 minimum barring factor for one of the following algorithms:\n- Progressive Access Barring\n- Progressive Barring of Special Access Classes\n- PLMN-Specific Access Barring";
      yexte:dependencies "Only takes effect when Progressive Access Barring is activated.";
      type erienmnrmlrat:ddt-Lrat_EUtranCellTDD_lbabMinBarringFactorPrio4;
      default 0;
    }
    leaf cellDownlinkCaCapacity {
      description "Normalized downlink cell capacity available for use by carrier aggregation. The value is used to calculate the aggregated capacity of a UE:s possible aggregation possibilities, for example by the CA Aware IFLB feature.";
      type erienmnrmlrat:ddt-Lrat_EUtranCellTDD_cellDownlinkCaCapacity;
      default 0;
    }
    leaf harqOffsetDl {
      description "Offset used when tReorderingDl is calculated by automatic configuration. tReorderingDl = 'Max number of HARQ for DL' * HARQ-interval + harqOffsetDl.";
      yexte:takes-effect "New connection";
      type erienmnrmlrat:ddt-Lrat_EUtranCellTDD_harqOffsetDl;
      default 3;
    }
    leaf advCellSupSensitivity {
      description "Indicates the sensitivity of the Advanced Cell Supervision function. A higher value will make ACS detect a sleeping cell faster, but with higher risk for false detection. A lower value will make ACS detect a sleeping cell slower, but with lower risk for false detection.";
      yexte:disturbances "Changing this attribute can cause loss of traffic.";
      type erienmnrmlrat:ddt-Lrat_EUtranCellTDD_advCellSupSensitivity;
      default 0;
    }
    leaf initialBufferSizeDefault {
      description "The number of bytes that is assumed to be in the UE buffer when an SR is received through PUCCH.";
      yexte:takes-effect "Cell lock/unlock";
      type erienmnrmlrat:ddt-Lrat_EUtranCellTDD_initialBufferSizeDefault;
      default 86;
    }
    leaf lbabMinBarringFactorPrio1 {
      description "Priority level 1 minimum barring factor for one of the following algorithms:\n- Progressive Access Barring\n- Progressive Barring of Special Access Classes\n- PLMN-Specific Access Barring";
      yexte:dependencies "Only takes effect when feature Progressive Access Barring is activated.";
      type erienmnrmlrat:ddt-Lrat_EUtranCellTDD_lbabMinBarringFactorPrio1;
      default 0;
    }
    leaf puschNcpChannelEstWindowSize {
      description "Normal or Large Window Size for PUSCH filter channel estimation for normal CP.";
      yexte:takes-effect "Next cell unlock";
      type erienmnrmlrat:enum-PuschChannelEstWindowSize;
      default NORMAL_SIZE;
    }
    leaf noOfPucchFormat3PrbPairs {
      description "Number of PUCCH Format 3 PRB pairs.";
      yexte:takes-effect "Cell lock/unlock";
      yexte:dependencies "Only takes effect when either of the following conditions is satisfied:\n3CC Carrier aggregation Extension Feature (FAJ 121 3084) is enabled, or nonCaAnModeF3Enable is true.";
      type erienmnrmlrat:ddt-Lrat_EUtranCellTDD_noOfPucchFormat3PrbPairs;
      default 1;
    }
    leaf lbabMinBarringFactorPrio2 {
      description "Priority level 2 minimum barring factor for one of the following algorithms:\n- Progressive Access Barring\n- Progressive Barring of Special Access Classes\n- PLMN-Specific Access Barring";
      yexte:dependencies "Only takes effect when feature Progressive Access Barring is activated.";
      type erienmnrmlrat:ddt-Lrat_EUtranCellTDD_lbabMinBarringFactorPrio2;
      default 0;
    }
    leaf allocThrPucchFormat1 {
      description "Threshold in terms of number of remaining SR resources available for the cell. Below this threshold, allocTimerPucchFormat1 for allocation of an additional PUCCH format 1 PRB pair is triggered. Occurs if  feature Dynamic PUCCH  is activated. Value 0 means the dynamic PUCCH allocation/deallocation operation for this cell is disabled.";
      yexte:dependencies "If Scheduling Request resources limitation pool for privileged access connections is activated in eNodeB, threshold for allocation of an additional PUCCH format 1 PRB pair by dynamic PUCCH must be higher than number of resources in limitation pool.\n(allocThrPucchFormat1 > AdmissionControl::limitSrNonPa)";
      type erienmnrmlrat:ddt-Lrat_EUtranCellTDD_allocThrPucchFormat1;
      default 50;
    }
    leaf primaryUpperLayerInd {
      description "Whether upperLayerIndication is set for PLMN identified by ENodeBFunction::eNodeBPlmnId.\nThe upperLayerIndication is broadcast in SIB2.";
      yexte:dependencies "Valid for Baseband Radio Node only.";
      type erienmnrmlrat:enum-LayerState;
      default OFF;
    }
    container acBarringForMoSignalling {
      description "Access class barring parameters for mobile originating signaling.\nInformation broadcasted in SIB2.";
      erienmyext:enm-type STRUCT;
      uses erienmnrmlrat:struct-AcBarringConfig;
    } // end 'container acBarringForMoSignalling'
    leaf cellCapMinMaxWriProt {
      description "Write protection that prevents feature Automated Cell Capacity Estimation from changing the value on parameters cellCapMinCellSubCap and cellCapMaxCellSubCap.\nIf set to true, feature Automated Cell Capacity Estimation cannot reset cellCapMinCellSubCap and cellCapMaxCellSubCap at cell unlock.\nIf set to false, feature Automated Cell Capacity Estimation can change cellCapMinCellSubCap and cellCapMaxCellSubCap at cell unlock.";
      type boolean;
      default false;
    }
    leaf lbTpRankThreshMin {
      description "The minimum threshold for the relative gain at throughput aware load balancing. A negative value may allow for some throughput loss for the individual UE, if the load balancing criteria requires so. Higher values may increase the fraction of non-qualified UEs at UE selection for throughput aware load balancing and may cause the load balancing to stall.\nSpecial value -100 means the lower boundary for the threshold is disabled.";
      yexte:disturbances "Changing this attribute can cause loss of traffic.";
      type erienmnrmlrat:ddt-Lrat_EUtranCellTDD_lbTpRankThreshMin;
      default -20;
    }
    leaf physicalLayerSubCellId {
      description "Subidentity within the physical layer cell ID group.\nPhysical layer cell IDs are grouped into 168 unique physical layer cell ID groups. Each group contains 3 unique subidentities.\nUsed with physicalLayerCellIdGroup to calculate physical layer cell ID.";
      mandatory true;
      yexte:disturbances "Changes may affect traffic.";
      type erienmnrmlrat:ddt-Lrat_EUtranCellTDD_physicalLayerSubCellId;
    }
    leaf lbabIncr {
      description "How fast the Access Class Barring probability is increased, that is how fast acBarringFactor in SIB2 is decreased when the cell load is increased.";
      yexte:dependencies "Only takes effect when Load-Based Access Barring is activated.";
      type erienmnrmlrat:ddt-Lrat_EUtranCellTDD_lbabIncr;
      default 5;
    }
    leaf harqOffsetUl {
      description "Offset used when tReorderingUl is calculated by automatic configuration. tReorderingUl = 'Max number of HARQ for UL' * HARQ-interval + harqOffsetUl.";
      yexte:takes-effect "New connection";
      type erienmnrmlrat:ddt-Lrat_EUtranCellTDD_harqOffsetUl;
      default 3;
    }
    container acBarringPresence {
      description "Specifies how access class barring IE for each traffic class is present in SIB2 and priority level assigned to it.";
      erienmyext:enm-type STRUCT;
      uses erienmnrmlrat:struct-AcBarringPresence;
    } // end 'container acBarringPresence'
    leaf sdmActive {
      description "Specifies if SDM (Spatial Division Multiplexing) for CombinedCell configuration is activated or not. If SDM is activated, it is possible to multiplex multiple Ues in different sectors in the same time and same frequency resource.";
      yexte:disturbances "Change can affect traffic";
      yexte:takes-effect "Object disabled/enabled";
      type boolean;
      default false;
    }
    leaf pdschMaxNrOfPrbsPerUe {
      description "Maximum number of physical resource blocks (PRBs) allowed on PDSCH for each UE.\nNote: If the set value is larger than the system bandwidth, then the system bandwidth value will be used instead.\nFor PDSCH resource allocation type 0, the actual maximum number of PRBs that is allocated will be a multiple of RBGs (Resource Block Groups) that is nearest to the set value but without exceeding it.";
      yexte:takes-effect "Object unlocked";
      type erienmnrmlrat:ddt-Lrat_EUtranCellTDD_pdschMaxNrOfPrbsPerUe;
      default 100;
    }
    leaf-list arpPriorityLevelForSPIFHo {
      min-elements 16;
      max-elements 16;
      description "ARP Priority Level list used in the feature Service or Priority-Triggered Inter-Frequency Handover.\nThe first instance in the list is for ARP Priority Level 0, second for 1, and so on. Value \"false\" means the UE with this bearer is not intended to be moved to other frequency.";
      yexte:takes-effect "New connection";
      type boolean;
      default false;
      default false;
      default false;
      default false;
      default false;
      default false;
      default false;
      default false;
      default false;
      default false;
      default false;
      default false;
      default false;
      default false;
      default false;
      default false;
    }
    leaf lbabThreshTimeLow {
      description "Time period to measure RRC Connection Reject Ratio against threshold lbabThreshRejectRateLow.";
      yexte:dependencies "Only takes effect when Load-Based Access Barring is activated.";
      type erienmnrmlrat:ddt-Lrat_EUtranCellTDD_lbabThreshTimeLow;
      default 30;
    }
    leaf maxQciLatencyMeas {
      status deprecated {
        yexte:status-information "Since L16A. Planned to be removed.";
      }
      description "Largest numerical value corresponding to the lowest priority of the QCIs included into MAC latency measurements.";
      yexte:dependencies "maxQciLatencyMeas >= minQciLatencyMeas";
      type erienmnrmlrat:ddt-Lrat_EUtranCellTDD_maxQciLatencyMeas;
      default 255;
    }
    leaf prioHpueCapability {
      description "Priority of high power UE capability.";
      type erienmnrmlrat:enum-PrioHpueCapability;
      default NO_PRIORITIZATION;
    }
    leaf lbEUtranTriggerOffloadThreshold {
      description "This attribute is a threshold for eNodeB. The value applies for offload towards EUTRAN target cells. The eNodeB attempts to offload traffic from the source cell to Inter-Frequency LTE neighbors corresponding to the subscription ratio above the threshold.";
      yexte:disturbances "Changing this attribute can cause loss of traffic.";
      type erienmnrmlrat:ddt-Lrat_EUtranCellTDD_lbEUtranTriggerOffloadThreshold;
      default 100;
    }
    leaf allocTimerPucchFormat1 {
      description "A guard time. After this time, a PUCCH format 1 PRB pair is allocated if threshold allocThrPucchFormat1 is still passed.";
      type erienmnrmlrat:ddt-Lrat_EUtranCellTDD_allocTimerPucchFormat1;
      default 50;
    }
    leaf diffAdmCtrlFilteringProfRef {
      description "Reference to an instance of DiffAdmCtrlFilteringProfile MO.";
      yexte:disturbances "Changing this attribute can cause loss of traffic.";
      erienmyext:enm-type MOREF;
      type string;
    }
    leaf pdcchCovImproveDtx {
      description "PDCCH DCI format 1A for first re-transmission due to DTX of SRB and QCI1.";
      yexte:takes-effect "Cell lock/unlock";
      type boolean;
      default false;
    }
    leaf cioUpperLimitAdjBySon {
      description "Indicates the upper limit value of cellIndividualOffsetEUtran range that the SON function is allowed to adjust.";
      yexte:disturbances "Changing this attribute can stop outgoing HO.";
      type erienmnrmlrat:ddt-Lrat_EUtranCellTDD_cioUpperLimitAdjBySon;
      default 4;
    }
    leaf pdcchCovImproveSrb {
      description "PDCCH DCI format 1A is used for SRB to increase transmission success rate and to minimize interruption time.";
      yexte:takes-effect "Cell lock/unlock";
      type boolean;
      default false;
    }
    leaf-list additionalUpperLayerIndList {
      min-elements 0;
      max-elements 5;
      description "Whether upperLayerIndication is set for additional PLMN identities. Indication in additionalUpperLayerIndList[x] refers to PLMN ID in additionalPlmnList[x].\nThe upperLayerIndication is broadcast in SIB2.";
      yexte:dependencies "Must have the same length as additionalPlmnList. Valid for Baseband Radio Node only.";
      type erienmnrmlrat:enum-LayerState;
      default OFF;
      default OFF;
      default OFF;
      default OFF;
      default OFF;
    }
    leaf-list activeServiceAreaId {
      min-elements 0;
      max-elements 64;
      config false;
      description "The active MBMS Service Area Identity. The content of this attribute is either empty or has the value of the attribute MbsfnArea::serviceAreaId for one or more MbsfnArea MOs. Purpose of this attribute is to support OSS SNAD functionality. This attribute is mirrored by OSS to ExternalEUtranCellFDD/TDD.";
      yexte:dependencies "A (configured) MbsfnArea::serviceAreaId becomes Active ServiceAreaId if:\n- the MBMS Multicarrier feature is activated\n- the cell has an unreserved MBSFNAreaCellRelation to an UNLOCKED MBSFNArea\n- time and phase synchronization accuracy fulfills requirements for LTE Broadcast";
      notife:notifiable-state-data true;
      type erienmnrmlrat:ddt-Lrat_EUtranCellTDD_activeServiceAreaId;
    }
    leaf estCellCapUsableFraction {
      description "Scaling factor for the estimated cell subscription capacity. Can be used to reduce the traffic load balancing attraction of the cell. Used if traffic handling capacity of the cell is constrained by circumstances the ACCE feature is unable to capture. An example of such a circumstance is at limited UL capacity in a TDD cell.\nWhen the attribute is value is set to 0, the corresponding cell uses the value cellSubscriptionCapacity as the Cell Subscription Capacity value for the cell. This bypasses the automatically estimated Cell Subscription Capacity value for the cell.";
      yexte:disturbances "Changing this attribute can cause loss of traffic.";
      type erienmnrmlrat:ddt-Lrat_EUtranCellTDD_estCellCapUsableFraction;
      default 100;
    }
    leaf hoOptAdjThresholdAbs {
      description "The absolute threshold value for adjusted handover failure rate required to adjust handover parameters.";
      yexte:disturbances "Changing this attribute can stop outgoing HO.";
      type erienmnrmlrat:ddt-Lrat_EUtranCellTDD_hoOptAdjThresholdAbs;
      default 5;
    }
    leaf cellCapMinCellSubCap {
      description "Minimum value for the estimated cell capacity.";
      yexte:dependencies "cellCapMinCellSubCap < cellCapMaxCellSubCap";
      type erienmnrmlrat:ddt-Lrat_EUtranCellTDD_cellCapMinCellSubCap;
      default 500;
    }
    leaf lbabDecr {
      description "How fast the Access Class Barring probability is decreased, that is how fast acBarringFactor in SIB2 is increased when the cell load is decreased.";
      yexte:dependencies "Only takes effect when Load-Based Access Barring is activated.";
      type erienmnrmlrat:ddt-Lrat_EUtranCellTDD_lbabDecr;
      default 5;
    }
    leaf-list additionalPlmnAlarmSupprList {
      min-elements 0;
      max-elements 5;
      description "The list of PLMN IDs in the cell indicates if they are suppressed for alarms PLMN Service Degraded and PLMN Service Unavailable when PLMN  is not available in the cell.\nThe PLMN ID appearing in additionalPlmnList[x] is suppressed when additionalPlmnAlarmSupprList[x] is true.\nIf the configured PLMN ID is not a served PLMN ID, then the alarm is suppressed independent of the configured settings.";
      yexte:dependencies "The length of this list must be the same as the list in addtionalPlmnList.";
      type boolean;
      default false;
      default false;
      default false;
      default false;
      default false;
    }
    leaf measuredMaxNoOfUsersInCell {
      erienmyext:no-notification;
      config false;
      description "Peak number of UE in RRC_CONNECTED mode measured in the cell. This attribute will be updated during operation of the eNB and used at unlock of the cell to distribute cells to different cores in Digital Units and Baseband Units with a multicore Main Processor. If attribute expectedMaxNoOfUsersInCell is changed from -1 to zero or higher, attribute measuredMaxNoOfUsersInCell will be reset to zero and not used to control the cell distribution.";
      yexte:takes-effect "Object unlocked";
      type erienmnrmlrat:ddt-Lrat_EUtranCellTDD_measuredMaxNoOfUsersInCell;
    }
    leaf pdcchLaGinrMargin {
      description "GINR back-off parameter for PDCCH link adaptation. Applies to all UEs when the feature Enhanced PDCCH Link Adaptation is disabled. In FDD, if the licenses for both Enhanced PDCCH Link Adaptation and Carrier Aggregation are enabled, this parameter applies to secondary cell PDCCH for UEs capable of carrier aggregation. In TDD, if the license for Enhanced PDCCH Link Adaptation is enabled, this parameter applies to:\n- UEs configured with carrier aggregation, and\n- UEs configured with HARQ-ACK PUCCH format 3 or HARQ-ACK multiplexing.";
      yexte:takes-effect "Object unlocked";
      type erienmnrmlrat:ddt-Lrat_EUtranCellTDD_pdcchLaGinrMargin;
      default 100;
    }
    leaf plmn2AbConfProfileRef {
      description "Reference to an instance of PlmnAbConfProfile. Points to the PLMN Access Barring configuration profile.";
      yexte:disturbances "Changing this attribute can cause loss of traffic.";
      yexte:dependencies "References plmn1AbConfProfileRef, plmn2AbConfProfileRef and plmn3AbConfProfileRef must point to unique PlmnAbConfProfile MO instance.";
      erienmyext:enm-type MOREF;
      type string;
    }
    leaf outOfCoverageSrTimerPeriodicity {
      description "Repetition rate of UL sparse grants that are eNodeB-triggered to Out Of Coverage (OOC) UEs.";
      yexte:takes-effect "Cell lock/unlock";
      type erienmnrmlrat:ddt-Lrat_EUtranCellTDD_outOfCoverageSrTimerPeriodicity;
      default 320;
    }
    list multipleNSPmaxReqMapping {
      min-elements 0;
      max-elements 64;
      key auto-generated-struct-key;
      leaf auto-generated-struct-key {
        type uint16;
        description "This leaf has been injected to allow for struct instances in a sequence to be ordered.";
        mandatory true;
      }
      description "A list which maps frequency bands to additional Pmax value, and additional spectrum emissions as described by 3GPP TS 36.101, table 6.2.4-1. This list is used to generate the value of additionalMultipleNSPmax.";
      erienmyext:enm-type STRUCT;
      uses erienmnrmlrat:struct-MultipleNSPmaxReqMapping;
    } // end 'list multipleNSPmaxReqMapping'
    leaf lbabPeriod {
      description "Minimum time for how often the acBarringFactor in SIB2 can be changed.";
      yexte:dependencies "Only takes effect when Load-Based Access Barring is activated.";
      type erienmnrmlrat:ddt-Lrat_EUtranCellTDD_lbabPeriod;
      default 120;
    }
    leaf dlBlerTargetEnabled {
      description "Turns on/off Configurable DL BLER Target.";
      yexte:takes-effect "Next cell unlock";
      type boolean;
      default false;
    }
    leaf mfbiFreqBandIndPrio {
      description "Changes priorities of bands for Multiple Frequency Band Indicators.\nIf true:\nCell broadcasts freqBandIndicatorPriority in SIB1, and FreqBandIndicatorPriority=broadcasted is sent over X2 interface to neighbor eNB.\nPrioritized additional frequency band list (prioAdditionalFreqBandList) is broadcasted in SIB1 and is also used for handovers (including S1 and X2 handovers) instead of additionalFreqBandList.\nIf UE indicates freqBandPriorityAdjustment capability (support of freqBandIndicatorPriority), primary band has the lowest priority, otherwise primary band has the highest priority.\nmfbiFreqBandIndPrio is not used for handovers between Ericsson eNBs if ENodeBFunction::caAwareMfbiIntraCellHo = true.\nIf false:\nCell doesn't broadcast freqBandIndicatorPriority in SIB1, and FreqBandIndicatorPriority=not-broadcasted is sent over X2 interface to neighbor eNB.\nadditionalFreqBandList is broadcasted in SIB1 and is also used for handovers (including S1 and X2 handovers).\nPrimary band always has the highest priority.";
      yexte:disturbances "Changing this attribute can cause loss of traffic. X2 handover and Connection Setup for MFBI capable UE can fail during a few seconds, leading to dropped calls.";
      yexte:takes-effect "New connection";
      yexte:dependencies "Only takes effect if Multiple Frequency Band Indicators is active.";
      type boolean;
      default false;
    }
    leaf cbrsCell {
      description "CBRS cell. If cell is externally supervised and operated with authorized channel by a spectrum access system.";
      yexte:takes-effect "Next cell unlock";
      yexte:dependencies "Only takes effect in Baseband Radio Node.";
      type boolean;
      default false;
    }
    leaf upperLayerIndR15Usage {
      description "Proprietary market adaptation parameter.";
      yexte:dependencies "Valid for Baseband Radio Node only.";
      type boolean;
      default false;
    }
    leaf pdcchCfiMode {
      description "Controls the CFI (Control Format Indicator) used for the control region. cfiMode maps to CFI as described under enumerations. For DL BW of 1400 kHz, values of CFI = 1, 2 and 3 map to 2, 3, and 4 control region symbols respectively. Other BW, CFI maps directly to number of control region symbols.";
      yexte:takes-effect "Object unlocked";
      yexte:dependencies "pdcchCfiMode cannot equal CFI_STATIC_1 while dlChannelBandwidth = 1400, 3000, or 5000 kHz since there would be insufficient CCEs to transmit a PDCCH for common channel messages such as SIB1 or SI. Certain values of pdcchCfiMode that allow high CFI values may be disallowed when the combination of attributes pdcchCfiMode, dlChannelBandwidth, noOfPucchCqiUsers, and noOfPucchSrUsers require too many corresponding PUCCH HARQ-ARQ resources.";
      type erienmnrmlrat:enum-CfiMode;
      default CFI_STATIC_BY_BW;
    }
    leaf channelBandwidth {
      description "The channel bandwidth in the cell.\n";
      yexte:disturbances "Changes may affect traffic.";
      yexte:takes-effect "Object unlocked";
      type erienmnrmlrat:ddt-Lrat_EUtranCellTDD_channelBandwidth;
      default 20000;
    }
    leaf otdoaSuplActive {
      description "Indicates if the feature OTDOA Support in SUPL Environment is ACTIVATED  or DEACTIVATED in the cell.";
      yexte:takes-effect "Object unlocked.";
      type boolean;
      default false;
    }
    leaf hoOptAdjThresholdAbsQci1 {
      description "Absolute threshold for adjusted handover failure rate required to adjust cellIndividualOffsetEUtranQci1.";
      yexte:disturbances "Changing this attribute can stop outgoing HO.";
      type erienmnrmlrat:ddt-Lrat_EUtranCellTDD_hoOptAdjThresholdAbsQci1;
      default 5;
    }
    leaf lbabThreshRejectRateLow {
      description "RRC Connection Reject Ratio threshold below which Load-Based Access Barring decreases access class barring probability or Progressive Access Barring, or PLMN-Specific Access Barring recedes to lower priority.";
      yexte:dependencies "Only takes effect when Load-Based Access Barring is activated.";
      type erienmnrmlrat:ddt-Lrat_EUtranCellTDD_lbabThreshRejectRateLow;
      default 20;
    }
    leaf adaptiveCfiHoProhibit {
      description "Controls adaptive CFI to avoid using CFI=1 or CFI=1,2, when scheduling UEs that are in handover. The highest CFI value in available CFI values determined by pdcchCfiMode is not prohibited.";
      yexte:takes-effect "Cell lock/unlock";
      yexte:dependencies "Applicable only when attribute pdcchCfiMode is set to CFI_AUTO_MAXIMUM_2 or CFI_AUTO_MAXIMUM_3.";
      type erienmnrmlrat:enum-AdaptiveCfiHoProhibitMode;
      default NO_HO_PROHIBIT_CFI;
    }
    leaf lbEUtranAcceptOffloadThreshold {
      description "This attribute is a threshold for eNodeB. The value applies in the target cell for incoming offload. The eNodeB accepts incoming offload traffic in the target cell as long as the subscription ratio is below the threshold.";
      yexte:disturbances "Changing this attribute can cause loss of traffic.";
      type erienmnrmlrat:ddt-Lrat_EUtranCellTDD_lbEUtranAcceptOffloadThreshold;
      default 50;
    }
    list spectrumEmissionReqMapping {
      min-elements 0;
      max-elements 64;
      key auto-generated-struct-key;
      leaf auto-generated-struct-key {
        type uint16;
        description "This leaf has been injected to allow for struct instances in a sequence to be ordered.";
        mandatory true;
      }
      description "A list which maps frequency bands to network signaling values specifying additional spectrum emissions, as described by 3GPP TS 36.101, table 6.2.4-1. A band which is not explicitly mapped to a network signaling value by this list, will use the value NS_01. This list is used to generate the value of additionalSpectrumEmissionValues.";
      erienmyext:enm-type STRUCT;
      uses erienmnrmlrat:struct-SpectrumEmissionReqMapping;
    } // end 'list spectrumEmissionReqMapping'
    leaf ulMaxMuMimoLayers {
      description "Enables uplink multiuser MIMO at cell level. The value corresponds to the maximum number of co-scheduled layers that is allowed. Only single user MIMO is allowed when the value is zero.";
      yexte:takes-effect "Next cell unlock";
      yexte:dependencies "Only takes effect if the cell is operating with an AAS radio.";
      type erienmnrmlrat:ddt-Lrat_EUtranCellTDD_ulMaxMuMimoLayers;
      default 0;
    }
    leaf dlPowerState {
      config false;
      description "State of downlink output power.";
      notife:notifiable-state-data true;
      type erienmnrmlrat:enum-DlPowerState;
    }
    leaf commonSrPeriodicity {
      description "Common SR periodicity, used for all UEs.";
      yexte:takes-effect "Cell lock/unlock";
      yexte:dependencies "For 1.4 MHz: Only valid inputs are 10 and 20.";
      type erienmnrmlrat:ddt-Lrat_EUtranCellTDD_commonSrPeriodicity;
      default 20;
    }
    leaf tm8ModeSwitchingEnabled {
      description "Enables dynamic switching between TM8 and TM3.";
      yexte:dependencies "Only takes effect if radio equipment supports AAS functionality.";
      type boolean;
      default false;
    }
    leaf orientMajorAxis {
      description "Orientation of the major axis of uncertainty, in degrees clockwise from north.  Orientation value (N) is derived by the formula:\nN <= X < (N + 1)\nwhere X is the orientation in degrees (0 - 180).";
      yexte:dependencies None;
      type erienmnrmlrat:ddt-Lrat_EUtranCellTDD_orientMajorAxis;
      default 0;
    }
    leaf ulDynUeAdmCtrlOverloadThr {
      description "Highest allowed UL radio resource utilization ratio for admission of a non-privileged UE. Applies to each UL resource considered by Dynamic UE Admission Control. Resource utilization is checked against this threshold for all new, re-established, or incoming handover RRC connections.";
      yexte:disturbances "Changing this attribute can affect the following:\n- the number of RRC-connected users\n- cell throughput and the number of rejected non-privileged RRC connection requests       - rejected non-privileged RRC connection re-establishment requests and rejected\n  non- privileged incoming handover requests.";
      yexte:dependencies "ulDynUeAdmCtrlOverloadThr >= ulDynUeAdmCtrlRetDiffThr";
      type erienmnrmlrat:ddt-Lrat_EUtranCellTDD_ulDynUeAdmCtrlOverloadThr;
      default 600;
    }
    leaf ul64qamEnabled {
      description "Enables UL 64-QAM at cell level.";
      yexte:takes-effect "Cell lock/unlock";
      yexte:dependencies "Only relevant if the license for UL 64-QAM is present and the\nfeature is active.";
      type boolean;
      default true;
    }
    leaf lessPrbUsageThreshold {
      description "Maximum downlink PRB usage that scheduling stays on-hold for Low Energy Scheduler Solution.";
      type erienmnrmlrat:ddt-Lrat_EUtranCellTDD_lessPrbUsageThreshold;
      default 90;
    }
    leaf-list includeLcgInMacUeThp {
      min-elements 4;
      max-elements 4;
      description "Controls the LCGs that are included in pmMacUeThpVolUl, pmMacUeThpTimeUl, and pmMacUeThpUlDistr. To include the n:th LCG, set includeLcgInMacUeThp[n]=true.\n";
      type boolean;
      default false;
      default false;
      default true;
      default true;
    }
    list endcAllowedPlmnList {
      min-elements 0;
      max-elements 6;
      key auto-generated-struct-key;
      leaf auto-generated-struct-key {
        type uint16;
        description "This leaf has been injected to allow for struct instances in a sequence to be ordered.";
        mandatory true;
      }
      description "PLMN ID allowed to use EN-DC. If empty, EN-DC not allowed in cell.\n";
      erienmyext:enm-type STRUCT;
      uses erienmnrmlrat:struct-PlmnIdentity;
    } // end 'list endcAllowedPlmnList'
    leaf eranUlCompUserSelSinrHys {
      description "Hysteresis of SINR threshold for Elastic RAN UL CoMP user selection.";
      yexte:dependencies "Must be used together with eranUlCompUserSelSinrThr.";
      type erienmnrmlrat:ddt-Lrat_EUtranCellTDD_eranUlCompUserSelSinrHys;
      default 10;
    }
    leaf hostingDigitalUnit {
      config false;
      description "Shows the DU or Baseband on which baseband processing for the cell is located";
      notife:notifiable-state-data true;
      erienmyext:enm-type MOREF;
      type string;
    }
    leaf initCdma2000SysTimeType {
      description "Intended type of CDMA2000 system time to broadcast in SIB8, if applicable.";
      type erienmnrmlrat:enum-Cdma2000SysTimeVals;
      default NONE;
    }
    leaf-list cellResourceRef {
      min-elements 0;
      max-elements 6;
      status deprecated {
        yexte:status-information "Since 18.Q2. Has no functional behavior. Planned to be removed.";
      }
      description "References to an instance of CellResource MO.";
      yexte:takes-effect "Next cell unlock";
      yexte:dependencies "CellResource MO having non empty plmnList and CellResource MO having non empty spidList shouldn't be referred together(CellResource MO having empty plmnList and empty spidList is considered as configuring spidList(non empty spidList)). Duplication of PLMN or SPID within referred CellResouce MOs is not allowed.";
      erienmyext:enm-type MOREF;
      type string;
    }
    leaf measCellGroupCellRef {
      description "References to an instance of MeasCellGroup MO for grouping on a cell basis.";
      yexte:dependencies "MeasCellGroup with 0 groupId can not be referred.\nOnly MeasCellGroup having empty spidList and empty plmnList can be referred.";
      erienmyext:enm-type MOREF;
      type string;
    }
    leaf servOrPrioRedirectEnabled {
      description "Indicates if release with redirection is allowed in the feature Service or Priority-Triggered Inter-Frequency Handover.";
      yexte:takes-effect "New connection";
      type boolean;
      default true;
    }
    leaf dl256QamEnabled {
      description "Enable or disable 256 QAM support in DL.";
      yexte:takes-effect "Cell lock/unlock";
      type boolean;
      default true;
    }
    leaf ailgRef {
      description "Refers to an instance of AirIfLoadProfile. Assigns a AirIfLoadProfile to a cell.";
      erienmyext:enm-type MOREF;
      type string;
    }
    leaf elcLongDrxCycle {
      description "Long DRX cycle for ELC. Value of elcLongDrxCycle is in number of sub-frames.";
      yexte:takes-effect "New connection";
      yexte:dependencies "Feature Ericsson Lean Carrier is present active.";
      type erienmnrmlrat:enum-ElcLongDrxCycle;
      default SF40;
    }
    leaf resourcePartitionGroupRef {
      description "Reference to an instance of ResourcePartitionGroup MO.";
      yexte:disturbances "Changing this attribute can affect traffic.";
      yexte:takes-effect "Cell lock/unlock";
      erienmyext:enm-type MOREF;
      type string;
    }
    leaf dl256QamStatus {
      erienmyext:no-notification;
      config false;
      description "Indication if 256 QAM in DL is supported in the cell.";
      type erienmnrmlrat:enum-Dl256QamSupport;
    }
    leaf crsGain {
      description "Sets the DL power of the Cell specific Reference Signal (CRS) relatively a reference level defined by the power of the PDSCH type A resource elements. If crsGain is +3dB, the CRS power is 3dB higher than that of a PDSCH type A resource element.\nThe settings crsGain=4.77db and 6dB are mapped to 3dB. These settings are not supported.\nPDSCH type A resource elements are located in symbols that do not contain CRS.";
      yexte:takes-effect "Cell lock/unlock";
      yexte:dependencies "The crsGain only takes effect if the configured number of antenna ports used in a sector is 2, 4, or 8.  In the one port case, crsGain is hardcoded to 0dB.";
      type erienmnrmlrat:ddt-Lrat_EUtranCellTDD_crsGain;
      default 0;
    }
    leaf measBasedElcControl {
      description "Enables or disables measurement-based Ericsson Lean Carrier Control.";
      yexte:takes-effect "New connection";
      yexte:dependencies "Only relevant if license Ericsson Lean Carrier is present and feature is active.";
      type boolean;
      default false;
    }
    leaf prachFrequencyAllocation {
      description "Controls allocation of PRACH to upper or lower part of band.\nFor example, it can be used for avoiding interfered part of band.\n0: Allocate PRACH from lower part of band.\n1: Allocate PRACH from upper part of band.";
      yexte:takes-effect "Next cell unlock";
      type erienmnrmlrat:ddt-Lrat_EUtranCellTDD_prachFrequencyAllocation;
      default 0;
    }
    leaf pZeroNominalPusch {
      description "The nominal component of the UE transmit power for Physical Uplink Shared Channel (PUSCH).";
      yexte:disturbances "Changes may affect traffic.";
      yexte:dependencies "Changing the value of pZeroNominalPusch, might have impact on the setting of puschPwrOffset64Qam.\nSee puschPwrOffset64Qam for how that attribute depends on pZeroNominalPusch.";
      type erienmnrmlrat:ddt-Lrat_EUtranCellTDD_pZeroNominalPusch;
      default -103;
    }
    leaf acBarringSkipForSms {
      description "Indicates whether or not access attempts for SMS over SGs or SMS over IP from UEs are to skip Access Class Barring functionality.";
      yexte:disturbances "Changing this attribute can block sms.";
      type boolean;
      default false;
    }
    list eutranCellPolygon {
      min-elements 0;
      max-elements 15;
      key auto-generated-struct-key;
      leaf auto-generated-struct-key {
        type uint16;
        description "This leaf has been injected to allow for struct instances in a sequence to be ordered.";
        mandatory true;
      }
      description "Models the manageable characteristics for the cell polygon used for UE positioning. Each polygon corner is described by a latitude and longitude pair. Each polygon corner is represented with one position in the sequence. The other configured polygon corners follow in sequence. There must at least be three corners configured in a polygon when the function is active/used. The points shall be connected in the order that they are given. The last point is connected to the first point.";
      erienmyext:enm-type STRUCT;
      uses erienmnrmlrat:struct-EutranCellCorner;
    } // end 'list eutranCellPolygon'
    leaf noOfPucchFormat2PrbPairsPerFrame {
      erienmyext:no-notification;
      config false;
      description "PRB usage for PUCCH Format2. Based on PUCCH CQI user configuration.";
      type erienmnrmlrat:ddt-Lrat_EUtranCellTDD_noOfPucchFormat2PrbPairsPerFrame;
    }
    leaf covTriggerdBlindHoAllowedBr {
      description "Enables blind handover initiation when CAT-M UE reports bad coverage.\nEven if value is true, eNodeB only initiates blind handover if it finds suitable cell.";
      yexte:takes-effect "New connection";
      type boolean;
      default true;
    }
    leaf latencyLongThreshold {
      description "Signaling latency threshold.\nDynamic Load Control considers procedure latency as long, if above latencyLongThreshold.";
      yexte:takes-effect "Next cell unlock";
      yexte:dependencies "Applicable only when serviceState = OPERABLE for Dynamic Load Control.";
      type erienmnrmlrat:ddt-Lrat_EUtranCellTDD_latencyLongThreshold;
      default 135;
    }
    leaf hpueCaSwitchTimeToTrigger {
      description "Time-to-trigger value for UL measurement in switching between High Power UE to Carrier Aggregation.";
      type erienmnrmlrat:ddt-Lrat_EUtranCellTDD_hpueCaSwitchTimeToTrigger;
      default 40;
    }
    leaf idleModePrioAtReleaseRef {
      description "Reference to an IdleModePrioAtRelease MO. Assigns an IdleModePrioAtRelease to a cell.";
      yexte:disturbances "Changing this attribute can affect traffic.";
      erienmyext:enm-type MOREF;
      type string;
    }
    container changeNotification {
      description "For each System Information Block (SIB), indicates when the SIB content is changed, if system information change notification is broadcast prior to broadcast of updated system information.";
      erienmyext:enm-type STRUCT;
      uses erienmnrmlrat:struct-ChangeNotificationSIBs;
    } // end 'container changeNotification'
    leaf tac {
      description "Tracking Area Code for the EUtran Cell.";
      mandatory true;
      yexte:disturbances "Changes may affect traffic";
      type erienmnrmlrat:ddt-Lrat_EUtranCellTDD_tac;
    }
    leaf ns05PathlossOffsetThres {
      description "Value of threshold to detect if the NS_05 UE is in repeater zone. If the NS_05 UE's pathloss measured on low band is bigger than or equal to the value of other band plus ns05PathlossOffsetThres, the NS_05 UE is detected as in repeater zone.";
      yexte:dependencies "Only takes effect if:\n- license for NS 05 Additional Maximum Power Reduction Support is present and the feature is active, and\n- attribute networkSignallingValue in MOC EUtranCellFDD/TDD is NS_05, and\n- attribute ns05LowBandSchedMode is ADAPTIVE_AVAILABLE_BY_REPEATER_DETECTION.";
      type erienmnrmlrat:ddt-Lrat_EUtranCellTDD_ns05PathlossOffsetThres;
      default 50;
    }
    leaf minBestCellHoAttempts {
      description "Number of attempts for handover to a cell better than the serving cell, before handover is attempted to the next best cell. If there is no next best cell in the UE report, handover to the best cell is attempted repeatedly.";
      type erienmnrmlrat:ddt-Lrat_EUtranCellTDD_minBestCellHoAttempts;
      default 1;
    }
    leaf noConsecutiveSubframes {
      description "The number of consecutive downlink sub-frames with positioning reference signals as defined in 3GPP TS 36.211. Values define 1, 2, 4, or 6 consecutive sub-frames.";
      yexte:takes-effect "Object unlocked";
      yexte:dependencies None;
      type erienmnrmlrat:enum-NoOfSubframesVals;
      default SF1;
    }
    leaf-list serviceAreaId {
      min-elements 0;
      max-elements 64;
      status deprecated {
        yexte:status-information "Since L16B. Replaced by MbsfnArea::serviceAreaId. Planned to be removed.";
      }
      description "The MBMS Service Area Identity.";
      yexte:dependencies "At least one defined serviceAreaId needs to be configured in the eNB to ENABLE a TermPointToMmeM3";
      type erienmnrmlrat:ddt-Lrat_EUtranCellTDD_serviceAreaId;
    }
    leaf longitude {
      description "The degree of longitude of the transmitter antenna position.\nIn case of Combined Cell (multi-sector cell):\n   For indoor system, antenna of any sector.\n   For outdoor system,antenna of macro sector.";
      type erienmnrmlrat:ddt-Lrat_EUtranCellTDD_longitude;
      default 0;
    }
    leaf clusteredPuschMprFactor {
      description "Multiplication factor applied to the 3GPP-defined Maximum Power Reduction values for Clustered PUSCH. Low settings imply high usage of Clustered PUSCH, high settings imply the opposite.";
      yexte:takes-effect "Object unlocked";
      type erienmnrmlrat:ddt-Lrat_EUtranCellTDD_clusteredPuschMprFactor;
      default 100;
    }
    leaf pdcchOuterLoopUpStepVolte {
      description "PDCCH outer loop up step size for UEs with any bearer mapped to a QCI with serviceType of VoIP. In TDD, this parameter applies only to UEs which are configured with HARQ-ACK bundling.";
      yexte:takes-effect "Object unlocked";
      type erienmnrmlrat:ddt-Lrat_EUtranCellTDD_pdcchOuterLoopUpStepVolte;
      default 6;
    }
    leaf srvccDelayTimer {
      description "The length of time the eNodeB delays Single Radio Voice Call Continuity (SRVCC) handover.\nValue 0 means no delay.";
      yexte:takes-effect "New connection";
      type erienmnrmlrat:ddt-Lrat_EUtranCellTDD_srvccDelayTimer;
      default 0;
    }
    leaf hoOptStatNumQci1 {
      description "Minimal number of handovers required by AMO function before adjusting cellIndividualOffsetEUtranQci1.";
      type erienmnrmlrat:ddt-Lrat_EUtranCellTDD_hoOptStatNumQci1;
      default 200;
    }
    leaf nonCaAnModeMuxEnable {
      description "Enables multiplexing as DL HARQ ACK/NACK feedback mode for TDD UEs not configured for carrier aggregation.";
      yexte:takes-effect "New connection";
      type boolean;
      default false;
    }
    leaf minQciLatencyMeas {
      status deprecated {
        yexte:status-information "Since L16A. Planned to be removed.";
      }
      description "Smallest numerical value corresponding to the highest priority of the QCIs included into MAC latency measurements.";
      yexte:dependencies "minQciLatencyMeas  =< maxQciLatencyMeas";
      type erienmnrmlrat:ddt-Lrat_EUtranCellTDD_minQciLatencyMeas;
      default 5;
    }
    leaf lbTpNonQualFraction {
      description "The fraction of non-qualified UEs at UE selection for throughput aware load balancing. In case throughput aware UE selection is enabled, this parameter sets a target size for the fraction of UE to be disqualified for load balancing due to insufficient relative gain when moving UE from source to target cell.\nSpecial value 0 means that the throughput aware UE selection for this cell is disabled.";
      type erienmnrmlrat:ddt-Lrat_EUtranCellTDD_lbTpNonQualFraction;
      default 35;
    }
    list pciDetectingCell {
      min-elements 0;
      max-elements 5;
      key auto-generated-struct-key;
      leaf auto-generated-struct-key {
        type uint16;
        description "This leaf has been injected to allow for struct instances in a sequence to be ordered.";
        mandatory true;
      }
      description "Indicates the CGI of the cell that detected the PCI collision/confusion. This value is only valid if the corresponding attribute pciConflict is \"YES\" or \"YES_CONFLICTING_CELL\". The first cell in the pciDetectingCell list corresponds to the first cell in the pciConflictCell list and the first value of pciConflict. The second cell in the pciDetectingCell list corresponds to the second cell in the pciConflictCell list and the first value of pciConflict.";
      erienmyext:enm-type STRUCT;
      uses erienmnrmlrat:struct-Cgi;
    } // end 'list pciDetectingCell'
    container frameStartOffset {
      description "The frame start offset of the cell. All TDD cells in the same frequency band, or specific frequency band combinations where one frequency band overlaps with another (e.g. Band 38 and Band 41) must have the same frame start offset.";
      erienmyext:enm-type STRUCT;
      uses erienmnrmlrat:struct-FrameStartOffsetTDD;
    } // end 'container frameStartOffset'
    leaf pdcchPowerBoostMax {
      description "Maximum power boost applied to UE-specific PDCCHs that require more CCEs than the maximum available CCE aggregation level. If UE-specific PDCCHs  require equal or less, an automatic power boost algorithm is applied. Attribute pdcchPowerBoostMax does not affect those PDCCHs.\nIf set to 0, there is no PDCCH power boost of the maximum CCE aggregation level. PDCCH coverage is not increased but the feature still optimizes the PDCCH power setting for PDCCHs that require equal or less CCEs than the maximum CCE aggregation level. This still allows for higher PDCCH capacity.";
      yexte:takes-effect "Cell lock/unlock";
      type erienmnrmlrat:ddt-Lrat_EUtranCellTDD_pdcchPowerBoostMax;
      default 0;
    }
    leaf prsConfigIndexMapped {
      config false;
      description "This parameter holds the resulting prsConfigIndex value. If prsPeriod is used by the operator then prsConfigIndexMapped will be set by the system. If prsConfigIndex is used by the operator then prsConfigIndexMapped will be a copy of the entered value.";
      notife:notifiable-state-data true;
      type erienmnrmlrat:ddt-Lrat_EUtranCellTDD_prsConfigIndexMapped;
    }
    leaf qQualMinOffset {
      description "The offset applied to the signaled qQualMin.\nCorresponds to Qqualminoffset in TS 36.304.\nValue 0 means that it is not sent in SIB1 and UE applies in such case the (default) value of 0 dB for Qqualminoffset.";
      yexte:dependencies "If the value of qQualMin is set to 0 the parameter qQualMinOffset will not be broadcasted.";
      type erienmnrmlrat:ddt-Lrat_EUtranCellTDD_qQualMinOffset;
      default 0;
    }
    leaf servOrPrioTriggeredIFHo {
      description "Specifies the trigger used in the feature Service or Priority-Triggered Inter-Frequency Handover.";
      yexte:takes-effect "New connection";
      type erienmnrmlrat:enum-ServOrPrioTriggeredIFHoType;
      default QCI;
    }
    leaf networkSignallingValue {
      description "Enables additional spectrum emission requirements according to 3GPP TS 36.101, table 6.2.4-1.";
      yexte:takes-effect "Object disabled/enabled";
      type erienmnrmlrat:enum-NetworkSignallingValue;
      default NS_01;
    }
    leaf qQualMinRsrqCe {
      description "Min quality level (RSRQ) in cell for UE in enhanced coverage mode.\nCorresponds to Qqualmin_CE in TS 36.304, sent in SIB1-BR. If 0, it is not sent and UE applies default value of negative infinity for Qqualmin_CE.";
      type erienmnrmlrat:ddt-Lrat_EUtranCellTDD_qQualMinRsrqCe;
      default 0;
    }
    leaf highBasebandPriority {
      description "Cell prioritization status for Baseband resources. Cells set to true get Baseband resources before cells set to false.";
      yexte:takes-effect "Next cell unlock";
      yexte:dependencies "Only has effect if Baseband Resource Cell Prioritization is enabled.";
      type boolean;
      default false;
    }
    leaf-list additionalFreqBandList {
      min-elements 0;
      max-elements 8;
      config false;
      description "A list of additional frequency bands the cell belongs to, not including the frequency band indicated by the EARFCN value of the cell (primary frequency band). The list is automatically set by the eNB. These additional frequency bands are broadcasted to the UEs in SystemInformationBlockType1 in case the feature Multiple Frequency Band Indicators is enabled in the cell.";
      notife:notifiable-state-data true;
      type erienmnrmlrat:ddt-Lrat_EUtranCellTDD_additionalFreqBandList;
    }
    leaf lastSchedLinkAdaptEnabled {
      description "Controls if link adaptation function allocates largest possible resource to last scheduled UE in the DL. Used to improve UE decoding success rate with reduced code rate.";
      yexte:takes-effect "Cell lock/unlock";
      type boolean;
      default true;
    }
    leaf ulConfigurableFrequencyStart {
      description "Specifies the start frequency offset for the allocation of resources when the uplink interference management is disabled expressed as a percentage of the configured bandwidth.";
      yexte:takes-effect "Object unlocked";
      yexte:dependencies "ulInterferenceManagementActive shall be disabled before this parameter takes effect.";
      type erienmnrmlrat:ddt-Lrat_EUtranCellTDD_ulConfigurableFrequencyStart;
      default 0;
    }
    leaf ssacBarringForMMTELVoicePresent {
      status deprecated {
        yexte:status-information "Since 17.Q3. Replaced by AcBarringPresence.acBarringForMmtelVoicePresence in EUtranCellFDD/EUtranCellTDD::acBarringPresence. Planned to be removed.";
      }
      description "Specifies presence of Information Element ssac-BarringForMMTEL-Voice-r9 in SIB2.";
      yexte:disturbances "Changing this attribute can block VoLTE calls in the cell.";
      type boolean;
      default false;
    }
    leaf ulFrequencyAllocationProportion {
      description "Specifies the amount of frequency resources that is allocated in UL expressed as a percentage of the configured bandwidth.";
      yexte:takes-effect "Object unlocked";
      type erienmnrmlrat:ddt-Lrat_EUtranCellTDD_ulFrequencyAllocationProportion;
      default 100;
    }
    leaf highSpeedUEActive {
      description "Indicates if the feature High Speed UE is activated in the cell";
      yexte:takes-effect "Object unlocked";
      type boolean;
      default false;
    }
    leaf pdcchAdmThreshold {
      status deprecated {
        yexte:status-information "Since L16A. Has no functional behavior. Planned to be removed.";
      }
      description "Sets the threshold for the CCE usage when ue starts to be rejected. This will only cause real rejects if pdcchAdmEnabled = true. Otherwise we will only step pmCellAdmControlPdcchRejMeas both no rejects will take place.";
      yexte:takes-effect "Cell lock/unlock";
      type erienmnrmlrat:ddt-Lrat_EUtranCellTDD_pdcchAdmThreshold;
      default 1000;
    }
    leaf catm1SupportEnabled {
      status deprecated {
        yexte:status-information "Since L17A. Planned to be removed.";
      }
      description "Whether or not support for Category M device is enabled in the cell.\nNote: Feature is optional and under license control.";
      yexte:takes-effect "Cell lock/unlock";
      type boolean;
      default false;
    }
    leaf iuaInterval {
      status deprecated {
        yexte:status-information "Since 18.Q3. Replaced by InstantUplinkAccess::iuaInterval. Planned to be removed.";
      }
      description "Time interval between UL short-SPS (semi-persistent scheduling) instances. Value 0 means load based selection of IUA interval.";
      yexte:dependencies "In MO EUtranCellFDD, only values 0,1,2,4 are allowed. In MO EUtranCellTDD, only values 0,1,5 are allowed.";
      type erienmnrmlrat:ddt-Lrat_EUtranCellTDD_iuaInterval;
      default 1;
    }
    leaf altitude {
      description "Transmitter antenna altitude (meters). Use +/- values to denote height/depth.\nIn case of Combined Cell (multi-sector cell):\nFor indoor system, antenna of any sector.\nFor outdoor system, antenna of macro sector.";
      type erienmnrmlrat:ddt-Lrat_EUtranCellTDD_altitude;
      default 0;
    }
    leaf-list measCellGroupUeRef {
      min-elements 0;
      max-elements 6;
      description "Reference to a list of MeasCellGroup MOs for grouping on UE basis. Referenced Mos include measurements on differentiated UEs into a measurement group.";
      yexte:dependencies "MeasCellGroup with 0 groupId can not be referred.\nMeasCellGroup with empty spidList and empty plmnList can not be referred.\nMeasCellGroup with non-empty plmnList and MeasCellGroup having non null spidList can not be referred together.\nDuplication of plmn or spid within referred MeasCellGroups is not allowed.";
      erienmyext:enm-type MOREF;
      type string;
    }
    container systemInformationBlock7 {
      description "Contains cell re-selection information common for cell re-selection towards GERAN.\n";
      erienmyext:enm-type STRUCT;
      uses erienmnrmlrat:struct-SIB7;
    } // end 'container systemInformationBlock7'
    leaf prescheduling {
      description "Whether or not prescheduling is enabled.";
      type boolean;
      default true;
    }
    container systemInformationBlock6 {
      description "Contains cell re-selection information common for cell re-selection towards UTRAN.\n";
      erienmyext:enm-type STRUCT;
      uses erienmnrmlrat:struct-SIB6;
    } // end 'container systemInformationBlock6'
    leaf pdcchCovImproveQci1 {
      description "PDCCH DCI format 1A to increase MOS for QCI1 in high interference or high path loss scenarios.";
      yexte:takes-effect "Cell lock/unlock";
      type boolean;
      default false;
    }
    leaf enableDrxAwareRlcArq {
      description "Enables function to automatically adapt t-PollretransmitTimer to the time it takes to complete HARQ procedure + harqOffset (UL and DL).";
      yexte:takes-effect "New connection";
      type boolean;
      default false;
    }
    container systemInformationBlock3 {
      description "Contains cell re-selection information common for intra-frequency, inter-frequency and/ or inter-RAT cell re-selection.\n";
      erienmyext:enm-type STRUCT;
      uses erienmnrmlrat:struct-SIB3;
    } // end 'container systemInformationBlock3'
    leaf transmissionMode {
      description "Defines the Transmission Mode (e.g. Transmit Diversity and Closed-Loop Spatial Multiplexing) that shall be used for the UEs that are connected to the cell.\nSee 3GPP TS 36.213 table 7.1-5 for a definition of Transmission Mode.";
      type erienmnrmlrat:enum-TransmissionMode;
      default TRANSMISSION_MODE_3;
    }
    leaf nonCaF3ResCollisionThresh {
      description "Upper percentage threshold for PUCCH format 3 resource collision rate. Limits number of TDD non-carrier aggregation UEs configured with PUCCH format 3 as HARQ feedback mode.";
      yexte:takes-effect "New connection";
      type erienmnrmlrat:ddt-Lrat_EUtranCellTDD_nonCaF3ResCollisionThresh;
      default 20;
    }
    leaf iuaEnabled {
      status deprecated {
        yexte:status-information "Since 18.Q3. Replaced by InstantUplinkAccess::iuaEnabled. Planned to be removed.";
      }
      description "Enables Instant Uplink Access (IUA) for a cell.";
      type boolean;
      default false;
    }
    container systemInformationBlock8 {
      description "Contains cell re-selection information common for cell re-selection towards CDMA2000. This is controlled by the licensing MO Cdma2000SessionContinuity. The SIB8 distribution and information are also controlled by other licenses.";
      erienmyext:enm-type STRUCT;
      uses erienmnrmlrat:struct-SIB8;
    } // end 'container systemInformationBlock8'
    leaf dlPowerRampUpInitRatio {
      description "Initial ratio for downlink output power to start power ramp up.\nValue 100 indicates full cell coverage.";
      yexte:takes-effect "Cell lock/unlock";
      type erienmnrmlrat:ddt-Lrat_EUtranCellTDD_dlPowerRampUpInitRatio;
      default 100;
    }
    leaf noOfChannelSelectionSets {
      description "The number of channel selection PUCCH resource sets (CS sets) to reserve in each cell for secondary cell HARQ feedback. To conserve PUCCH resource, this attribute can be set to 0 if the cell is not used as PCell for Carrier Aggregation.";
      yexte:takes-effect "Cell lock/unlock";
      type erienmnrmlrat:ddt-Lrat_EUtranCellTDD_noOfChannelSelectionSets;
      default 6;
    }
    leaf useBandPrioritiesInSib1 {
      status deprecated {
        yexte:status-information "Since 18.Q4. Replaced by mfbiFreqBandIndPrio. Planned to be removed.";
      }
      description "If enabled, prioritized additional frequency band list is broadcast in SIB1 according to priorities set in EUtranCellFDD::prioAdditionalFreqBandList or in EUtranCellTDD::prioAdditionalFreqBandList. The priorities must be valid.\nIf disabled, EUtranCellFDD::additionalFreqBandList or EUtranCellTDD::additionalFreqBandList is used.";
      yexte:takes-effect "New connection";
      yexte:precondition "eNodeB must support Multiple Frequency Band Indicators feature.";
      type boolean;
      default false;
    }
    leaf nonCaHarqAnModeMuxThresh {
      description "Upper threshold for number of active DL users. Limits number of TDD non-carrier aggregation UEs configured with multiplexing as HARQ feedback mode.";
      yexte:takes-effect "New connection";
      type erienmnrmlrat:ddt-Lrat_EUtranCellTDD_nonCaHarqAnModeMuxThresh;
      default 2;
    }
    leaf mobCtrlAtPoorCovActive {
      description "Specifies if the feature Mobility Control at Poor Coverage is enabled or disabled in the cell.";
      yexte:takes-effect "New connection";
      type boolean;
      default false;
    }
    leaf interEnbUlCompUserSelSinrThr {
      description "SINR threshold for inter-eNodeB UL CoMP user selection.";
      yexte:disturbances "If changed, system performance can be affected. As values go higher, more candidates are selected for Inter-eNodeB Uplink CoMP, but more user measurements are triggered. This impacts MP load and transport load over X2.";
      yexte:dependencies "Must be used together with interEnbUlCompUserSelSinrHys.";
      type erienmnrmlrat:ddt-Lrat_EUtranCellTDD_interEnbUlCompUserSelSinrThr;
      default 100;
    }
    leaf ulTxPsdDistrThr {
      description "Threshold for % of PRBs with \"UL Tx power per PRB >= ulPsdLoadThresholdSinrClpc\" during measSinrClpcPeriod. Below threshold means low cell power load and then SINR based UL closed-loop power control can be considered.";
      yexte:dependencies "Attribute enableSinrUplinkClpc must be true.";
      type erienmnrmlrat:ddt-Lrat_EUtranCellTDD_ulTxPsdDistrThr;
      default 40;
    }
    leaf ulSchedCtrlForOocUesEnabled {
      description "Enables feature UL Scheduling Control for Out Of Coverage (OOC) UEs.";
      yexte:takes-effect "Cell lock/unlock";
      type boolean;
      default true;
    }
    leaf qRxLevMin {
      description "The required minimum received Reference Symbol Received Power (RSRP) level in the E-UTRA frequency for cell reselection. Corresponds to parameter Qrxlevmin in 3GPP TS 36.304. This attribute is broadcast in SIB1.";
      type erienmnrmlrat:ddt-Lrat_EUtranCellTDD_qRxLevMin;
      default -140;
    }
    leaf earfcn {
      yexte:restricted;
      description "The E-UTRA Absolute Radio Frequency Channel Number (EARFCN) for the TDD cell. The mapping from EARFCN to physical frequency is for E-UTRA bands is described in 3GPP TS 36.104. The values depend on national, operator specific frequency allocation, as well as from the supported frequency band(s) of the equipment in the RBS.\nUse MO action changeFrequency for changing the frequency after that cell is initially setup. See description of changeFrequency, on how change takes effect and disturbances.";
      mandatory true;
      yexte:disturbances "Changes may affect traffic.";
      yexte:takes-effect "Object unlocked";
      type erienmnrmlrat:ddt-Lrat_EUtranCellTDD_earfcn;
    }
    container acBarringForCsfb {
      description "Access class barring parameters for mobile originating CSFB calls.\nThe information is broadcasted in SIB2.";
      erienmyext:enm-type STRUCT;
      uses erienmnrmlrat:struct-AcBarringConfig;
    } // end 'container acBarringForCsfb'
    leaf voiceMeasAccEnabled {
      status deprecated {
        yexte:status-information "Since 18.Q2. Has no functional behavior. Planned to be removed.";
      }
      description "Enables voice IRAT measurement acceleration in the cell.";
      yexte:takes-effect "New connection";
      yexte:dependencies "Only relevant if mobCtrlAtPoorCovActive is set to true.";
      type boolean;
      default false;
    }
    leaf acBarringSkipForMmtelVoice {
      description "Indicates whether or not access attempts for MMTEL voice from UEs are to skip Access Class Barring functionality.";
      yexte:disturbances "Changing this attribute can block VoLTE calls.";
      type boolean;
      default false;
    }
    leaf csiRsConfigType8TxTDD {
      description "This attribute specifies configuration type of CSI-RS (Channel State Information Reference Signal) for TDD 8Tx.";
      yexte:takes-effect "Cell lock/unlock";
      type erienmnrmlrat:enum-CsiRsConfigType8TxTDD;
      default NZP_CSIRS_TDD;
    }
    leaf confidence {
      description "Percentage of confidence that the target device is within the ellipsoid defined by the three axes of uncertainty: semi-major, semi-minor, and altitude.";
      yexte:dependencies None;
      type erienmnrmlrat:ddt-Lrat_EUtranCellTDD_confidence;
      default 100;
    }
    leaf loadBasedBarringFactor {
      config false;
      description "Current barring factor based on LBAB algorithm or PAB algorithm.";
      yexte:dependencies "Only takes effect when feature Load-Based Access Barring or feature Progressive Access Barring is activated.";
      notife:notifiable-state-data true;
      type erienmnrmlrat:ddt-Lrat_EUtranCellTDD_loadBasedBarringFactor;
    }
    leaf maxNoClusteredPuschAlloc {
      description "Maximum number of UEs with Clustered PUSCH allocations allowed in a TTI.";
      yexte:takes-effect "Object unlocked";
      type erienmnrmlrat:ddt-Lrat_EUtranCellTDD_maxNoClusteredPuschAlloc;
      default 0;
    }
    leaf qRxLevMinCe {
      description "Min received RSRP level in E-UTRA frequency for cell reselection for UE in enhanced coverage mode. Corresponds to parameter Qrxlevmin_CE in 3GPP TS 36.304. This attribute is broadcast in SIB1-BR.";
      type erienmnrmlrat:ddt-Lrat_EUtranCellTDD_qRxLevMinCe;
      default -140;
    }
    leaf ulTrigActive {
      description "Specifies if outgoing uplink-triggered mobility actions are enabled or disabled in the cell.\nUsed when Uplink-Triggered Inter-Frequency Mobility is enabled. The parameter has effect if Mobility Control in Poor Coverage is enabled and mobCtrlAtPoorCovActive is set to true in the cell.";
      type boolean;
      default true;
    }
    leaf hoOptAdjThresholdPerc {
      description "The permillage threshold value for adjusted handover failure rate required to adjust handover parameters.";
      yexte:disturbances "Changing this attribute can stop outgoing HO.";
      type erienmnrmlrat:ddt-Lrat_EUtranCellTDD_hoOptAdjThresholdPerc;
      default 50;
    }
    leaf pMaxServingCell {
      description "Limits UE uplink transmission power in the serving cell and calculates the parameter Pcompensation (defined in 3GPP TS 36.304) for cell selection.\nThe attribute is broadcast in SIB1.\nValue 1000 means the parameter is not included in system information.";
      yexte:disturbances "Changing this attribute can cause loss of traffic.";
      type erienmnrmlrat:ddt-Lrat_EUtranCellTDD_pMaxServingCell;
      default 1000;
    }
    leaf pdcchOuterLoopInitialAdjVolte {
      description "The initial value for PDCCH outer loop adjustment for UEs with any bearer mapped to a QCI with serviceType of VoIP. In TDD, this parameter applies only to UEs which are configured with HARQ-ACK bundling.";
      yexte:takes-effect "Object unlocked";
      type erienmnrmlrat:ddt-Lrat_EUtranCellTDD_pdcchOuterLoopInitialAdjVolte;
      default -70;
    }
    leaf dlPowerRampUpRate {
      description "Power ramp up rate per second for downlink output power to reach full cell coverage.";
      yexte:takes-effect "Cell lock/unlock";
      type erienmnrmlrat:ddt-Lrat_EUtranCellTDD_dlPowerRampUpRate;
      default 1;
    }
    leaf pdcchTargetBler {
      description "PDCCH target error rate for UEs that do not have any secondary cell configured and do not have any bearer mapped to a QCI with serviceType of VoIP. In TDD, this parameter applies only to UEs which are configured with HARQ-ACK bundling.";
      yexte:takes-effect "Object unlocked";
      type erienmnrmlrat:ddt-Lrat_EUtranCellTDD_pdcchTargetBler;
      default 24;
    }
    leaf bsrThreshold {
      description "Threshold used to help identify data-aware UL scheduling UEs. If BSR >= bsrThreshold, UE becomes candidate UE for UL improvement.";
      type erienmnrmlrat:ddt-Lrat_EUtranCellTDD_bsrThreshold;
      default 0;
    }
    leaf iuaMaxPrbsPerUe {
      status deprecated {
        yexte:status-information "Since 18.Q3. Replaced by InstantUplinkAccess::iuaUePrbLimit. Planned to be removed.";
      }
      description "Maximum UL PRBs that are used by an IUA UE. The actual number of PRBs per UE depends on iuaMaxResourcePerCell.";
      type erienmnrmlrat:ddt-Lrat_EUtranCellTDD_iuaMaxPrbsPerUe;
      default 20;
    }
    leaf dlPowerRampUpInitialRatio {
      status deprecated {
        yexte:status-information "Since 18.Q4. Planned to be removed.";
      }
      description "Initial ratio for downlink output power to start power ramp up.\nValue 100 indicates full cell coverage.";
      yexte:takes-effect "Cell lock/unlock";
      type erienmnrmlrat:ddt-Lrat_EUtranCellTDD_dlPowerRampUpInitialRatio;
      default 100;
    }
    leaf plmn3AbConfProfileRef {
      description "Reference to an instance of PlmnAbConfProfile. Points to the PLMN Access Barring configuration profile.";
      yexte:disturbances "Changing this attribute can cause loss of traffic.";
      yexte:dependencies "References plmn1AbConfProfileRef, plmn2AbConfProfileRef and plmn3AbConfProfileRef must point to unique PlmnAbConfProfile MO instance.";
      erienmyext:enm-type MOREF;
      type string;
    }
    leaf noOfPucchSrUsers {
      description "The number of Scheduling Request (SR) resources available on the PUCCH channel.\nFor TDD Subframe Assignment 1 the recommended value is 64.";
      yexte:disturbances "Cell runs new set-up procedure. All cell-connected UEs are released and connected again.";
      type erienmnrmlrat:ddt-Lrat_EUtranCellTDD_noOfPucchSrUsers;
      default 16;
    }
    leaf lastModification {
      description "Indicates whether the MO was last modified by the operator or if the MO has been modified by the PCI conflict detection application.";
      type erienmnrmlrat:enum-LastModificationSourceCell;
      default OPERATOR;
    }
    leaf pZeroNominalPucch {
      description "The nominal component of the UE transmit power for Physical Uplink Control Channel (PUCCH).";
      yexte:disturbances "Changes may affect traffic.";
      type erienmnrmlrat:ddt-Lrat_EUtranCellTDD_pZeroNominalPucch;
      default -117;
    }
    leaf rachRootSequence {
      description "The first root sequence number for Random Access Channel (RACH) preamble generation. RACH root sequence is broadcast as a part of system information distribution and used for preamble detection.\nSee definition for logical root sequence number in 3GPP TS 36.211.\nIf feature Automated Rach Root Sequence Allocation is not activated a parameter change triggers automatic cell lock/unlock.\nIf feature Automated Rach Root Sequence Allocation is activated the parameter is changed without the need to lock/unlock the cell.";
      yexte:disturbances "Changes may affect traffic.";
      type erienmnrmlrat:ddt-Lrat_EUtranCellTDD_rachRootSequence;
      default 386;
    }
    leaf nonCaAnModeF3Enable {
      description "Enables PUCCH format3 as DL HARQ ACK/NACK feedback mode for TDD UEs not configured for carrier aggregation.";
      yexte:takes-effect "Next cell unlock";
      yexte:dependencies "Applicable only when attribute noOfPucchFormat3PrbPairs > 0.";
      type boolean;
      default false;
    }
    leaf isLaa {
      description "Indicates if the cell is operated in unlicensed spectrum with downlink only and no uplink.";
      yexte:disturbances "Changes can affect traffic.";
      yexte:takes-effect "Next cell unlock";
      type boolean;
      default false;
    }
    leaf dlFrequencyAllocationProportion {
      description "Specifies the amount of frequency resources that is allocated in DL expressed as a percentage of the configured bandwidth.";
      yexte:disturbances "Changing this attribute can cause loss of traffic.";
      yexte:takes-effect "Object unlocked";
      type erienmnrmlrat:ddt-Lrat_EUtranCellTDD_dlFrequencyAllocationProportion;
      default 100;
    }
    action stopAilg {
      description "Stops execution of the optional feature Air Interface Load Generator.";
    }
    action setCbrsTxExpireTime {
      description "Action requests node to set transmission expire time on externally supervised cell.\nAction sets date and time to attribute cbrsTxExpireTime on cell. If transmitExpireTime is -1, \"\" is set (empty).\nSpectrum access system controls transmission. Do not execute manually.";
      input {
        leaf transmitExpireTime {
          mandatory true;
          description "A time period granted for transmission on the assigned spectrum.";
          type erienmnrmlrat:ddt-EUtranCellTDD_setCbrsTxExpireTime_transmitExpireTime;
        }
      }
    }
    action startAilg {
      description "Starts execution of the optional feature Air Interface Load Generator.";
    }
    action changeFrequency {
      description "Changes the frequency of the cell. The attribute earfcn is changed. This MO action includes the following steps:\n\n\n- An instance of EUtranFrequency with correct frequency is created (if not already existing).\n\n\n- For neigbouring cells with existing cell relations to the cell, create new EUtranFreqRelation instances (if not already existing) and new EUtranCellRelation instances (with the same attribute values as the existing EUtranFreqRelation and EUtranCellRelation MOs).\n\n\n- For the changed cell an instance of EUtranFreqRelation with reference to the correct instance of EUtranFrequency is created, if not already existing (with the same attribute values as the existing EUtranFreqRelation MO).\n\nNote that changing frequency of a EUtranCellTDD will imply that all other eNBs that have this cell configured as an ExternaEUtranCellTDD will be updated with the new frequency. This means that new EUtranFreqRelation and corresponding EUtranFrequency MOs might be created.\n\n";
      input {
        leaf earfcn {
          mandatory true;
          description "The new frequency for this cell.\n";
          type erienmnrmlrat:ddt-EUtranCellTDD_changeFrequency_earfcn;
        }
      }
    }
  } // end 'grouping moc-EUtranCellTDD'
  grouping moc-ReportConfigB2GeranUlTrig-keys {
    description "Key(s) for MOC ReportConfigB2GeranUlTrig";
    leaf id {
      erienmyext:no-notification;
      description "The value component of the RDN.";
      mandatory true;
      yexte:ecim-name reportConfigB2GeranUlTrigId;
      type string;
    }
  } // end 'grouping moc-ReportConfigB2GeranUlTrig-keys'
  grouping moc-ReportConfigB2GeranUlTrig {
    description "Contains report configuration settings for the B2 event for GERAN measurements initiated by Uplink-Triggered Inter-Frequency Mobility. The actual threshold values used can be adjusted by frequency relation or QCI related offsets if the feature Multi-Layer Service-Triggered Mobility (MLSTM) is enabled.\n\nThe RDN of this MO is ReportConfigB2GeranUlTrig=1.";
    leaf hysteresisB2 {
      description "The hysteresis value for the event B2.";
      yexte:takes-effect "New connection";
      type erienmnrmlrat:ddt-Lrat_ReportConfigB2GeranUlTrig_hysteresisB2;
      default 10;
    }
    leaf b2Threshold2Geran {
      description "The Signal Quality in the ThresholdGERAN, threshold2 value for eventB2.";
      yexte:takes-effect "New connection";
      type erienmnrmlrat:ddt-Lrat_ReportConfigB2GeranUlTrig_b2Threshold2Geran;
      default -110;
    }
    leaf timeToTriggerB2 {
      description "Time-to-trigger value for event B2.";
      yexte:takes-effect "New connection";
      type erienmnrmlrat:ddt-Lrat_ReportConfigB2GeranUlTrig_timeToTriggerB2;
      default 640;
    }
    leaf reportIntervalB2 {
      description "The interval for event triggered periodical reporting for B2 event.";
      yexte:takes-effect "New connection";
      type erienmnrmlrat:enum-ReportInterval;
      default MS_2048;
    }
  } // end 'grouping moc-ReportConfigB2GeranUlTrig'
  grouping moc-QciProfileOperatorDefined-keys {
    description "Key(s) for MOC QciProfileOperatorDefined";
    leaf id {
      erienmyext:no-notification;
      description "The value component of the RDN.";
      mandatory true;
      yexte:ecim-name qciProfileOperatorDefinedId;
      type string;
    }
  } // end 'grouping moc-QciProfileOperatorDefined-keys'
  grouping moc-QciProfileOperatorDefined {
    description "Contains bearer-level QoS configuration. Instances of this class are created on demand by the operator. Each QciProfileOperatorDefined instance corresponds to a unique operator defined QCI number within the range 10-255. The instances can be created and configured independent of the serviceStateOperatorDefinedQci. However the configured QCI profiles can not be used at bearer setup / modify unless the service state is OPERABLE.\n";
    leaf serviceType {
      description "Indicates the service that the bearer is used for.\nServiceType PTT and MC_SIGNALING cannot be set on QciProfileOperatorDefined MO.";
      yexte:takes-effect "Cell lock/unlock";
      yexte:dependencies "Changes to this parameter take effect only if the license for QoS Aware Scheduler is present and the feature is active.";
      type erienmnrmlrat:enum-ServiceType;
      default UNDEFINED;
    }
    leaf userLabel {
      description "Label for free use.";
      type erienmnrmlrat:ddt-Lrat_QciProfileOperatorDefined_userLabel;
    }
    leaf pdcpSNLength {
      description "Indicates the Packet Data Convergence Protocol (PDCP) Sequence Number length in bits as specified in TS 36.323.";
      yexte:takes-effect "Cell lock/unlock";
      yexte:dependencies "RLC UM must be configured (rlcMode = UM) to set this attribute to 7. RLC AM must be configured (rlcMode = AM) to set this attribute to 15. 15-bits PDCP SN is only applied if:\n - pdcp-SN-Extension capability is indicated by UE; And\n - UE is of category 11 or above; And\n - UE is capable of at least 3C Carrier Aggregation.\nOtherwise, default value of 12-bits PDCP SN is applied for RLC AM bearers.";
      type erienmnrmlrat:ddt-Lrat_QciProfileOperatorDefined_pdcpSNLength;
      default 12;
    }
    leaf pdbOffset {
      description "An offset to the PDB used by Active Queue Management (AQM).";
      yexte:takes-effect "Cell lock/unlock";
      yexte:dependencies "pdb + pdbOffset >= 0";
      type erienmnrmlrat:ddt-Lrat_QciProfileOperatorDefined_pdbOffset;
      default 0;
    }
    leaf rlcMode {
      description "RLC Mode";
      yexte:takes-effect "Cell lock/unlock";
      yexte:dependencies "Can only be set to AM if rlcSNLength is set to 10 or 16 and pdcpSNLength is set to 12 or 15. Must be set to UM if rlcSNLength is set to 5 or pdcpSNLength is set to 7.";
      type erienmnrmlrat:enum-RlcMode;
      default AM;
    }
    leaf dataFwdPerQciEnabled {
      description "Enables forwarding of data for this QCI.";
      yexte:dependencies "The parameter is only valid if the IntraLTEHODataFwd or S1HODataFwd licence is installed and active.";
      type boolean;
      default false;
    }
    leaf endcProfileRef {
      description "Reference to an instance of EndcProfile or EndcProfilePredefined.\nEN-DC profile associated with this QCI.\nIf not set, defaults to EndcProfilePredefined with LDN = ManagementElement=1, ENodeBFunction=1, EndcProfilePredefined=1.";
      yexte:disturbances "Changing this attribute can cause loss of traffic.";
      yexte:takes-effect "New connection";
      yexte:dependencies "Only applicable in Baseband Radio Node.";
      erienmyext:enm-type MOREF;
      type string;
    }
    leaf rlfPriority {
      description "The relative priority among the RLF (Radio Link Failure) profiles, i.e. if the bearer that is setup with this QCI has a higher RLF priority than any of the existing bearers, the RLF configuration will be set to those selected by the rlfProfileId for this QCI. If more than one QCI has been configured with the same and highest value of rlfPriority the RLF configuration will be set by the lowest QCI. The instances that share the same rlfProfileId may have the same rlfPriority value. Also note that larger rlfPriority values indicate higher relative priority.";
      yexte:takes-effect "Object unlocked";
      type erienmnrmlrat:ddt-Lrat_QciProfileOperatorDefined_rlfPriority;
      default 0;
    }
    leaf ulMaxHARQTxQci {
      description "Maximum number of transmissions for one HARQ process in UL when this QCI has the highest HARQ priority.";
      yexte:takes-effect "New connection";
      type erienmnrmlrat:ddt-Lrat_QciProfileOperatorDefined_ulMaxHARQTxQci;
      default 5;
    }
    leaf dlResourceAllocationStrategy {
      description "Defines the downlink resource allocation strategy of the QoS Class Identifier (QCI).";
      yexte:takes-effect "New connection";
      yexte:dependencies "Changes to this parameter take effect only if the licenses for Downlink Frequency Selective Scheduling and QoS Aware Scheduler are present and the features are active.";
      type erienmnrmlrat:enum-ResourceAllocationStrategy;
      default RESOURCE_FAIR;
    }
    leaf counterActiveMode {
      description "Defines the interpretation of active for the QCI:\nFALSE (DEFAULT):\nActive time is measured in the case of:\nDRB: as the time when there is data in a buffer, DL and/or UL, with an added guard period of 100 ms thereafter\nUE: as the time when there is data in a buffer, DL and/or UL, with an added guard period of 100 ms thereafter in any of the DRBs connected to the UE\nThe pmCounters for active E-RABs are stepped in case of data in a buffer, DL and/or UL.\nTRUE:\nActive time is measured in the case of:\nDRB: from the first data occurrence in a buffer to the last data occurrence in a buffer for that DRB\nUE: from the first data occurrence in a buffer to the last data occurrence in a buffer for any DRB associated with the UE\nThe pmCounters for active E-RABs are always stepped since the DRB is considered always active";
      yexte:takes-effect "Cell lock/unlock";
      type boolean;
      default false;
    }
    leaf dscp {
      description "The Differentiated Services Code Point for a Quality of Service Class Indicator (QCI). This corresponds to mappings from RAN QoS to Transport Network QoS.";
      mandatory true;
      yexte:takes-effect "New connection";
      type erienmnrmlrat:ddt-Lrat_QciProfileOperatorDefined_dscp;
    }
    leaf srsAllocationStrategy {
      description "If the parameter srsAllocationStrategy in the QoS configuration for a Data radio Bearer assigned to a UE is set to ACTIVATED, then an attempt is made to allocate sounding for a UE. If several Data Radio Bearers are setup towards the UE with different QoS configurations, and the QoS configurations has different QCI parameter, an algorithm using the priority parameter in the QoS configuration, will resolve which QoS configuration that will define sounding";
      yexte:takes-effect "New connection";
      type erienmnrmlrat:enum-SrsAllocationStrategy;
      default DEACTIVATED;
    }
    leaf relativePriority {
      description "The relative priority associated with a QCI.";
      yexte:takes-effect "New connection";
      yexte:dependencies "Changes to this parameter take effect only if the feature states of the  QoS Aware Scheduler , Proportional Fair Scheduler, and  the Rps are enabled.";
      type erienmnrmlrat:ddt-Lrat_QciProfileOperatorDefined_relativePriority;
      default 1;
    }
    leaf ulMaxWaitingTime {
      description "The scheduler attempts to achieve ulMaxWaitingTime for UL bearers before giving any UL bearer a higher priority. Value 0 means that the higher priority is never applied. Must be set to a similar or slightly shorter value than the PDB. Setting too low a value can affect other services with higher priority. For more information about PDB refer to TS 23.203.";
      yexte:disturbances "Changing this attribute can affect performance of all data bearers. A value that is set too low can affect other services with higher priority. A value that is set too high can cause Dynamic UE Admission Control to fail in keeping the cell stable at overload.";
      yexte:takes-effect "New connection";
      yexte:dependencies "Only used for Resource Fair Scheduling algorithm. Only relevant if the license for Advanced Differentiation for Resource Fair Scheduler is present and the feature is active.";
      type erienmnrmlrat:ddt-Lrat_QciProfileOperatorDefined_ulMaxWaitingTime;
      default 0;
    }
    leaf qci {
      yexte:restricted;
      description "Quality of Service Class Indicator (QCI) as defined in 3GPP TS 23.203 (Release 8). Each instance of this MO has a unique value for the QCI.";
      mandatory true;
      yexte:takes-effect "Object unlocked";
      yexte:dependencies "Each qci must be set to a unique value.";
      type erienmnrmlrat:ddt-Lrat_QciProfileOperatorDefined_qci;
    }
    leaf schedulingAlgorithm {
      description "Specifies which scheduling algorithm is to be used for a certain QCI.";
      yexte:disturbances "Changing this attribute can cause loss of traffic.";
      yexte:takes-effect "New connection";
      yexte:dependencies "Only relevant if the license for QoS Aware Scheduler is present and the feature is active. The value DELAY_BASED can only be used if the attribute serviceType has value VOIP.";
      type erienmnrmlrat:enum-SchedulingAlgorithm;
      default RESOURCE_FAIR;
    }
    leaf dlMaxWaitingTime {
      description "The scheduler attempts to achieve dlMaxWaitingTime for DL bearers before giving any DL bearer a higher priority. Value 0 means that the higher priority is never applied. Must be set to a similar or slightly shorter value than the PDB. Setting too low a value can affect other services with higher priority. For more information about PDB refer to TS 23.203.";
      yexte:disturbances "Changing this attribute can affect performance of all data bearers. A value that is set too low can affect other services with higher priority. A value that is set too high can cause Dynamic UE Admission Control to fail in keeping the cell stable at overload.";
      yexte:takes-effect "New connection";
      yexte:dependencies "Only used for Resource Fair Scheduling algorithm. Only relevant if the license for Advanced Differentiation for Resource Fair Scheduler is present and the feature is active.";
      type erienmnrmlrat:ddt-Lrat_QciProfileOperatorDefined_dlMaxWaitingTime;
      default 0;
    }
    leaf absPrioOverride {
      description "Indicates if the data radio bearer is subject to Absolute Priority Override.";
      yexte:disturbances "Changing this attribute can cause loss of traffic.";
      yexte:takes-effect "New connection";
      yexte:dependencies "Only relevant if the license for QoS Aware Scheduler is present and the feature is active.";
      type erienmnrmlrat:enum-AbsPrioOverride;
      default NO_OVERRIDE;
    }
    leaf dlMinBitRate {
      description "The scheduler will attempt to achieve minbitrate for all bearers before giving any user a higher rate. Value 0 means that the minRate scheduler is not used.";
      yexte:disturbances "Changing this attribute can cause loss of traffic.";
      yexte:takes-effect "New connection";
      yexte:dependencies "This parameter will only be used if one of the following Proportional Fair scheduling algorithms, \"maximum_C_over_I\", \"proportional_fair_low\", \"proportional_fair_medium\", \"proportional_fair_high\" or \"equal_rate\", has been selected.\nOnly relevant if the license for QoS Aware Scheduler is present and the feature is active.";
      type erienmnrmlrat:ddt-Lrat_QciProfileOperatorDefined_dlMinBitRate;
      default 0;
    }
    leaf priorityFraction {
      description "Fractional part of QCI-related priority.\nDecimal part of priority is defined by priority attribute.";
      yexte:disturbances "Changing this attribute can cause loss of traffic.";
      yexte:takes-effect "New connection";
      yexte:dependencies "(priority + priorityFraction) > 0 AND (priority * 10 + priorityFraction) <= 140";
      type erienmnrmlrat:ddt-Lrat_QciProfileOperatorDefined_priorityFraction;
      default 0;
    }
    leaf logicalChannelGroupRef {
      description "Refers to an instance of LogicalChannelGroup. Assigns a Logical Channel Group to a Quality of Service Class Indicator (QCI).";
      mandatory true;
      yexte:takes-effect "New connection";
      erienmyext:enm-type MOREF;
      type string;
    }
    leaf qciACTuning {
      description "Tuning factor per QCI for admission control. Only valid for QCIs with resource type GBR.";
      yexte:takes-effect "New connection";
      yexte:dependencies "Only relevant if the license for Dynamic GBR admission control is present and the feature is active.";
      type erienmnrmlrat:ddt-Lrat_QciProfileOperatorDefined_qciACTuning;
      default 1000;
    }
    leaf inactivityTimerOffset {
      description "The offset time value that can be used to prolong the default inactivity timer.";
      yexte:takes-effect "New connection";
      type erienmnrmlrat:ddt-Lrat_QciProfileOperatorDefined_inactivityTimerOffset;
      default 0;
    }
    leaf drxProfileRef {
      description "Points out the DRX profile associated with this QCI. If not set the default reference will be to the DrxProfile instance corresponding to Local Distinguished Name (LDN) = ManagementElement=1, ENodeBFunction=1, DRxProfile=0.";
      yexte:disturbances "Changing this attribute can cause loss of traffic. Possible mismatch between DRX setting used by network and UE for ongoing connections.";
      yexte:takes-effect "Object unlocked";
      yexte:dependencies "The DRX profile must exist, otherwise it will be interpreted as default DRX profile.";
      erienmyext:enm-type MOREF;
      type string;
    }
    leaf tReorderingDl {
      description "This timer is used by the receiving end of Acknowledged Mode (AM) or Unacknowledged Mode (UM) Radio Link Control (RLC) entity in UE, to detect loss of downlink RLC protocol data units at lower layers.";
      yexte:takes-effect "New connection";
      yexte:dependencies "Not applicable for RLC TM. Only relevant when rlcMode is UM or AM";
      type erienmnrmlrat:ddt-Lrat_QciProfileOperatorDefined_tReorderingDl;
      default 35;
    }
    leaf harqPriority {
      description "Relative HARQ priority of this QCI. If a bearer that is setup with this QCI has highest HARQ priority, HARQ transmission number is set to ulMaxHARQTxQci and dlMaxHARQTxQci. HARQ priority must be unique for all configured MOC instances for QciProfilePredefined and QciProfileOperatorDefined. Does not apply when ulMaxHARQTxQci and dlMaxHARQTxQci are same. Note that larger harqPriority values indicate higher relative priority.";
      yexte:takes-effect "New connection";
      type erienmnrmlrat:ddt-Lrat_QciProfileOperatorDefined_harqPriority;
      default 0;
    }
    container measReportConfigParams {
      description "Parameters for service-specific load management for a certain QCI profile.";
      erienmyext:enm-type STRUCT;
      uses erienmnrmlrat:struct-MeasReportConfigParams;
    } // end 'container measReportConfigParams'
    leaf qciSubscriptionQuanta {
      description "Normalized subscription quantity associated with the specific the QCI. Specifies the subscription cost of a bearer with this predefined profile. The subscription cost is used for traffic load balancing purposes.";
      yexte:disturbances "Changing this attribute can cause loss of traffic.";
      type erienmnrmlrat:ddt-Lrat_QciProfileOperatorDefined_qciSubscriptionQuanta;
      default 1;
    }
    leaf priority {
      description "Decimal part of QCI-related priority.\nFractional part of priority is defined by priorityFraction attribute.";
      mandatory true;
      yexte:disturbances "Changing this attribute can cause loss of traffic.";
      yexte:takes-effect "New connection";
      yexte:dependencies "(priority + priorityFraction) > 0 AND (priority * 10 + priorityFraction) <= 140";
      type erienmnrmlrat:ddt-Lrat_QciProfileOperatorDefined_priority;
    }
    leaf pdb {
      description "The contribution from eNodeB to the Packet Delay Budget (PDB) for a QCI. Packet delays outside eNodeB e.g. in the transport network are excluded. For more information about PDB refer to TS 23.203";
      yexte:takes-effect "Cell lock/unlock";
      yexte:dependencies "Only relevant if the license for QoS Aware Scheduler is present and active.";
      type erienmnrmlrat:ddt-Lrat_QciProfileOperatorDefined_pdb;
      default 80;
    }
    leaf rlcSNLength {
      description "Radio Link Control (RLC) Sequence Number length in bits as specified in TS 36.322.";
      yexte:takes-effect "Cell lock/unlock";
      yexte:dependencies "RLC UM must be configured (rlcMode = UM) to set this attribute to 5. RLC AM must be configured (rlcMode = AM) to set this attribute to 16. 16-bit RLC SN is only applied if:\n- extendedRLC-SN-SO-Field-r13 is indicated by UE; and\n- 5CC DL Carrier Aggregation Extension license is enabled; and\n- UE is capable of at least 5CC DL Carrier Aggregation.\nOtherwise, default value of 10-bit RLC SN is applied for RLC AM bearers.";
      type erienmnrmlrat:ddt-Lrat_QciProfileOperatorDefined_rlcSNLength;
      default 10;
    }
    leaf drxPriority {
      description "The relative priority among the DRX profiles, i.e. if the bearer that is setup with this QCI has a higher DRX priority than any of the existing bearers, the DRX configuration will be set to those selected by the drxProfileId for this QCI. The drxPriority has to be unique across all the configured QciProfilePredefined and QciProfileOperatorDefined MOC instances except for instances where the drxProfileId is the same. That is, instances that share the same drxProfileId may have the same drxPriority value. Also note that larger drxPriority values indicate higher relative priority.";
      yexte:disturbances "Changing this attribute can cause loss of traffic. Possible mismatch between DRX setting used by network and UE for ongoing connections.";
      yexte:takes-effect "Object unlocked";
      type erienmnrmlrat:ddt-Lrat_QciProfileOperatorDefined_drxPriority;
      default 0;
    }
    leaf rohcEnabled {
      description "Indicates if Robust Header Compression (ROHC) is enabled.\nNote: Enabling ROHC is only supported for a QCI that is intended to carry RTP/RTCP/UDP based VoIP traffic as for example the standardized QCI1 (3GPP TS 23.203) and not for any other type of traffic.";
      yexte:takes-effect "New connection";
      type boolean;
      default false;
    }
    leaf tReorderingUl {
      description "This timer is used by the receiving end of the Acknowledged Mode (AM) or Unacknowledged Mode (UM) Radio Link Control (RLC) entity in eNB, to detect loss of uplink RLC protocol data units at lower layers.";
      yexte:takes-effect "Cell lock/unlock";
      yexte:dependencies "Not applicable for RLC TM. Only relevant when rlcMode is UM or AM";
      type erienmnrmlrat:ddt-Lrat_QciProfileOperatorDefined_tReorderingUl;
      default 35;
    }
    leaf aqmMode {
      description "Active Queue Management (AQM) mode";
      yexte:takes-effect "Cell lock/unlock";
      type erienmnrmlrat:enum-AQMMode;
      default OFF;
    }
    leaf resourceAllocationStrategy {
      description "Defines the resource allocation strategy of the QoS Class Identifier (QCI).";
      yexte:takes-effect "New connection";
      yexte:dependencies "Only relevant if the license for QoS Aware Scheduler is present and the feature is active";
      type erienmnrmlrat:enum-ResourceAllocationStrategy;
      default RESOURCE_FAIR;
    }
    leaf rlfProfileRef {
      description "Points out the RLF profile associated with this QCI. If not set the default reference will be to the RlfProfile instance corresponding to Local Distinguished Name (LDN) = ManagementElement=1, ENodeBFunction=1, RlfProfile=0.";
      yexte:takes-effect "Object unlocked";
      yexte:dependencies "The RLF profile must exist, otherwise it will be interpreted as default RLF profile.";
      erienmyext:enm-type MOREF;
      type string;
    }
    leaf ulMinBitRate {
      description "The scheduler will attempt to achieve minbitrate for all bearers before giving any user a higher rate. Value 0 means that the minRate scheduler is not used.";
      yexte:disturbances "Changing this attribute can cause loss of traffic.";
      yexte:takes-effect "New connection";
      yexte:dependencies "This parameter will only be used if one of the following Proportional Fair scheduling algorithms, \"maximum_C_over_I\", \"proportional_fair_low\", \"proportional_fair_medium\", \"proportional_fair_high\" or \"equal_rate\", has been selected.\nOnly relevant if the license for QoS Aware Scheduler is present and the feature is active.";
      type erienmnrmlrat:ddt-Lrat_QciProfileOperatorDefined_ulMinBitRate;
      default 0;
    }
    leaf-list reservedBy {
      min-elements 0;
      erienmyext:no-notification;
      config false;
      description "Contains a list of MO instances that reserve this MO instance.";
      erienmyext:enm-type MOREF;
      type string;
    }
    leaf timerPriority {
      description "Relative priority among the timer profiles. TimerProfile with highest priority can be applied for a new connection in case the bearer QCI has an associated TimerProfile.\nIn case several bearers with different QCIs are established, the TimerProfile with highest relative priority is applied.\nThe TimerProfile with lowest QCI number is applied, if TimerProfiles have the same priority,\nLarger timerPriority value indicates higher relative priority.";
      yexte:takes-effect "Object unlocked";
      type erienmnrmlrat:ddt-Lrat_QciProfileOperatorDefined_timerPriority;
      default 0;
    }
    leaf dlMaxHARQTxQci {
      description "Maximum number of transmissions for one HARQ process in DL when this QCI has the highest HARQ priority. Values higher than 7 will be treated as 7.";
      yexte:takes-effect "New connection";
      type erienmnrmlrat:ddt-Lrat_QciProfileOperatorDefined_dlMaxHARQTxQci;
      default 5;
    }
    leaf lessMaxDelayThreshold {
      description "Time delay that scheduling stays on-hold for Low Energy Scheduler Solution.\nIf 0, Low Energy Scheduler Solution is disabled.";
      yexte:takes-effect "New connection";
      type erienmnrmlrat:ddt-Lrat_QciProfileOperatorDefined_lessMaxDelayThreshold;
      default 0;
    }
    leaf timerProfileRef {
      description "Refers to the timer profile associated with this QCI.";
      yexte:takes-effect "Object unlocked";
      erienmyext:enm-type MOREF;
      type string;
    }
    leaf resourceType {
      yexte:restricted;
      description "Indicates if the resource type of the Quality of Service Class Indicator (QCI) is Guaranteed Bit Rate (GBR) or non-GBR as defined in 3GPP TS 23.203.";
      mandatory true;
      yexte:takes-effect "Object unlocked";
      type erienmnrmlrat:enum-ResourceType;
    }
  } // end 'grouping moc-QciProfileOperatorDefined'
  grouping moc-Etws-keys {
    description "Key(s) for MOC Etws";
    leaf id {
      erienmyext:no-notification;
      description "The value component of the Relative Distinguished Name (RDN).";
      mandatory true;
      yexte:ecim-name etwsId;
      type string;
    }
  } // end 'grouping moc-Etws-keys'
  grouping moc-Etws {
    description "Stores warning information for cell to be broadcast in SIB10 or SIB11.\n\nThe RDN of this MO is Etws=1.";
  } // end 'grouping moc-Etws'
  grouping moc-DlComp-keys {
    description "Key(s) for MOC DlComp";
    leaf id {
      erienmyext:no-notification;
      description "The value component of the RDN.";
      mandatory true;
      yexte:ecim-name dlCompId;
      type string;
    }
  } // end 'grouping moc-DlComp-keys'
  grouping moc-DlComp {
    description "This MO contains configuration settings for Downlink Coordinated Multi-Point.\n\nThe RDN of this MO is DlComp=1.";
  } // end 'grouping moc-DlComp'
  grouping moc-PtmFunction-keys {
    description "Key(s) for MOC PtmFunction";
    leaf id {
      erienmyext:no-notification;
      description "The value component of the RDN.";
      mandatory true;
      yexte:ecim-name ptmFunctionId;
      type string;
    }
  } // end 'grouping moc-PtmFunction-keys'
  grouping moc-PtmFunction {
    description "Contains eNodeB-specific configuration for Preferential Traffic Management.\n\nThe RDN of this MO is PtmFunction=1.";
    leaf ptmEnabled {
      description "Enables PTM on eNodeB level.\nMust be set to TRUE to enable PTM on any cell.";
      yexte:disturbances "Changing this attribute can affect traffic.";
      type boolean;
      default false;
    }
  } // end 'grouping moc-PtmFunction'
  grouping moc-ExternalEUtranCellFDD-keys {
    description "Key(s) for MOC ExternalEUtranCellFDD";
    leaf id {
      erienmyext:no-notification;
      description "The value component of the Relative Distinguished Name (RDN).\n";
      mandatory true;
      yexte:ecim-name externalEUtranCellFDDId;
      type string;
    }
  } // end 'grouping moc-ExternalEUtranCellFDD-keys'
  grouping moc-ExternalEUtranCellFDD {
    description "This managed object represents a neighbor EUTRAN cell (FDD) in another ENodeB in any MME pool.\n";
    leaf userLabel {
      description "User-defined alphanumeric label, maximum 128 characters including spaces.\n";
      type erienmnrmlrat:ddt-Lrat_ExternalEUtranCellFDD_userLabel;
    }
    leaf noOfTxAntennas {
      description "Number of antennas that can be used for DL transmission.";
      yexte:takes-effect "New connection";
      type erienmnrmlrat:ddt-Lrat_ExternalEUtranCellFDD_noOfTxAntennas;
      default 2;
    }
    leaf-list pciConflict {
      min-elements 0;
      max-elements 5;
      description "A PCI confusion exists if a source cell has relations to two neighbor cells where both neighbor cells have the same PCI and frequency. A PCI collision exists if a source cell has a relation to a neighbor cell where both the source cell and neighbor cell have the same PCI and frequency.";
      type erienmnrmlrat:enum-PciConflict;
    }
    leaf dlChannelBandwidth {
      config false;
      description "The downlink channel bandwidth in a cell that is served by a neighboring RBS. The parameter is set by the RBS at X2 SETUP procedure. The value 0 means there is no valid value available.";
      notife:notifiable-state-data true;
      type erienmnrmlrat:ddt-Lrat_ExternalEUtranCellFDD_dlChannelBandwidth;
    }
    leaf csgPhysCellId {
      status deprecated {
        yexte:status-information "Since L16B. Has no functional behavior. Planned to be removed.";
      }
      description "Physical Cell Identity for the CSG (Closed Subscriber Group). It is the start physical cell ID in the SIB4. If value is equal to 1000, it means that csg-PhysCellIdRange IE is not presented in SIB4.";
      yexte:dependencies "This attribute has a dependency to csgPhysCellIdRange.";
      type erienmnrmlrat:ddt-Lrat_ExternalEUtranCellFDD_csgPhysCellId;
      default 1000;
    }
    leaf physicalLayerCellId {
      config false;
      description "Physical-layer cell ID.";
      yexte:dependencies "Equal to 3 x physicalLayerCellIdGroup + physicalLayerSubCellId.";
      notife:notifiable-state-data true;
      type erienmnrmlrat:ddt-Lrat_ExternalEUtranCellFDD_physicalLayerCellId;
    }
    leaf csgPhysCellIdRange {
      status deprecated {
        yexte:status-information "Since L16B. Has no functional behavior. Planned to be removed.";
      }
      description "It is the range of Physical Cell Identity for the CSG (Closed Subscriber Group). The information is broadcasted in SIB4.";
      yexte:dependencies "If csgPhyscellId != 1000, csgPhysCellId + csgPhysCellIdRange <= 504";
      type erienmnrmlrat:ddt-Lrat_ExternalEUtranCellFDD_csgPhysCellIdRange;
      default 1;
    }
    leaf masterEUtranCellFDDId {
      description "The identity of the EUtranCellFDD represented by this MO, for managed objects automatically created by ExternalEUtranCellFDD.";
      type erienmnrmlrat:ddt-Lrat_ExternalEUtranCellFDD_masterEUtranCellFDDId;
      default "";
    }
    list activePlmnList {
      min-elements 0;
      max-elements 6;
      key auto-generated-struct-key;
      leaf auto-generated-struct-key {
        type uint16;
        description "This leaf has been injected to allow for struct instances in a sequence to be ordered.";
        mandatory true;
      }
      description "Lists the PLMN IDs in the external E-UTRAN cell. The list may include up to 6 PLMN IDs. The list tracks the activePlmnList in the corresponding instance of EUtranCellFDD/TDD in another RBS. It is configured by ANR when ANR feature creates the MO and then set to the PLMN Id from the CGI report. The list is updated via X2 or OSS-RC, or manually.";
      erienmyext:enm-type STRUCT;
      uses erienmnrmlrat:struct-PlmnIdentity;
    } // end 'list activePlmnList'
    leaf mfbiFreqBandIndPrioExt {
      erienmyext:no-notification;
      config false;
      description "Indicates if external cell supports additional frequency band priority. Used during handover procedure.\nUndefined value: UNDEFINED_VALUE";
      yexte:dependencies "Only takes effect if MFBI is active.";
      type erienmnrmlrat:enum-MfbiFreqBandIndPrioExt;
    }
    list pciConflictCell {
      min-elements 0;
      max-elements 5;
      key auto-generated-struct-key;
      leaf auto-generated-struct-key {
        type uint16;
        description "This leaf has been injected to allow for struct instances in a sequence to be ordered.";
        mandatory true;
      }
      description "Indicates the CGI of the other cell that is involved in the PCI collision/confusion. This value is only valid if the attribute pciConflict is \"YES\" or \"YES_CONFLICTING_CELL\".";
      erienmyext:enm-type STRUCT;
      uses erienmnrmlrat:struct-Cgi;
    } // end 'list pciConflictCell'
    leaf lbEUtranCellOffloadCapacity {
      description "This attribute indicates the offload subscription capacity associated with the EUTRAN target cell. The value is used to moderate the offload rate to the EUTRAN target cell.";
      yexte:disturbances "Changing this attribute can cause loss of traffic.";
      type erienmnrmlrat:ddt-Lrat_ExternalEUtranCellFDD_lbEUtranCellOffloadCapacity;
      default 1000;
    }
    leaf isRemoveAllowed {
      description "Indicates if the Automated Neighbor Relations (ANR) function is allowed to remove this object. The setting does not restrict operator removal of the object. Objects created by ANR have this attribute set to true initially.";
      type boolean;
      default false;
    }
    leaf remoteCellStateEranUlComp {
      config false;
      description "Whether indicated cell can serve as external cell for Elastic RAN UL CoMP.";
      yexte:dependencies "X2 connection must be operational and software compatible. Remote cell must be operState ENABLED and adminState UNLOCKED.";
      notife:notifiable-state-data true;
      type erienmnrmlrat:enum-OperState;
    }
    leaf tac {
      description "The Tracking Area Code of an external cell.";
      mandatory true;
      yexte:takes-effect "New connection.";
      type erienmnrmlrat:ddt-Lrat_ExternalEUtranCellFDD_tac;
    }
    leaf sCellCaConfigurationAvailabilty {
      status deprecated {
        yexte:status-information "Since L16B. Has no functional behavior. Planned to be removed.";
      }
      erienmyext:no-notification;
      config false;
      description "Reflects whether the indicated cell is currently able to serve as an SCell. The remoteCellState must be operState ENABLED and Inter-eNodeB license must be active. As well, at least one tunnel connecting the indicated ESCell to this eNodeB must be enabled.  If not, no UEs are configured with this candidate, though UEs already configured with this cell will possibly retain the configuration.";
      yexte:dependencies "Depends on feature license and success of tunnels in TermPointToLbm, interEnbSwCompatibilityState and on remoteCellState.";
      type erienmnrmlrat:enum-OperState;
    }
    leaf eutranFrequencyRef {
      description "Reference to the EUTRAN frequency MO, EUtranFrequency. Cannot be changed as long as this MO is referred to by a EUtranCellRelation MO.";
      mandatory true;
      erienmyext:enm-type MOREF;
      type string;
    }
    leaf freqBand {
      config false;
      description "The primary frequency band the cell belongs to according to its defined EARFCN. This frequency band indicator is broadcasted to the UEs in SystemInformationBlockType1.";
      notife:notifiable-state-data true;
      type erienmnrmlrat:ddt-Lrat_ExternalEUtranCellFDD_freqBand;
    }
    leaf physicalLayerSubCellId {
      description "The unique subidentity within a group. Physical-layer cell identities are grouped into 168 unique physical-layer cell-identity groups, each group containing 3 unique subidentities.";
      mandatory true;
      type erienmnrmlrat:ddt-Lrat_ExternalEUtranCellFDD_physicalLayerSubCellId;
    }
    list pciDetectingCell {
      min-elements 0;
      max-elements 5;
      key auto-generated-struct-key;
      leaf auto-generated-struct-key {
        type uint16;
        description "This leaf has been injected to allow for struct instances in a sequence to be ordered.";
        mandatory true;
      }
      description "Indicates the CGI of the cell that detected the PCI collision/confusion. This value is only valid if the corresponding attribute pciConflict is \"YES\" or \"YES_CONFLICTING_CELL\". The first cell in the pciDetectingCell list corresponds to the first cell in the pciConflictCell list and the first value of pciConflict. The second cell in the pciDetectingCell list corresponds to the second cell in the pciConflictCell list and the first value of pciConflict.";
      erienmyext:enm-type STRUCT;
      uses erienmnrmlrat:struct-Cgi;
    } // end 'list pciDetectingCell'
    leaf timeOfCreation {
      erienmyext:no-notification;
      config false;
      description "Indicates the time and date when the MO was created.\nFormat: YYYY-MM-DD HH:MM:SS";
      type erienmnrmlrat:ddt-Lrat_ExternalEUtranCellFDD_timeOfCreation;
    }
    leaf physicalLayerCellIdGroup {
      description "The physical-layer cell-identity group. Physical-layer cell IDs are grouped into 168 unique physical-layer cell-identity groups, each group containing 3 unique subidentities.";
      mandatory true;
      type erienmnrmlrat:ddt-Lrat_ExternalEUtranCellFDD_physicalLayerCellIdGroup;
    }
    leaf ulChannelBandwidth {
      config false;
      description "The uplink channel bandwidth in a cell that is served by a neighboring RBS. The attribute is set by the RBS at X2 SETUP procedure. The value 0 means there is no valid value available.";
      notife:notifiable-state-data true;
      type erienmnrmlrat:ddt-Lrat_ExternalEUtranCellFDD_ulChannelBandwidth;
    }
    leaf timeOfLastModification {
      config false;
      description "Indicates the time and date when the MO was last modified.\nFormat: YYYY-MM-DD HH:MM:SS";
      notife:notifiable-state-data true;
      type erienmnrmlrat:ddt-Lrat_ExternalEUtranCellFDD_timeOfLastModification;
    }
    leaf remoteCellStateInterEnbUlComp {
      erienmyext:no-notification;
      config false;
      description "Whether indicated cell can serve as external cell for inter-eNodeB UL CoMP.";
      yexte:dependencies "X2 connection must be operational and software compatible. Remote cell must be operState ENABLED and adminState UNLOCKED.";
      type erienmnrmlrat:enum-OperState;
    }
    leaf-list additionalFreqBandList {
      min-elements 0;
      max-elements 8;
      config false;
      description "A list of additional frequency bands the cell belongs to, not including the frequency band indicated by the EARFCN value of the cell (primary frequency band). The list is automatically set by the eNB.";
      notife:notifiable-state-data true;
      type erienmnrmlrat:ddt-Lrat_ExternalEUtranCellFDD_additionalFreqBandList;
    }
    list mbsfnSubframeAlloc {
      min-elements 0;
      max-elements 8;
      key auto-generated-struct-key;
      leaf auto-generated-struct-key {
        type uint16;
        description "This leaf has been injected to allow for struct instances in a sequence to be ordered.";
        mandatory true;
      }
      description "Shows the subframes that are reserved for MBSFN in DL.";
      status deprecated {
        yexte:status-information "Since 17.Q2. Replaced by commonSFAllocList. Planned to be removed.";
      }
      erienmyext:enm-type STRUCT;
      uses erienmnrmlrat:struct-MbsfnSubframeConfigRO;
    } // end 'list mbsfnSubframeAlloc'
    leaf createdBy {
      config false;
      description "Indicates whether the MO has been created by the Automated Neighbor Relations (ANR) function or operator or X2";
      notife:notifiable-state-data true;
      type erienmnrmlrat:enum-CreatedByEutran;
    }
    leaf-list reservedBy {
      min-elements 0;
      config false;
      description "Lists EUtranCellRelation managed object instances that reserve this managed object instance.";
      yexte:dependencies "The managed object cannot be deleted if it is reserved.";
      notife:notifiable-state-data true;
      erienmyext:enm-type MOREF;
      type string;
    }
    leaf lastModification {
      config false;
      description "Indicates whether the MO was last modified by the Automated Neighbor Relations (ANR) function or operator or X2 and if the MO is to be deleted who triggered the deletion";
      notife:notifiable-state-data true;
      type erienmnrmlrat:enum-LastModificationEutran;
    }
    list commonSFAllocList {
      min-elements 0;
      max-elements 8;
      key auto-generated-struct-key;
      leaf auto-generated-struct-key {
        type uint16;
        description "This leaf has been injected to allow for struct instances in a sequence to be ordered.";
        mandatory true;
      }
      description "Shows the subframes that are reserved for MBSFN in DL.";
      erienmyext:enm-type STRUCT;
      uses erienmnrmlrat:struct-SubFrameConfigRO;
    } // end 'list commonSFAllocList'
    leaf localCellId {
      description "RBS internal ID attribute for the ExternalEUtranCellFDD. Must be unique in the RBS. Together with the Node ID and Public Land Mobile Network (PLMN) ID this is a globally unique eUTRAN Cell ID (ECGI).";
      mandatory true;
      type erienmnrmlrat:ddt-Lrat_ExternalEUtranCellFDD_localCellId;
    }
    leaf remoteCellState {
      erienmyext:no-notification;
      config false;
      description "Reflects whether the indicated cell is currently able to serve as an SCell. The remote cell must be operState ENABLED and adminState UNLOCKED.";
      yexte:dependencies "Depends on X2 connection being operational and software compatibility.";
      type erienmnrmlrat:enum-OperState;
    }
    leaf-list activeServiceAreaId {
      min-elements 0;
      max-elements 64;
      description "The active MBMS Service Area Identity of an external cell.";
      type erienmnrmlrat:ddt-Lrat_ExternalEUtranCellFDD_activeServiceAreaId;
    }
    action changeFrequency {
      input {
        leaf earfcn {
          mandatory true;
          description "Changes the frequency of the external cell. If not already existing an instance of EUtranFrequency with corresponding EUtranFreqRelation is created. For all EUtranCells within the eNB with existing cell relations to the updated external cell, new EUtranCellRelation instances are created.\n";
          type erienmnrmlrat:ddt-ExternalEUtranCellFDD_changeFrequency_earfcn;
        }
      }
    }
  } // end 'grouping moc-ExternalEUtranCellFDD'
  grouping moc-GeranFreqGroup-keys {
    description "Key(s) for MOC GeranFreqGroup";
    leaf id {
      erienmyext:no-notification;
      description "The value component of the Relative Distinguished Name (RDN).\n";
      mandatory true;
      yexte:ecim-name geranFreqGroupId;
      type string;
    }
  } // end 'grouping moc-GeranFreqGroup-keys'
  grouping moc-GeranFreqGroup {
    description "This managed object contains information about a set of Geran ARFCN values, which represent a group of Geran frequencies.\nIt is not possible to include Geran frequencies from both band 1800 and 1900 within the same GeranFreqGroup.\n\n";
    leaf frequencyGroupId {
      yexte:restricted;
      description "This ID identifies the GeranFreqGroup in the network.\n";
      mandatory true;
      type erienmnrmlrat:ddt-Lrat_GeranFreqGroup_frequencyGroupId;
    }
    leaf userLabel {
      description "Label for free use.\n";
      type erienmnrmlrat:ddt-Lrat_GeranFreqGroup_userLabel;
    }
    leaf-list reservedBy {
      min-elements 0;
      config false;
      description "Contains a list of MO instances that reserve this MO instance.\n";
      yexte:dependencies "The MO may not be deleted if it is reserved.";
      notife:notifiable-state-data true;
      erienmyext:enm-type MOREF;
      type string;
    }
  } // end 'grouping moc-GeranFreqGroup'
  grouping moc-ResourcePartitions-keys {
    description "Key(s) for MOC ResourcePartitions";
    leaf id {
      erienmyext:no-notification;
      description "The value component of the RDN.";
      mandatory true;
      yexte:ecim-name resourcePartitionsId;
      type string;
    }
  } // end 'grouping moc-ResourcePartitions-keys'
  grouping moc-ResourcePartitions {
    description "Set of resource partitions defined for use in the node.\n\nThe RDN of this MO is ResourcePartitions=1.";
  } // end 'grouping moc-ResourcePartitions'
  grouping moc-ReportConfigA5-keys {
    description "Key(s) for MOC ReportConfigA5";
    leaf id {
      erienmyext:no-notification;
      description "The value component of the Relative Distinguished Name (RDN).";
      mandatory true;
      yexte:ecim-name reportConfigA5Id;
      type string;
    }
  } // end 'grouping moc-ReportConfigA5-keys'
  grouping moc-ReportConfigA5 {
    description "This managed object contains report configuration settings for the A5 event measurements. The A5 event is used to detect when serving cell becomes worse than threshold1, and neighbor cell becomes better than threshold2. The actual threshold values used can be adjusted by frequency relation related offsets if the feature Multi-Layer Service-Triggered Mobility (MLSTM) is enabled.\n\nThe RDN of this MO is ReportConfigA5=1.";
    leaf triggerQuantityA5 {
      description "The quantity that triggers the eventA5 for the eventA5 measurement.";
      yexte:takes-effect "New connection";
      type erienmnrmlrat:enum-TriggerQuantity;
      default RSRP;
    }
    leaf a5Threshold2Rsrq {
      description "The Reference Signal Received Quality (RSRQ) threshold2 value for eventA5.";
      yexte:takes-effect "New connection";
      yexte:dependencies "Only used if triggerQuantityA5 is set to RSRQ.";
      type erienmnrmlrat:ddt-Lrat_ReportConfigA5_a5Threshold2Rsrq;
      default -195;
    }
    leaf a5Threshold2Rsrp {
      description "The Reference Signal Received Power (RSRP) threshold2 value for eventA5.";
      yexte:takes-effect "New connection";
      yexte:dependencies "Only used if triggerQuantityA5 is set to RSRP.";
      type erienmnrmlrat:ddt-Lrat_ReportConfigA5_a5Threshold2Rsrp;
      default -136;
    }
    leaf timeToTriggerA5 {
      description "Time-to-trigger value for event A5. If timeToTriggerA5Rsrq is -1, this attribute is used for both RSRP and RSRQ. But if not set to -1, this attribute is used only for RSRP.";
      yexte:takes-effect "New connection";
      type erienmnrmlrat:ddt-Lrat_ReportConfigA5_timeToTriggerA5;
      default 640;
    }
    leaf hysteresisA5 {
      description "The hysteresis value for the eventA5 measurement.";
      yexte:takes-effect "New connection";
      type erienmnrmlrat:ddt-Lrat_ReportConfigA5_hysteresisA5;
      default 10;
    }
    leaf hysteresisA5RsrqOffset {
      description "Offset to obtain the Hysteresis for A5 measurement for trigger quantity RSRQ. hysteresisA5Rsrq = hysteresisA5 + hysteresisA5RsrqOffset";
      yexte:takes-effect "New connection";
      yexte:dependencies "Feature Mobility Control at Poor Coverage must be active.";
      type erienmnrmlrat:ddt-Lrat_ReportConfigA5_hysteresisA5RsrqOffset;
      default 0;
    }
    leaf a5Threshold1Rsrp {
      description "The Reference Signal Received Power (RSRP) threshold1 value for eventA5.";
      yexte:takes-effect "New connection";
      yexte:dependencies "Only used if triggerQuantityA5 is set to RSRP.";
      type erienmnrmlrat:ddt-Lrat_ReportConfigA5_a5Threshold1Rsrp;
      default -140;
    }
    leaf timeToTriggerA5Rsrq {
      description "Time-to-trigger value for event A5 with trigger quantity RSRQ. If set to -1, this attribute is not used for report configuration.";
      yexte:takes-effect "New connection";
      yexte:dependencies "Feature Mobility Control at Poor Coverage must be active.";
      type erienmnrmlrat:ddt-Lrat_ReportConfigA5_timeToTriggerA5Rsrq;
      default -1;
    }
    leaf a5Threshold1Rsrq {
      description "The Reference Signal Received Quality (RSRQ) threshold1 value for eventA5.";
      yexte:takes-effect "New connection";
      yexte:dependencies "Only used if triggerQuantityA5 is set to RSRQ.";
      type erienmnrmlrat:ddt-Lrat_ReportConfigA5_a5Threshold1Rsrq;
      default -195;
    }
  } // end 'grouping moc-ReportConfigA5'
  grouping moc-SubscriberGroupProfile-keys {
    description "Key(s) for MOC SubscriberGroupProfile";
    leaf id {
      erienmyext:no-notification;
      description "The value component of the RDN.";
      mandatory true;
      yexte:ecim-name subscriberGroupProfileId;
      type string;
    }
  } // end 'grouping moc-SubscriberGroupProfile-keys'
  grouping moc-SubscriberGroupProfile {
    description "Contains set of trigger conditions used to select subset of all subscribers as well as a number of parameters/functions that are applied to this group.";
    leaf userLabel {
      description "Label for free use.";
      yexte:takes-effect "New connection";
      type erienmnrmlrat:ddt-Lrat_SubscriberGroupProfile_userLabel;
    }
    list bearerTriggerList {
      min-elements 0;
      max-elements 5;
      key auto-generated-struct-key;
      leaf auto-generated-struct-key {
        type uint16;
        description "This leaf has been injected to allow for struct instances in a sequence to be ordered.";
        mandatory true;
      }
      description "Bearer parameters included in subscriber profile. Evaluated for a UE when a bearer is added, modified or released. If empty, all bearers are included. One element indicates that only that set of bearer parameters makes the trigger evaluate to TRUE. Multiple elements indicate a bearer needs to fulfill at least one of them for the trigger to evaluate to TRUE. For a UE to be part of this subscriber group, it must be evaluated to true in these trigger lists: spidTriggerList, bearerTriggerList and customTriggerList. If all three arrays are empty, all UEs match. If all lists are not empty, UE must match at least one value in each list.";
      erienmyext:enm-type STRUCT;
      uses erienmnrmlrat:struct-BearerTriggerElement;
    } // end 'list bearerTriggerList'
    leaf-list subGroupConfiguration2 {
      min-elements 0;
      max-elements 5;
      description "Config 2 of the subscriber group profile.";
      yexte:disturbances "Changing this attribute can cause loss of traffic.";
      yexte:takes-effect "New connection";
      type erienmnrmlrat:ddt-Lrat_SubscriberGroupProfile_subGroupConfiguration2;
    }
    leaf-list subGroupConfiguration1 {
      min-elements 0;
      max-elements 5;
      description "Config 1 of the subscriber group profile.";
      yexte:disturbances "Changing this attribute can cause loss of traffic.";
      yexte:takes-effect "New connection";
      type erienmnrmlrat:ddt-Lrat_SubscriberGroupProfile_subGroupConfiguration1;
    }
    leaf-list subGroupConfiguration4 {
      min-elements 0;
      max-elements 5;
      description "Config 4 of the subscriber group profile.";
      yexte:disturbances "Changing this attribute can cause loss of traffic.";
      yexte:takes-effect "New connection";
      type erienmnrmlrat:ddt-Lrat_SubscriberGroupProfile_subGroupConfiguration4;
    }
    leaf-list subGroupConfiguration3 {
      min-elements 0;
      max-elements 10;
      description "Config 3 of the subscriber group profile.";
      yexte:disturbances "Changing this attribute can cause loss of traffic.";
      yexte:takes-effect "New connection";
      type erienmnrmlrat:ddt-Lrat_SubscriberGroupProfile_subGroupConfiguration3;
    }
    leaf-list subGroupConfiguration6 {
      min-elements 0;
      max-elements 20;
      description "Config 6 of the subscriber group profile.";
      yexte:disturbances "Changing this attribute can cause loss of traffic.";
      yexte:takes-effect "New connection";
      type erienmnrmlrat:ddt-Lrat_SubscriberGroupProfile_subGroupConfiguration6;
    }
    leaf-list subGroupConfiguration5 {
      min-elements 0;
      max-elements 5;
      description "Config 5 of the subscriber group profile.";
      yexte:disturbances "Changing this attribute can cause loss of traffic.";
      yexte:takes-effect "New connection";
      type erienmnrmlrat:ddt-Lrat_SubscriberGroupProfile_subGroupConfiguration5;
    }
    leaf preschedulingMode {
      description "Defines prescheduling mode for this subscriber group.";
      type erienmnrmlrat:enum-PreschedulingMode;
      default NO_OVERRIDE;
    }
    leaf customTriggerType {
      description "Type of customTriggerList. If set to 0 (TRIGGER_NOT_USED), then customTriggerList evaluates to TRUE, irrespective of its content.";
      yexte:disturbances "Changing this attribute can cause loss of traffic.";
      yexte:takes-effect "New connection";
      type erienmnrmlrat:enum-CustomTriggerType;
      default TRIGGER_NOT_USED;
    }
    leaf profileIndex {
      config false;
      description "Subscriber group profile index.";
      notife:notifiable-state-data true;
      type erienmnrmlrat:ddt-Lrat_SubscriberGroupProfile_profileIndex;
    }
    leaf-list spidTriggerList {
      min-elements 0;
      max-elements 5;
      description "SPID values included in subscriber profile. If empty, all SPIDs are included. One value indicates that only this SPID makes the trigger evaluate to TRUE. Multiple values indicates UE must fulfill at least one of them for the trigger to evaluate to TRUE. The value 0 matches all UEs without any assigned SPID. Note: For a UE to be part of this subscriber group, it must be evaluated to true in these trigger lists: spidTriggerList, bearerTriggerList and customTriggerList. If all three arrays are empty, all UEs match. If all lists are not empty, UE must match at least one value in each list.";
      yexte:disturbances "Changing this attribute can cause loss of traffic.";
      yexte:takes-effect "New connection";
      type erienmnrmlrat:ddt-Lrat_SubscriberGroupProfile_spidTriggerList;
    }
    leaf pZeroNominalPuschOffset {
      description "Defines offset to pZeroNominalPusch as defined in EUtranCellFDD/TDD.";
      yexte:disturbances "Changing this attribute can cause loss of traffic.";
      type erienmnrmlrat:ddt-Lrat_SubscriberGroupProfile_pZeroNominalPuschOffset;
      default 0;
    }
    leaf qciOffsetForQCI9 {
      description "Defines QCI9 bearer offset. Apply it to map this QCI into range of operator-defined QCIs. If UE fulfills subscriber profile conditions, QCI9 bearer can then 1) assign different QoS parameters than normal, and 2) be observed by QCI counters.";
      yexte:disturbances "Changing this attribute can cause loss of traffic.";
      yexte:takes-effect "New connection";
      type erienmnrmlrat:ddt-Lrat_SubscriberGroupProfile_qciOffsetForQCI9;
      default 0;
    }
    leaf drxMode {
      description "Defines DRX mode for this subscriber group.";
      type erienmnrmlrat:enum-DrxMode;
      default NO_OVERRIDE;
    }
    leaf qciOffsetForQCI8 {
      description "Defines QCI8 bearer offset. Apply it to map this QCI into range of operator-defined QCIs. If UE fulfills subscriber profile conditions, QCI8 bearer can then 1) assign different QoS parameters than normal, and 2) be observed by QCI counters.";
      yexte:disturbances "Changing this attribute can cause loss of traffic.";
      yexte:takes-effect "New connection";
      type erienmnrmlrat:ddt-Lrat_SubscriberGroupProfile_qciOffsetForQCI8;
      default 0;
    }
    leaf pZeroNominalPucchOffset {
      description "Defines offset to pZeroNominalPucch as defined in EUtranCellFDD/TDD.";
      yexte:disturbances "Changing this attribute can cause loss of traffic.";
      type erienmnrmlrat:ddt-Lrat_SubscriberGroupProfile_pZeroNominalPucchOffset;
      default 0;
    }
    leaf qciOffsetForQCI7 {
      description "Defines QCI7 bearer offset. Apply it to map this QCI into range of operator-defined QCIs. If UE fulfills subscriber profile conditions, QCI7 bearer can then 1) assign different QoS parameters than normal, and 2) be observed by QCI counters.";
      yexte:disturbances "Changing this attribute can cause loss of traffic.";
      yexte:takes-effect "New connection";
      type erienmnrmlrat:ddt-Lrat_SubscriberGroupProfile_qciOffsetForQCI7;
      default 0;
    }
    leaf qciOffsetForQCI6 {
      description "Defines QCI6 bearer offset. Apply it to map this QCI into range of operator-defined QCIs. If UE fulfills subscriber profile conditions, QCI6 bearer can then 1) assign different QoS parameters than normal, and 2) be observed by QCI counters.";
      yexte:disturbances "Changing this attribute can cause loss of traffic.";
      yexte:takes-effect "New connection";
      type erienmnrmlrat:ddt-Lrat_SubscriberGroupProfile_qciOffsetForQCI6;
      default 0;
    }
    leaf preschedProfileRef {
      description "Prescheduling profile associated with this subscriber group.\nPoints to MO PreschedProfile. If not set, PreschedulingProfile setting is used for this subscriber group.";
      erienmyext:enm-type MOREF;
      type string;
    }
    leaf profilePriority {
      description "Relative priority among subscriber group profiles. If UE fulfills more than one profile, subscriber group profile with highest relative priority is applied. Higher value of profile priority gives higher priority.";
      yexte:takes-effect "New connection";
      type erienmnrmlrat:ddt-Lrat_SubscriberGroupProfile_profilePriority;
      default 1;
    }
    leaf-list customTriggerList {
      min-elements 0;
      max-elements 20;
      description "Values from customTriggerType included in subscriber profile. If empty, list is evaluated to TRUE. Otherwise it is evaluated based on what type it is. Attribute customTriggerType defines type. Note: For a UE to be part of this subscriber group, it must be evaluated to true in these trigger lists: spidTriggerList and customTriggerList. If all three arrays are empty, all UEs match. If all lists are not empty, UE must match at least one value in each list.";
      yexte:disturbances "Changing this attribute can cause loss of traffic.";
      yexte:takes-effect "Depends on prototypeTriggerType.";
      type erienmnrmlrat:ddt-Lrat_SubscriberGroupProfile_customTriggerList;
    }
    leaf caRateAdjustCoeff {
      description "Used to adjust factor of CC rate for CA UEs in this subscriber group, which is used in scheduler's proportional fairness algorithm. If set to -1, the value of caRateAdjustCoeff in CarrierAggregationFunction is used.";
      type erienmnrmlrat:ddt-Lrat_SubscriberGroupProfile_caRateAdjustCoeff;
      default -1;
    }
    leaf-list subGroupConfiguration7 {
      min-elements 0;
      max-elements 10;
      description "Config 7 of the subscriber group profile.";
      yexte:disturbances "Changing this attribute can cause loss of traffic.";
      yexte:takes-effect "New connection";
      type erienmnrmlrat:ddt-Lrat_SubscriberGroupProfile_subGroupConfiguration7;
    }
  } // end 'grouping moc-SubscriberGroupProfile'
  grouping moc-PtmIflbConfig-keys {
    description "Key(s) for MOC PtmIflbConfig";
    leaf id {
      erienmyext:no-notification;
      description "The value component of the RDN.";
      mandatory true;
      yexte:ecim-name ptmIflbConfigId;
      type string;
    }
  } // end 'grouping moc-PtmIflbConfig-keys'
  grouping moc-PtmIflbConfig {
    description "Contains PTM specific parameters affecting Inter-Frequency Load Balancing feature.\n\nThe RDN of this MO is PtmIflbConfig=1.";
    leaf stopIncomingIflbThreshold {
      description "If PtmCellProfile::cellType is set to PRIORITY and this threshold is exceeded by cell subscription ratio, cell notifies neighboring cells to stop IFLB towards cell.\nNo effect when PtmCellProfile::cellType is set to NON_PRIORITY.";
      yexte:disturbances "Changing this attribute can affect traffic.";
      yexte:dependencies stopIncomingIFLBThreshold<=lbEUtranTriggerOffloadThreshold;
      type erienmnrmlrat:ddt-Lrat_PtmIflbConfig_stopIncomingIflbThreshold;
      default 60;
    }
    leaf stopOutgoingIflbEnabled {
      description "If PtmCellProfile::cellType is set to NON_PRIORITY and this parameter is set to TRUE, cell stops outgoing load balancing towards cells that broadcast Stop Incoming IFLB Traffic Load State.\nNo effect when PtmCellProfile::cellType is set to PRIORITY.";
      yexte:disturbances "Changing this attribute can affect traffic.";
      type boolean;
      default false;
    }
  } // end 'grouping moc-PtmIflbConfig'
  grouping moc-ReportConfigA4-keys {
    description "Key(s) for MOC ReportConfigA4";
    leaf id {
      erienmyext:no-notification;
      description "The value component of the Relative Distinguished Name (RDN).";
      mandatory true;
      yexte:ecim-name reportConfigA4Id;
      type string;
    }
  } // end 'grouping moc-ReportConfigA4-keys'
  grouping moc-ReportConfigA4 {
    description "This managed object contains report configuration settings for the A4 event measurements. The A4 event is used to detect when neighbor cell becomes better than threshold.\n\nThe RDN of this MO is ReportConfigA4=1.";
    leaf a4ThresholdRsrq {
      description "The Reference Signal Received Quality (RSRQ) threshold value for eventA4.";
      yexte:takes-effect "New connection";
      yexte:dependencies "Only used if triggerQuantityA4 is set to RSRQ.";
      type erienmnrmlrat:ddt-Lrat_ReportConfigA4_a4ThresholdRsrq;
      default -195;
    }
    leaf triggerQuantityA4 {
      description "The quantity that triggers the eventA4 for the eventA4 measurement.";
      yexte:takes-effect "New connection";
      type erienmnrmlrat:enum-TriggerQuantity;
      default RSRP;
    }
    leaf hysteresisA4 {
      description "The hysteresis value for the eventA4 measurement.";
      yexte:takes-effect "New connection";
      type erienmnrmlrat:ddt-Lrat_ReportConfigA4_hysteresisA4;
      default 10;
    }
    leaf a4ThresholdRsrp {
      description "The Reference Signal Received Power (RSRP) threshold value for eventA4.";
      yexte:takes-effect "New connection";
      yexte:dependencies "Only used if triggerQuantityA4 is set to RSRP.";
      type erienmnrmlrat:ddt-Lrat_ReportConfigA4_a4ThresholdRsrp;
      default -140;
    }
    leaf timeToTriggerA4 {
      description "The time-to-trigger value for the eventA4 measurement.";
      yexte:takes-effect "New connection";
      type erienmnrmlrat:ddt-Lrat_ReportConfigA4_timeToTriggerA4;
      default 640;
    }
  } // end 'grouping moc-ReportConfigA4'
  grouping moc-ReportConfigCsfbCdma2000-keys {
    description "Key(s) for MOC ReportConfigCsfbCdma2000";
    leaf id {
      erienmyext:no-notification;
      description "Value component of the RDN";
      mandatory true;
      yexte:ecim-name reportConfigCsfbCdma2000Id;
      type string;
    }
  } // end 'grouping moc-ReportConfigCsfbCdma2000-keys'
  grouping moc-ReportConfigCsfbCdma2000 {
    description "The MO contains report configuration settings for the B1 or B2 event for CDMA2000 1xRTT measurements, used when searching for a suitable target cell when CS Fallback is triggered for the UE.\n\nThe RDN of this MO is ReportConfigCsfbCdma2000=1.";
    leaf thresholdCdma20001xRtt {
      description "Signal Quality in the thresholdCDMA2000, threshold value for eventB1";
      yexte:takes-effect "New connection";
      type erienmnrmlrat:ddt-Lrat_ReportConfigCsfbCdma2000_thresholdCdma20001xRtt;
      default -75;
    }
    leaf timeToTrigger {
      description "Time to trigger value for the eventB1 measurement on CDMA2000";
      yexte:takes-effect "New connection";
      type erienmnrmlrat:ddt-Lrat_ReportConfigCsfbCdma2000_timeToTrigger;
      default 40;
    }
    leaf hysteresis {
      description "Hysteresis value for the eventB1 measurement on CDMA2000";
      yexte:takes-effect "New connection";
      type erienmnrmlrat:ddt-Lrat_ReportConfigCsfbCdma2000_hysteresis;
      default 10;
    }
  } // end 'grouping moc-ReportConfigCsfbCdma2000'
  grouping moc-NonPlannedPciDrxProfile-keys {
    description "Key(s) for MOC NonPlannedPciDrxProfile";
    leaf id {
      erienmyext:no-notification;
      description "The value component of the RDN.";
      mandatory true;
      yexte:ecim-name nonPlannedPciDrxProfileId;
      type string;
    }
  } // end 'grouping moc-NonPlannedPciDrxProfile-keys'
  grouping moc-NonPlannedPciDrxProfile {
    description "Contains DRX profiles, DRX parameters, to map with non-planned PCI, CSG cell and Hybrid CSG cell CGI reading.\n\nThe RDN of this MO is NonPlannedPciDrxProfile=1.";
    leaf nonPlannedPciDrxInactivityTimer {
      description "The number of consecutive PDCCH subframes after successfully decoding a PDCCH that indicates an initial UL or DL user data transmission for this UE. Attribute is only used to read CGI for Non-planned PCI, CSG cell or Hybrid CSG cell. TS36.331 ch. 6.3.2, RRC parameter drx-InactivityTimer.";
      yexte:takes-effect "Object unlocked";
      type erienmnrmlrat:enum-DrxInactivityTimer;
      default PSF2;
    }
    leaf nonPlannedPciOnDurationTimer {
      description "The number of consecutive PDCCH subframes at DRX Cycle initialization. Attribute is only used to read CGI for Non-planned PCI, CSG cell or Hybrid CSG cell. TS36.331 ch. 6.3.2, RRC parameter onDurationTimer.";
      yexte:takes-effect "Object unlocked";
      type erienmnrmlrat:enum-OnDurationTimer;
      default PSF1;
    }
    leaf nonPlannedPciLongDrxCycle {
      description "Value longDrxCycle indicates the number of subframes. Attribute is only used to read CGI for Non-planned PCI, CSG cell or Hybrid CSG cell.";
      yexte:takes-effect "Object unlocked";
      type erienmnrmlrat:enum-LongDrxCycle;
      default SF320;
    }
  } // end 'grouping moc-NonPlannedPciDrxProfile'
  grouping moc-Cdma2000FreqRelation-keys {
    description "Key(s) for MOC Cdma2000FreqRelation";
    leaf id {
      erienmyext:no-notification;
      description "The value component of the Relative Distinguished Name (RDN).";
      mandatory true;
      yexte:ecim-name cdma2000FreqRelationId;
      type string;
    }
  } // end 'grouping moc-Cdma2000FreqRelation-keys'
  grouping moc-Cdma2000FreqRelation {
    description "This Managed Object represents a mobility relation between a EUtranCellFDD or an EUtranCellTDD and a CDMA2000Frequency. It contains parameters that are specific for this relation.\n\nDeleting this MO while the parent EUtranCellFDD/EUtranCellTDD has operationalState set to ENABLED is not recommended as it may affect traffic.\n";
    leaf b2Thr2Cdma2000FreqOffset {
      description "The frequency-relation specific offset for the absolute threshold b2Threshold2Cdma2000, Signal quality in the thresholdCDMA2000 for event B2, used for Multi-Layer Service-Triggered Mobility.";
      yexte:takes-effect "Ongoing connection";
      type erienmnrmlrat:ddt-Lrat_Cdma2000FreqRelation_b2Thr2Cdma2000FreqOffset;
      default 0;
    }
    leaf userLabel {
      description "Label for free use.";
      type erienmnrmlrat:ddt-Lrat_Cdma2000FreqRelation_userLabel;
    }
    leaf connectedModeMobilityPrio {
      description "Prioritizes CDMA2000 frequencies among all frequencies related to the cell for UEs in connected mode.\n(0 means the lowest priority. -1 means the frequency is excluded.)";
      yexte:takes-effect "New connection";
      type erienmnrmlrat:ddt-Lrat_Cdma2000FreqRelation_connectedModeMobilityPrio;
      default 6;
    }
    leaf b2Thr1RsrqCdma2000FreqOffset {
      description "The frequency-relation specific offset for the absolute threshold b2Threshold1Rsrq, RSRQ threshold1 for event B2, used for Multi-Layer Service-Triggered Mobility.";
      yexte:takes-effect "Ongoing connection";
      type erienmnrmlrat:ddt-Lrat_Cdma2000FreqRelation_b2Thr1RsrqCdma2000FreqOffset;
      default 0;
    }
    list qciB2ThrOffsets {
      min-elements 0;
      max-elements 19;
      key auto-generated-struct-key;
      leaf auto-generated-struct-key {
        type uint16;
        description "This leaf has been injected to allow for struct instances in a sequence to be ordered.";
        mandatory true;
      }
      description "Parameters for adding QCI profile and frequency relation specific offsets to B2 threshold values used for mobility decisions. Applicable if Multi-Layer Service-Triggered Mobility (MLSTM) is active.";
      erienmyext:enm-type STRUCT;
      uses erienmnrmlrat:struct-Cdma2000FreqRelQciB2ThrOffsets;
    } // end 'list qciB2ThrOffsets'
    leaf cdma2000FreqRef {
      yexte:restricted;
      description "Reference to the Cdma2000Freq MO";
      mandatory true;
      erienmyext:enm-type MOREF;
      type string;
    }
    leaf b2Thr1RsrpCdma2000FreqOffset {
      description "The frequency-relation specific offset for the absolute threshold b2Threshold1Rsrp, RSRP threshold1 for event B2, used for Multi-Layer Service-Triggered Mobility.";
      yexte:takes-effect "Ongoing connection";
      type erienmnrmlrat:ddt-Lrat_Cdma2000FreqRelation_b2Thr1RsrpCdma2000FreqOffset;
      default 0;
    }
    list b2Cdma2000OffsetPerPC {
      min-elements 0;
      max-elements 2;
      key auto-generated-struct-key;
      leaf auto-generated-struct-key {
        type uint16;
        description "This leaf has been injected to allow for struct instances in a sequence to be ordered.";
        mandatory true;
      }
      description "The frequency-relation specific offset for the absolute threshold, RSRP/RSRQ threshold1 for event B2, used for Multi-Layer Service-Triggered Mobility and High Power UE.";
      erienmyext:enm-type STRUCT;
      uses erienmnrmlrat:struct-B2Cdma2000PCOffsetMCPC;
    } // end 'list b2Cdma2000OffsetPerPC'
    leaf qOffsetFreq {
      description "Indicates a frequency-specific offset to apply when evaluating triggering conditions for measurement reporting.";
      yexte:takes-effect "New connection";
      type erienmnrmlrat:ddt-Lrat_Cdma2000FreqRelation_qOffsetFreq;
      default 0;
    }
  } // end 'grouping moc-Cdma2000FreqRelation'
  grouping moc-GtpPath-keys {
    description "Key(s) for MOC GtpPath";
    leaf id {
      erienmyext:no-notification;
      description "The value component of the RDN.";
      mandatory true;
      yexte:ecim-name gtpPathId;
      type string;
    }
  } // end 'grouping moc-GtpPath-keys'
  grouping moc-GtpPath {
    description "Models GTP-U path between RBS and another node, either SGW or neighbor RBS.\n\nThe RDN of this MO is GtpPath=1.";
    leaf samplingInterval {
      erienmyext:no-notification;
      config false;
      description "Sampling interval used for path. No delay measurements are performed and a 60-second interval is used when sampling interval is set to 0.";
      type erienmnrmlrat:ddt-Lrat_GtpPath_samplingInterval;
    }
    leaf echoPeerStatus {
      erienmyext:no-notification;
      config false;
      description "Peer reachability status for path.";
      type erienmnrmlrat:enum-PeerStatus;
    }
    leaf operationalState {
      erienmyext:no-notification;
      config false;
      description "The operational state. This attribute is set by the application in the RBS.";
      type erienmnrmlrat:enum-OperState;
    }
    leaf localIpAddress {
      erienmyext:no-notification;
      config false;
      description "Local address used for path termination point. Can be IPv4 or IPv6 address.";
      type erienmnrmlrat:ddt-Lrat_GtpPath_localIpAddress;
    }
    leaf remoteIpAddress {
      erienmyext:no-notification;
      config false;
      description "Remote address used for path termination point. Can be IPv4 or IPv6 address.";
      type erienmnrmlrat:ddt-Lrat_GtpPath_remoteIpAddress;
    }
  } // end 'grouping moc-GtpPath'
  grouping moc-QciTable-keys {
    description "Key(s) for MOC QciTable";
    leaf id {
      erienmyext:no-notification;
      description "The value component of the RDN.\n";
      mandatory true;
      yexte:ecim-name qciTableId;
      type string;
    }
  } // end 'grouping moc-QciTable-keys'
  grouping moc-QciTable {
    description "Contains mapping from QCIs to parameters that has impact on QoS for DRBs.\n\nThe RDN of this MO is QciTable=default.";
    leaf-list reservedBy {
      min-elements 0;
      config false;
      description "Contains a list of cells that reserves this MO instance.\n";
      yexte:takes-effect "New connection.";
      notife:notifiable-state-data true;
      erienmyext:enm-type MOREF;
      type string;
    }
  } // end 'grouping moc-QciTable'
  grouping moc-CellResources-keys {
    description "Key(s) for MOC CellResources";
    leaf id {
      status deprecated {
        yexte:status-information "Since 18.Q2. Has no functional behavior. Planned to be removed.";
      }
      erienmyext:no-notification;
      description "The value component of the RDN.";
      mandatory true;
      yexte:ecim-name cellResourcesId;
      type string;
    }
  } // end 'grouping moc-CellResources-keys'
  grouping moc-CellResources {
    description "Set of cell resource partitions defined for use in the node.\n\nThe RDN of this MO is CellResources=1.";
  } // end 'grouping moc-CellResources'
  grouping moc-NodePerformance-keys {
    description "Key(s) for MOC NodePerformance";
    leaf id {
      erienmyext:no-notification;
      description "The value component of the RDN.";
      mandatory true;
      yexte:ecim-name nodePerformanceId;
      type string;
    }
  } // end 'grouping moc-NodePerformance-keys'
  grouping moc-NodePerformance {
    description "Contains parameters related to node level performance improvement.\n\nThe RDN of this MO is NodePerformance=1.";
  } // end 'grouping moc-NodePerformance'
  grouping moc-ReportConfigB1Utra-keys {
    description "Key(s) for MOC ReportConfigB1Utra";
    leaf id {
      erienmyext:no-notification;
      description "The value component of the Relative Distinguished Name (RDN).";
      mandatory true;
      yexte:ecim-name reportConfigB1UtraId;
      type string;
    }
  } // end 'grouping moc-ReportConfigB1Utra-keys'
  grouping moc-ReportConfigB1Utra {
    description "This managed object contains report configuration settings for the B1 event for WCDMA measurements. The B1 event is used to detect when a WCDMA cell becomes better than threshold.\n\nThe RDN of this MO is ReportConfigB1Utra=1.";
    leaf timeToTriggerB1 {
      description "The time to trigger value for the eventB1 measurement on UTRAN.";
      yexte:takes-effect "New connection";
      type erienmnrmlrat:ddt-Lrat_ReportConfigB1Utra_timeToTriggerB1;
      default 640;
    }
    leaf b1ThresholdEcNoUtra {
      description "Ratio of energy per modulation bit to noise spectral density in the ThresholdUTRA, threshold value for eventB1.\nNot applicable for UTRA TDD.";
      yexte:takes-effect "New connection";
      yexte:dependencies "Only used when measQuantityUtraFDD is set to ECNO";
      type erienmnrmlrat:ddt-Lrat_ReportConfigB1Utra_b1ThresholdEcNoUtra;
      default -240;
    }
    leaf hysteresisB1 {
      description "The hysteresis value for the eventB1 measurement on UTRAN";
      yexte:takes-effect "New connection";
      type erienmnrmlrat:ddt-Lrat_ReportConfigB1Utra_hysteresisB1;
      default 10;
    }
    leaf b1ThresholdRscpUtra {
      description "RSCP threshold value for the event B1 measurement for Coverage based IRAT handover to UTRAN.";
      yexte:takes-effect "New connection";
      yexte:dependencies "Only used when measQuantityUtraFDD is set to RSCP";
      type erienmnrmlrat:ddt-Lrat_ReportConfigB1Utra_b1ThresholdRscpUtra;
      default -115;
    }
  } // end 'grouping moc-ReportConfigB1Utra'
  grouping moc-ReportConfigCsg-keys {
    description "Key(s) for MOC ReportConfigCsg";
    leaf id {
      erienmyext:no-notification;
      description "The value component of the RDN.";
      mandatory true;
      yexte:ecim-name reportConfigCsgId;
      type string;
    }
  } // end 'grouping moc-ReportConfigCsg-keys'
  grouping moc-ReportConfigCsg {
    description "Report configuration setting for A5 measurement that assists UE to redirect another EUTRA Inter-frequency. Used for feature Mobility to CSG Cells.\n\nThe RDN of this MO is ReportConfigCsg=1.";
    leaf a5Thr2RsrpAltCsgOffset {
      description "Specific offset for redirecting to alternative frequencies for the absolute threshold ReportConfigA5::a5Threshold2Rsrp.";
      yexte:takes-effect "New connection";
      type erienmnrmlrat:ddt-Lrat_ReportConfigCsg_a5Thr2RsrpAltCsgOffset;
      default 0;
    }
    leaf timeToTriggerA5AltCsg {
      description "The time-to-trigger value for event A5-RSRP measurement used for redirecting to alternative frequency.";
      yexte:takes-effect "New connection";
      type erienmnrmlrat:ddt-Lrat_ReportConfigCsg_timeToTriggerA5AltCsg;
      default 0;
    }
    leaf a5Thr1RsrpAltCsgOffset {
      description "Specific offset for redirecting to alternative frequencies for the absolute threshold ReportConfigA5::a5Threshold1Rsrp.";
      yexte:takes-effect "New connection";
      type erienmnrmlrat:ddt-Lrat_ReportConfigCsg_a5Thr1RsrpAltCsgOffset;
      default 0;
    }
    leaf hysteresisA5AltCsg {
      description "The hysteresis value for the event A5-RSRP measurement used for redirecting to alternative frequency.";
      yexte:takes-effect "New connection";
      type erienmnrmlrat:ddt-Lrat_ReportConfigCsg_hysteresisA5AltCsg;
      default 10;
    }
  } // end 'grouping moc-ReportConfigCsg'
  grouping moc-ReportConfigA5UlTrig-keys {
    description "Key(s) for MOC ReportConfigA5UlTrig";
    leaf id {
      erienmyext:no-notification;
      description "The value component of the RDN.";
      mandatory true;
      yexte:ecim-name reportConfigA5UlTrigId;
      type string;
    }
  } // end 'grouping moc-ReportConfigA5UlTrig-keys'
  grouping moc-ReportConfigA5UlTrig {
    description "Contains report configuration settings for the A5 event for inter-frequency LTE measurements initiated by Uplink-Triggered Inter-Frequency Mobility. The actual threshold values used can be adjusted by frequency relation or QCI related offsets if the feature Multi-Layer Service-Triggered Mobility (MLSTM) is enabled.\n\nThe RDN of this MO is ReportConfigA5UlTrig=1.";
    leaf a5Threshold2Rsrq {
      description "The Reference Signal Received Quality (RSRQ) threshold2 value for event A5.";
      yexte:takes-effect "New connection";
      yexte:dependencies "Only used if bothA5RsrpRsrqCheck is set to TRUE.";
      type erienmnrmlrat:ddt-Lrat_ReportConfigA5UlTrig_a5Threshold2Rsrq;
      default -195;
    }
    leaf a5Threshold2Rsrp {
      description "The Reference Signal Received Power (RSRP) threshold2 value for eventA5.";
      yexte:takes-effect "New connection";
      type erienmnrmlrat:ddt-Lrat_ReportConfigA5UlTrig_a5Threshold2Rsrp;
      default -140;
    }
    leaf timeToTriggerA5 {
      description "Time-to-trigger value for event A5.";
      yexte:takes-effect "New connection";
      type erienmnrmlrat:ddt-Lrat_ReportConfigA5UlTrig_timeToTriggerA5;
      default 640;
    }
    leaf hysteresisA5 {
      description "The hysteresis value for the eventA5.";
      yexte:takes-effect "New connection";
      type erienmnrmlrat:ddt-Lrat_ReportConfigA5UlTrig_hysteresisA5;
      default 10;
    }
    leaf reportIntervalA5 {
      description "The interval for event triggered periodical reporting for A5 event.";
      yexte:takes-effect "New connection";
      type erienmnrmlrat:enum-ReportInterval;
      default MS_2048;
    }
    leaf a5Threshold1Rsrp {
      description "The Reference Signal Received Power (RSRP) threshold1 value for eventA5.";
      yexte:takes-effect "New connection";
      type erienmnrmlrat:ddt-Lrat_ReportConfigA5UlTrig_a5Threshold1Rsrp;
      default -44;
    }
    leaf a5Threshold1Rsrq {
      description "The Reference Signal Received Quality (RSRQ) threshold1 value for event A5.";
      yexte:takes-effect "New connection";
      yexte:dependencies "Only used if bothA5RsrpRsrqCheck is set to TRUE.";
      type erienmnrmlrat:ddt-Lrat_ReportConfigA5UlTrig_a5Threshold1Rsrq;
      default -30;
    }
  } // end 'grouping moc-ReportConfigA5UlTrig'
  grouping moc-ENodeBFunction-keys {
    description "Key(s) for MOC ENodeBFunction";
    leaf id {
      erienmyext:no-notification;
      description "The value component of the RDN.\n";
      mandatory true;
      yexte:ecim-name eNodeBFunctionId;
      type string;
    }
  } // end 'grouping moc-ENodeBFunction-keys'
  grouping moc-ENodeBFunction {
    description "The RDN of this MO is ENodeBFunction=1.";
    leaf release {
      config false;
      description "The product release of the ManagedFunction.\nIt commonly contains the Managed Function release, for example  L12.0, 13A, R1A ";
      notife:notifiable-state-data true;
      type string;
    }
    leaf timePhaseMaxDeviationOtdoa {
      description "The maximum allowed time and phase deviation for time and phase synchronization of the eNodeB. It is the deviation that is allowed for Observed Time Difference of Arrival (OTDOA) Support to function. When the limit is exceeded, the service is deactivated.";
      yexte:disturbances "Traffic can be affected if this attribute is changed. It can cause malfunction of the Observed Time Difference of Arrival (OTDOA) Support feature due to the time and phase deviation for time and phase synchronization of the eNodeB.";
      type erienmnrmlrat:ddt-Lrat_ENodeBFunction_timePhaseMaxDeviationOtdoa;
      default 9;
    }
    leaf s1GtpuEchoFailureAction {
      description "S1-U failure action.";
      type erienmnrmlrat:enum-GtpuEchoFailureAction;
      default NONE;
    }
    leaf tRelocOverallValue {
      status deprecated {
        yexte:status-information "Since L16B. Replaced by attribute tRelocOverall. Planned to be removed.";
      }
      description "Supervision timer of the outgoing S1/X2/intra-eNodeB handover execution procedure according to 3GPP TS 36.413 and TS 36.423.\nIf the feature Multi-Target RRC Connection Re-establishment is active this timer also supervises the Context Fetch procedure.\n";
      yexte:takes-effect "New connection";
      type erienmnrmlrat:ddt-Lrat_ENodeBFunction_tRelocOverallValue;
      default 5;
    }
    leaf iuaBbmResourceLimit {
      description "Maximum percentage of UL PRBs and UL SEs for each TTI that IUA can use at BBM level. Minimum value of 1 means 1 UL PRB and 1 UL SE for each TTI. Ceiling function is applied while calculating other values. For example, at BBM level, if there are 128 UL SEs for each TTI with iuaBbmResourceLimit set to 20, maximum SEs IUA can use for each TTI is (20% of 128) = 26.";
      type erienmnrmlrat:ddt-Lrat_ENodeBFunction_iuaBbmResourceLimit;
      default 20;
    }
    leaf minRandc {
      description "Rand range datatype is the eight most significant bits (MSB) of the Rand used for authentication.\nThis attribute controls the minimum random number value that can be generated. Typically a range of random numbers is allocated to each system using this attribute.";
      yexte:dependencies "minRandc < maxRandc";
      type erienmnrmlrat:ddt-Lrat_ENodeBFunction_minRandc;
      default 1;
    }
    leaf adaptiveRlcRetxDl {
      status deprecated {
        yexte:status-information "Since L16B. Has no functional behavior. Planned to be removed.";
      }
      description "Shows if Adaptive RLC Retransmission in DL is active or not.";
      type boolean;
      default false;
    }
    leaf timePhaseSynchStateMbms {
      erienmyext:no-notification;
      config false;
      description "Set to false when the Multimedia Broadcast Multicast Service (MBMS) feature is degraded due to time and phase synchronization accuracy requirements not fulfilled, otherwise it is set to true.";
      type boolean;
    }
    leaf tddVoipDrxProfileId {
      description "DrxProfile ID used for TDD VOIP bearers on a mixed FDD/TDD eNodeB. The default value results in TDD using the same DrxProfile as FDD for VOIP bearers.";
      yexte:takes-effect "New connection";
      type erienmnrmlrat:ddt-Lrat_ENodeBFunction_tddVoipDrxProfileId;
      default -1;
    }
    leaf timePhaseSynchStateOtdoa {
      erienmyext:no-notification;
      config false;
      description "Set to false when the Observed Time Difference of Arrival (OTDOA) feature is degraded due to time and phase synchronization accuracy requirements not fulfilled, otherwise it is set to true.";
      type boolean;
    }
    leaf ipsecEpAddressRef {
      description "The local outer address used for this node. Reference to an AddressIPv4 MO or an IpAccessHostEt MO.";
      yexte:disturbances "Changing this attribute can affect traffic.";
      erienmyext:enm-type MOREF;
      type string;
    }
    leaf licDlBbPercentileConf {
      description "The percentile to use for the counter BbProcessingResource::pmLicDlCapActual.";
      type erienmnrmlrat:ddt-Lrat_ENodeBFunction_licDlBbPercentileConf;
      default 90;
    }
    leaf biasThpWifiMobility {
      description "In order to send a UE to WiFi, a throughput comparison is made between WiFi and LTE.\nFor comparisons made in eNodeB, a UE is admitted to WiFi if, WiFi throughput > biasThpWifiMobility * LTE throughput.";
      yexte:disturbances "Changing this attribute can affect traffic";
      type erienmnrmlrat:ddt-Lrat_ENodeBFunction_biasThpWifiMobility;
      default 10;
    }
    leaf tOutgoingHoExecCdma1xRtt {
      description "Supervision timer of the outgoing LTE to CDMA 1xRtt handover execution procedure.";
      yexte:takes-effect "Cell lock/unlock";
      type erienmnrmlrat:ddt-Lrat_ENodeBFunction_tOutgoingHoExecCdma1xRtt;
      default 5;
    }
    leaf prioritizeAdditionalBands {
      description "When enabled, additional frequency bands have higher priority than primary frequency band when considering whether intra-cell handover will improve secondary cell availability.";
      yexte:precondition "useBandPrioritiesInSCellEval must be enabled.";
      type boolean;
      default false;
    }
    leaf maxNrOfEnbPartnersEranUlComp {
      description "Max number of Elastic RAN UL CoMP candidate partners. Currently only 0..6 is supported and 7..20 will be considered as 6.";
      yexte:takes-effect "Next tunnel setup";
      type erienmnrmlrat:ddt-Lrat_ENodeBFunction_maxNrOfEnbPartnersEranUlComp;
      default 6;
    }
    leaf s1GtpuEchoEnable {
      description "If the node monitors and measures delay for all S1-U termination points or not.";
      yexte:dependencies "For DU Radio Node:\nIf feature Transport Path Characteristics Monitoring is activated, and peer node supports delay measurements, delay measurements are performed and monitoring interval is 5 seconds.\nIf feature Transport Path Characteristics Monitoring is activated, and peer node does not support delay measurements, delay measurements are not performed and monitoring interval is 60 seconds.\nIf feature Transport Path Characteristics Monitoring is not activated, monitoring is not enabled.\nFor Baseband Radio Node:\nIf feature Transport Path Characteristics Monitoring is activated, and peer node supports delay measurements, delay measurements are performed and monitoring interval is determined by s1GtpuEchoInterval.\nIf feature Transport Path Characteristics Monitoring is not activated, or peer node does not support delay measurements,\ndelay measurements are not performed and monitoring interval is 60 seconds.";
      type erienmnrmlrat:enum-GtpuEchoEnable;
      default DISABLED;
    }
    container interNodalProtVersions {
      description "Protocol versions for inter-nodal features.";
      erienmyext:enm-type STRUCT;
      uses erienmnrmlrat:struct-InterNodalProtocolVerRO;
    } // end 'container interNodalProtVersions'
    leaf upX2IpAddressRef {
      description "Refers to the IpAccessHostEt or AddressIPv4/AddressIPv6 instance to use for configuring the IP address for X2 user plane connections.";
      yexte:disturbances "Changing this attribute can affect traffic";
      yexte:takes-effect "Node restart";
      erienmyext:enm-type MOREF;
      type string;
    }
    leaf initPreschedulingEnable {
      description "Indicates that prescheduling is enabled during connection setup phase.";
      yexte:takes-effect "Object unlocked";
      type boolean;
      default true;
    }
    leaf intraEnbHoNasNonDelIndCause {
      description "Set value of Radio Network Cause in the 3GPP 36.413 \"NAS NON DELIVERY INDICATION\" to \"X2 Handover Triggered\" instead of default \"Interaction with other procedure\" for intra eNB handover. Operator may configure it depending on 3rd party MMEs behavior.";
      type boolean;
      default false;
    }
    leaf ulMaxWaitingTimeGlobal {
      description "The targeted maximum allowed time between scheduling occasions of an UL bearer. A bearer that is not scheduled within the specified time is given higher priority. Value 0 means that the higher priority is never applied. It is recommended to set the value =< than the PDB. A value that is set too low can affect other services with higher priority.";
      yexte:disturbances "Changing this attribute can affect performance of all data bearers. A value that is set too low can affect other services with higher priority. A value that is set too high can cause Dynamic UE Admission Control to fail in keeping the cell stable at overload.";
      yexte:dependencies "Only used for Resource Fair Scheduling algorithm. Only relevant if the license for Dynamic UE Admission Control is present and the feature is active.";
      type erienmnrmlrat:ddt-Lrat_ENodeBFunction_ulMaxWaitingTimeGlobal;
      default 0;
    }
    leaf measuringEcgiWithAgActive {
      description "Configures use of autonomous gap as method of CGI measurement. If enabled, capable UEs are configured to use autonomous gap for CGI measurement to target LTE or UTRAN cell.";
      yexte:takes-effect "New connection";
      yexte:dependencies "This attribute is effective only when ANR for LTE or UTRAN feature is activated.";
      type boolean;
      default false;
    }
    leaf sctpX2Ref {
      description "Refers to the SCTP endpoint for X2 control connections.";
      yexte:disturbances "Changing this attribute can affect traffic";
      yexte:takes-effect "Node restart";
      yexte:dependencies "Only takes effect in Baseband Radio Node.";
      erienmyext:enm-type MOREF;
      type string;
    }
    leaf licDlPrbPercentileConf {
      description "The percentile to use for the counter BbProcessingResource::pmLicDlPrbCapActual.";
      type erienmnrmlrat:ddt-Lrat_ENodeBFunction_licDlPrbPercentileConf;
      default 90;
    }
    leaf x2IpAddrViaS1Active {
      description "Indicates if the function X2 IP addresses over S1 is active in the RBS.";
      type boolean;
      default true;
    }
    leaf maxRandc {
      description "Rand range datatype is the eight most significant bits (MSB) of the Rand used for authentication.\nThis attribute controls the maximum random number value that can be generated. Typically a range of random numbers is allocated to each system using this attribute.";
      yexte:dependencies "maxRandc > minRandc";
      type erienmnrmlrat:ddt-Lrat_ENodeBFunction_maxRandc;
      default 255;
    }
    leaf csmMinHighHitThreshold {
      description "Minimum required hit rate to qualify a related cell as high hit rate coverage cell by feature Cell Sleep Mode.";
      type erienmnrmlrat:ddt-Lrat_ENodeBFunction_csmMinHighHitThreshold;
      default 70;
    }
    leaf x2GtpuEchoEnable {
      description "If the node monitors and measures delay for all X2-U termination points or not.";
      yexte:dependencies "For DU Radio Node:\nIf feature Transport Path Characteristics Monitoring is activated, and peer node supports delay measurements, delay measurements are performed and monitoring interval is 1 second.\nIf feature Transport Path Characteristics Monitoring is activated, and peer node does not support delay measurements, delay measurements are not performed and monitoring interval is 60 seconds.\nIf feature Transport Path Characteristics Monitoring is not activated, monitoring is not enabled.\nFor Baseband Radio Node:\nIf feature Transport Path Characteristics Monitoring is activated, and peer node supports delay measurements, delay measurements are performed and monitoring interval is 1 second.\nIf feature Transport Path Characteristics Monitoring is not activated, or peer node does not support delay measurements,\ndelay measurements are not performed and monitoring interval is 60 seconds.";
      type erienmnrmlrat:enum-GtpuEchoEnable;
      default DISABLED;
    }
    leaf s1HODirDataPathAvail {
      description "S1 Handover data forwarding can be of two types, direct and indirect. Direct forwarding requires direct connectivity between source and target eNodeB. This parameter is used to indicate if such direct connectivity exist.";
      yexte:disturbances "Changing this attribute can cause loss of traffic. Possible throughput degradation at S1 HO.";
      yexte:dependencies "Optional Feature Data Forwarding at S1 Handover";
      type boolean;
      default false;
    }
    leaf timePhaseMaxDeviationCdma2000 {
      description "The maximum allowed time and phase deviation for time and phase synchronization of the eNodeB. It is the deviation that is allowed for features related to CDMA2000 fallback and handover to function. When the limit is exceeded, some of the functionality is deactivated.";
      yexte:disturbances "Traffic can be affected if this attribute is changed. It can cause malfunction of the features related to CDMA2000 due to the time and phase deviation for time and phase synchronization of the eNodeB.";
      type erienmnrmlrat:ddt-Lrat_ENodeBFunction_timePhaseMaxDeviationCdma2000;
      default 100;
    }
    leaf releaseInactiveUesInactTime {
      description "Inactivity time value to be used to decide release of inactive UEs at handover.";
      yexte:disturbances "Changing this attribute can cause loss of traffic.";
      type erienmnrmlrat:ddt-Lrat_ENodeBFunction_releaseInactiveUesInactTime;
      default 1;
    }
    leaf interEnbCaTunnelDscp {
      description "DSCP value used for outgoing inter-eNB CA packets on X2.\nIt is recommended to set this to the same value as \"QCI9 - Non-GBR TCP Default Bearer\", as inter-eNB CA benefits should be treated as opportunistic and not allowed to interfere with baseline LTE performance.";
      yexte:disturbances "Changing this attribute can also affect other X2 traffic than CA packets.";
      yexte:takes-effect "Next tunnel setup";
      type erienmnrmlrat:ddt-Lrat_ENodeBFunction_interEnbCaTunnelDscp;
      default 14;
    }
    leaf endcPowerOffsetLte {
      description "Offset value to calculate maximum power value for LTE. Same offset applies to NR.\nUsed for semi-static power sharing algorithm when dynamic power sharing is not supported by UE with EN-DC configured.";
      yexte:takes-effect "New connection";
      yexte:dependencies "Only applicable in Baseband Radio Node.";
      type erienmnrmlrat:ddt-Lrat_ENodeBFunction_endcPowerOffsetLte;
      default 3;
    }
    leaf releaseInactiveUesMpLoadLevel {
      description "Minimum MP load level at which inactive UEs are released at handover.";
      type erienmnrmlrat:enum-HoNotAllowedMpLoadLevel;
      default VERY_HIGH_LOAD;
    }
    leaf ulBbCapacityMaxLimit {
      erienmyext:no-notification;
      config false;
      description "Max UL baseband capacity available on unlocked Baseband hardware.\nMaximum limit of UL capacity that can be granted by baseband HWAC. This level sets the limit at emergency unlock.";
      type erienmnrmlrat:ddt-Lrat_ENodeBFunction_ulBbCapacityMaxLimit;
    }
    leaf mtRreWithoutNeighborActive {
      description "Enables or disables the RRC Connection Reestablishment in source cell when there is no target neighbor cell information.";
      yexte:takes-effect "New connection";
      yexte:dependencies "This attribute is only effective when feature Multi-Target RRC Connection Reestablishment is activated.";
      type boolean;
      default true;
    }
    leaf s1GtpuEchoDscp {
      description "DSCP value used for outgoing GTP-U echo request packets on S1-U.";
      type erienmnrmlrat:ddt-Lrat_ENodeBFunction_s1GtpuEchoDscp;
      default 14;
    }
    leaf softLockRwRWaitTimerOperator {
      description "Length of waiting time before soft-lock of cell starts to release all ongoing calls with Release with Redirect (RwR), when operator triggers soft-lock of cell.";
      type erienmnrmlrat:ddt-Lrat_ENodeBFunction_softLockRwRWaitTimerOperator;
      default 60;
    }
    leaf timePhaseMaxDeviationEdrx {
      description "Max allowed deviation for time and phase synchronization of eNodeB for Idle Mode eDRX. Highest value recommended is 50. If higher, deviation is too large for efficient synchronization.";
      yexte:disturbances "Changing this attribute may affect traffic.";
      type erienmnrmlrat:ddt-Lrat_ENodeBFunction_timePhaseMaxDeviationEdrx;
      default 10;
    }
    leaf iuaMaxResourcePerBbm {
      status deprecated {
        yexte:status-information "Since 18.Q3. Replaced by iuaBbmResourceLimit. Planned to be removed.";
      }
      description "Maximum percentage of UL PRBs and SEs that are used by IUA at BBM level.";
      type erienmnrmlrat:ddt-Lrat_ENodeBFunction_iuaMaxResourcePerBbm;
      default 20;
    }
    leaf eNBId {
      description "The ENodeB ID that forms part of the Cell Global Identity, and is also used to identify the node over the S1 interface.";
      yexte:takes-effect "At node restart";
      type erienmnrmlrat:ddt-Lrat_ENodeBFunction_eNBId;
      default -1;
    }
    leaf rrcConnReestActive {
      description "Indicates if the feature RRC Connection Reestablishment is ACTIVATED or DEACTIVATED.";
      type boolean;
      default false;
    }
    leaf csfbUseRegisteredLai {
      description "Whether or not information about Registered LAI received during CS Fallback procedure is considered during selection of GERAN and UTRAN target frequencies.";
      yexte:precondition "This parameter is only relevant for feature 'CS Fallback to GERAN and UTRAN'.";
      type boolean;
      default false;
    }
    leaf dnsLookupTimer {
      description "The interval to perform DNS Lookup to get potential new IP addresses of MME nodes. DNS lookup is performed for the TAI domain name. If the value is set to zero, then no periodic DNS Lookup is done.";
      type erienmnrmlrat:ddt-Lrat_ENodeBFunction_dnsLookupTimer;
      default 0;
    }
    leaf dlBbCapacityMaxLimit {
      erienmyext:no-notification;
      config false;
      description "Max DL baseband capacity available on unlocked Baseband hardware.\nMaximum limit of DL capacity that can be granted by baseband HWAC. This level sets the limit at emergency unlock.";
      type erienmnrmlrat:ddt-Lrat_ENodeBFunction_dlBbCapacityMaxLimit;
    }
    leaf timePhaseSyncStateEdrx {
      erienmyext:no-notification;
      config false;
      description "Set to false when the Idle Mode eDRX feature is degraded due to time and phase synchronization accuracy requirements not fulfilled, otherwise it is set to true.";
      type boolean;
    }
    leaf mfbiSupportPolicy {
      description "A policy parameter that sets the start value of the attribute mfbiSupport when an ExternalENodeBFunction is automatically created by the eNodeB.";
      type boolean;
      default false;
    }
    leaf combCellSectorSelectThreshTx {
      description "Used for PDSCH and PHICH sector selection in combined Cell. For each UE, all sectors received power are compared against the primary sector. Sectors that are below the threshold will be selected.";
      yexte:disturbances "Changes may affect Sector Selection.";
      yexte:takes-effect "Next cell unlock";
      type erienmnrmlrat:ddt-Lrat_ENodeBFunction_combCellSectorSelectThreshTx;
      default 300;
    }
    leaf softLockRwRWaitTimerInternal {
      description "Length of waiting time before soft-lock of cell starts to release all ongoing calls with Release with Redirect (RwR), when eNodeB internally triggers soft-lock of cell.";
      type erienmnrmlrat:ddt-Lrat_ENodeBFunction_softLockRwRWaitTimerInternal;
      default 60;
    }
    leaf dscpLabel {
      description "Static mapping of DiffServ label for control messages, Performance Management (PM), and Non-Access Stratum (NAS).";
      yexte:takes-effect "Node restart";
      yexte:dependencies "Will only be used then dscpUsage is active.";
      type erienmnrmlrat:ddt-Lrat_ENodeBFunction_dscpLabel;
      default 24;
    }
    leaf tS1HoCancelTimer {
      description "The timeout time for receiving HANDOVER CANCEL ACKNOWLEDGE after RBS sent HO CANCEL message to MME.\nValue specifies supervision time of outgoing S1 HO Cancellation according to procedure described in 3GPP TS 36.413 section 8.4.5.";
      yexte:takes-effect "Ongoing connection";
      type erienmnrmlrat:ddt-Lrat_ENodeBFunction_tS1HoCancelTimer;
      default 3;
    }
    leaf timePhaseMaxDeviationTdd {
      description "Max allowed deviation for time and phase synchronization of eNodeB for TDD cells. If exceeded, TDD cells that use this limit are disabled.";
      yexte:disturbances "Changing this attribute can affect traffic.";
      yexte:dependencies "timeAndPhaseSynchAlignment must be true.";
      type erienmnrmlrat:ddt-Lrat_ENodeBFunction_timePhaseMaxDeviationTdd;
      default 15;
    }
    leaf dlMaxWaitingTimeGlobal {
      description "The targeted maximum allowed time between scheduling occasions of a DL bearer. A bearer that is not scheduled within the specified time is given higher priority. Value 0 means that the higher priority is never applied. It is recommended to set the value =< than the PDB. A value that is set too low can affect other services with higher priority.";
      yexte:disturbances "Changing this attribute can affect performance of all data bearers. A value that is set too low can affect other services with higher priority. A value that is set too high can cause Dynamic UE Admission Control to fail in keeping the cell stable at overload.";
      yexte:dependencies "Only used for Resource Fair Scheduling algorithm. Only relevant if the license for Dynamic UE Admission Control is present and the feature is active.";
      type erienmnrmlrat:ddt-Lrat_ENodeBFunction_dlMaxWaitingTimeGlobal;
      default 0;
    }
    leaf interEnbUlCompTunnelDscp {
      description "DSCP value used for outgoing inter-eNodeB UL CoMP packets on X2. Set to same value as \"QCI9 - Non-GBR TCP Default Bearer\". Treat inter-eNodeB UL CoMP benefits as opportunistic and do not allow it to interfere with baseline LTE performance.";
      yexte:takes-effect "Next tunnel setup";
      type erienmnrmlrat:ddt-Lrat_ENodeBFunction_interEnbUlCompTunnelDscp;
      default 14;
    }
    leaf altNasBackTo {
      description "Method to select an alternative MME when eNodeB sends back initial UE message to MME. Used when eNodeB fails to select valid MME by receiving reroute NAS request message that is defined in TS36.413 ch. 8.6.2.5.";
      yexte:disturbances "Changing this attribute can cause loss of traffic.";
      type erienmnrmlrat:enum-AltMmeInfo;
      default DEFAULT_DCN;
    }
    leaf ulSchedulerDynamicBWAllocationEnabled {
      description "Specifies if the advanced UL scheduler is enabled\n";
      type boolean;
      default true;
    }
    leaf bbVlanPortRef {
      status deprecated {
        yexte:status-information "Since L17A. Replaced by eranVlanPortRef. Planned to be removed.";
      }
      description "Refers to the VlanPort instance to use for configuring the EthernetPort VLAN for a set of BB links.";
      yexte:disturbances "Changing this attribute can affect traffic. A node restart is required.";
      yexte:takes-effect "At node restart";
      erienmyext:enm-type MOREF;
      type string;
    }
    leaf timePhaseMaxDeviationMbms {
      description "The maximum allowed time and phase deviation for time and phase synchronization of the eNodeB. It is the deviation that is allowed for Multimedia Broadcast Multicast Service (MBMS) to function. When the limit is exceeded, the service is deactivated.";
      yexte:disturbances "Traffic can be affected if this attribute is changed. It can cause malfunction of the Multimedia Broadcast Multicast Service (MBMS) due to the time and phase deviation for time and phase synchronization of the eNodeB.";
      type erienmnrmlrat:ddt-Lrat_ENodeBFunction_timePhaseMaxDeviationMbms;
      default 50;
    }
    list x2WhiteList {
      min-elements 0;
      max-elements 64;
      key auto-generated-struct-key;
      leaf auto-generated-struct-key {
        type uint16;
        description "This leaf has been injected to allow for struct instances in a sequence to be ordered.";
        mandatory true;
      }
      description "The list of whitelisted RBS IDs. Automated Neighbor Relations (ANR) is not allowed to disconnect X2 for any neighbor RBS in the whitelist.";
      erienmyext:enm-type STRUCT;
      uses erienmnrmlrat:struct-GlobalEnbId;
    } // end 'list x2WhiteList'
    leaf licCapDistrMethod {
      description "Used to set how the licensed capacity will be distributed between the baseband processing resources";
      type erienmnrmlrat:enum-LicCapDistrMethod;
      default SYSTEM;
    }
    leaf maxNoCellsNaccCsfb {
      description "Max number of UTRAN/GERAN cells with system information. Can be included in an RRC connection release message triggered by CS Fallback as specified in 3GPP TS 36.331.";
      type erienmnrmlrat:ddt-Lrat_ENodeBFunction_maxNoCellsNaccCsfb;
      default 4;
    }
    leaf s1GtpuEchoInterval {
      description "Monitoring interval for delay measurements for all S1-U termination points.";
      yexte:dependencies "Only applicable for Baseband Radio Node. Takes effect if license and feature Transport Path Characteristics Monitoring is activated, s1GtpuEchoEnable = PERIODIC, and peer node supports delay measurements.";
      type erienmnrmlrat:ddt-Lrat_ENodeBFunction_s1GtpuEchoInterval;
      default 1000;
    }
    leaf tRelocOverall {
      description "Supervision timer of the outgoing S1/X2/intra-eNodeB handover execution procedure according to 3GPP TS 36.413 and TS 36.423.\nIf the feature Multi-Target RRC Connection Re-establishment is active this timer also supervises the Context Fetch procedure.";
      yexte:disturbances "Low values can stop outgoing HO.";
      yexte:takes-effect "New connection";
      type erienmnrmlrat:ddt-Lrat_ENodeBFunction_tRelocOverall;
      default 5;
    }
    container eNodeBPlmnId {
      description "The ENodeB Public Land Mobile Network (PLMN) ID that forms part of the ENodeB Global ID used to identify the node over the S1 interface.\nNote: The value (MCC=001, MNC=01) indicates that the PLMN is not initiated. The value can not be used as a valid PLMN Identity.\n";
      erienmyext:enm-type STRUCT;
      uses erienmnrmlrat:struct-PlmnIdentity;
    } // end 'container eNodeBPlmnId'
    leaf x2SetupTwoWayRelations {
      description "This parameter indicates if two way relations shall be setup during X2 setup and eNB configuration. The RBS creates a two-way relation for each entry in the received neighbour information that contains a relation to a source cell. Neighbour information is sent in X2 setup and eNB configuration. Neighbour information is eUtranCellRelations per source cell from the sending node.";
      yexte:takes-effect "New connection";
      type boolean;
      default true;
    }
    leaf dnsSelectionS1X2Ref {
      description "Controls DNS selection for S1 and X2 lookups. If not set, DNS server on OAM network is used.\nFor DU Radio Node it can be set to reference a DnsResolver, and DNS queries are resolved using referenced DnsResolver (typically using DNS server on transport network).\nFor Baseband Radio Node it can be set to reference a DnsClient, and DNS queries are resolved using referenced DnsClient (typically using DNS server on transport network).";
      yexte:disturbances "Changing this attribute can cause loss of traffic.";
      yexte:precondition "To enable this attribute DNS servers must support EDNS0.";
      erienmyext:enm-type MOREF;
      type string;
    }
    leaf timePhaseMaxDevIeNBUlComp {
      description "Max deviation for time and phase synchronization of eNodeB allowed for inter-eNodeB UL CoMP to function. If exceeded, service for inter-eNodeB UL CoMP is deactivated.";
      yexte:disturbances "Traffic can be affected if this attribute is changed. It can cause malfunction of inter-eNodeB UL CoMP feature due to time and phase deviation for time and phase synchronization between two eNodeBs.";
      yexte:dependencies "timeAndPhaseSynchAlignment must be true.";
      type erienmnrmlrat:ddt-Lrat_ENodeBFunction_timePhaseMaxDevIeNBUlComp;
      default 30;
    }
    leaf dlBbCapacityNet {
      erienmyext:no-notification;
      config false;
      description "Granted DL baseband capacity.\nAvailable capacity of corresponding Baseband HWAC property for all enabled Baseband HW.";
      type erienmnrmlrat:ddt-Lrat_ENodeBFunction_dlBbCapacityNet;
    }
    leaf ulBbCapacityNet {
      erienmyext:no-notification;
      config false;
      description "Granted UL baseband capacity.\nAvailable capacity of corresponding Baseband HWAC property for all enabled Baseband HW.";
      type erienmnrmlrat:ddt-Lrat_ENodeBFunction_ulBbCapacityNet;
    }
    leaf csfbMeasFromIdleMode {
      description "When CS Fallback is requested for a UE in idle mode this parameter controls if measurements for release with redirect and handover must be performed. If the parameter is set to false a blind release with redirect is done.";
      yexte:dependencies "This parameter is only relevant for features 'Measurement-Based CSFB Target Selection' and 'PSHO-based CS Fallback to WCDMA' .";
      type boolean;
      default true;
    }
    leaf x2retryTimerMaxAuto {
      description "See attribute x2RetryTimerStart.";
      type erienmnrmlrat:ddt-Lrat_ENodeBFunction_x2retryTimerMaxAuto;
      default 1440;
    }
    leaf timePhaseMaxDeviation {
      description "Defines the maximum allowed time/phase deviation for time/phase synchronization of the eNodeB.";
      yexte:disturbances "Changing this attribute can cause loss of traffic.";
      yexte:dependencies "This parameter is relevant when the parameter timeAndPhaseSynchCritical has the value true.";
      type erienmnrmlrat:ddt-Lrat_ENodeBFunction_timePhaseMaxDeviation;
      default 100;
    }
    leaf caAwareMfbiIntraCellHo {
      description "Activation/deactivation of feature Intra-Cell Handover to Additional Band.";
      yexte:precondition "Requires support for the feature Multiple Frequency Band Indicators in the eNB.";
      type boolean;
      default false;
    }
    leaf intraRanIpAddressRef {
      description "Reference to an AddressIPv4/AddressIPv6 instance. Used to configure IP address for intra RAN control, and user plane connections unless specified by rpUpIpAddressRef.";
      yexte:takes-effect "Node restart";
      erienmyext:enm-type MOREF;
      type string;
    }
    leaf combCellSectorSelectThreshRx {
      description "Used for PUSCH sector selection in combined Cell. For each UE, all sectors received power are compared against the primary sector. Only the primary and the best sector that is below the threshold will be selected.";
      yexte:disturbances "Changes may affect Sector Selection.";
      yexte:takes-effect "Next cell unlock";
      type erienmnrmlrat:ddt-Lrat_ENodeBFunction_combCellSectorSelectThreshRx;
      default 300;
    }
    leaf timePhaseMaxDeviationSib16 {
      description "The maximum allowed time and phase deviation for time and phase synchronization of the eNodeB. It is the deviation that is allowed for SIB16 Time Information Broadcast feature to function. When the limit is exceeded, the feature is deactivated.";
      yexte:disturbances "Traffic can be affected if this attribute is changed. It can cause malfunction of the SIB16 Time Information Broadcast due to the time and phase deviation for time and phase synchronization of the eNodeB.";
      type erienmnrmlrat:ddt-Lrat_ENodeBFunction_timePhaseMaxDeviationSib16;
      default 100;
    }
    leaf elasticRanUlCompSupport {
      status deprecated {
        yexte:status-information "Since 18.Q2. Has no functional behavior. Planned to be removed.";
      }
      description "Whether eNodeB supports Elastic RAN UL CoMP feature.";
      yexte:dependencies "Only takes effect in Baseband Radio Node.";
      type boolean;
      default false;
    }
    list x2BlackList {
      min-elements 0;
      max-elements 64;
      key auto-generated-struct-key;
      leaf auto-generated-struct-key {
        type uint16;
        description "This leaf has been injected to allow for struct instances in a sequence to be ordered.";
        mandatory true;
      }
      description "A list of blacklisted RBS IDs. X2 may not be set up to any neighbor RBS in the blacklist.";
      erienmyext:enm-type STRUCT;
      uses erienmnrmlrat:struct-GlobalEnbId;
    } // end 'list x2BlackList'
    leaf licUlPrbPercentileConf {
      description "The percentile to use for the counter BbProcessingResource::pmLicUlPrbCapActual.";
      type erienmnrmlrat:ddt-Lrat_ENodeBFunction_licUlPrbPercentileConf;
      default 90;
    }
    leaf userLabel {
      description "Label for free use.\n";
      type erienmnrmlrat:ddt-Lrat_ENodeBFunction_userLabel;
    }
    leaf timeAndPhaseSynchAlignment {
      description "If set to true, any time and phase synchronization accuracy-dependent feature is deactivated or degraded if its time and phase synchronization accuracy is not fulfilled.";
      yexte:disturbances "Changing this attribute can affect traffic.";
      type boolean;
      default false;
    }
    leaf gtpuErrorIndicationDscp {
      description "DSCP value used for outgoing GTP-U error indication messages.";
      type erienmnrmlrat:ddt-Lrat_ENodeBFunction_gtpuErrorIndicationDscp;
      default 40;
    }
    leaf eranUlCompVlanPortRef {
      description "VlanPort instance that can be used to set up EranInterMeLinks and BbLinks for Elastic RAN UL CoMP. Used as default when no value is specified for ExternalENodeBFunction::eranUlCompVlanPortRef.";
      yexte:takes-effect "Node restart";
      erienmyext:enm-type MOREF;
      type string;
    }
    leaf s1RetryTimer {
      description "Defines the frequency to perform re-establishment of SCTP and S1-AP connection,\nwhen the connection to a MME is lost.\n";
      type erienmnrmlrat:ddt-Lrat_ENodeBFunction_s1RetryTimer;
      default 30;
    }
    leaf enabledUlTrigMeas {
      description "Enables or disables the UL SINR max measurements and event triggers for the UL quality. Only has effect if license for Uplink-Triggered Inter-Frequency Mobility is not installed.";
      type boolean;
      default false;
    }
    leaf useBandPrioritiesInSib1 {
      status deprecated {
        yexte:status-information "Since 18.Q2. Has no functional behavior. Planned to be removed";
      }
      description "When enabled, prioritized additional frequency band list is broadcasted in SIB1 according to priorities in EUtranCellFDD/EUtranCellTDD::prioAdditionalFreqBandList.";
      yexte:precondition "Requires support for the feature Multiple Frequency Band Indicators in the eNB.";
      type boolean;
      default false;
    }
    leaf timePhaseMaxDeviationTdd4 {
      description "Max allowed deviation for time and phase synchronization of eNodeB for TDD cells. If exceeded, TDD cells that use this limit are disabled.";
      yexte:disturbances "Changing this attribute can affect traffic.";
      yexte:dependencies "timeAndPhaseSynchAlignment must be true.";
      type erienmnrmlrat:ddt-Lrat_ENodeBFunction_timePhaseMaxDeviationTdd4;
      default 15;
    }
    leaf timePhaseMaxDeviationTdd3 {
      description "Max allowed deviation for time and phase synchronization of eNodeB for TDD cells. If exceeded, TDD cells that use this limit are disabled.";
      yexte:disturbances "Changing this attribute can affect traffic.";
      yexte:dependencies "timeAndPhaseSynchAlignment must be true.";
      type erienmnrmlrat:ddt-Lrat_ENodeBFunction_timePhaseMaxDeviationTdd3;
      default 15;
    }
    leaf dnsLookupOnTai {
      description "Controls if the Tracking Area Identity (TAI) is used to get IP addresses of MME nodes from the Domain Name System (DNS).\nThe RBS uses TAI to automatically obtain all MME IP addresses from the DNS when dnsLookupOnTai is switched on, or at RBS start or restart.\nThe MME IP address list is refreshed periodically and MME connections released and setup according to the new list. The MME IP address list can also be refreshed from OSS-RC.";
      yexte:disturbances "Changing this attribute can cause loss of traffic.";
      type erienmnrmlrat:enum-DnsLookup;
      default ON;
    }
    leaf eranVlanPortRef {
      description "VlanPort instance that can be used to set up EranInterMeLinks and BbLinks. Used as default when no value is specified for ExternalENodeBFunction::eranVlanPortRef.";
      yexte:disturbances "Changing this attribute can affect traffic. A node restart is required.";
      yexte:takes-effect "Node restart";
      erienmyext:enm-type MOREF;
      type string;
    }
    leaf timePhaseMaxDeviationTdd2 {
      description "Max allowed deviation for time and phase synchronization of eNodeB for TDD cells. If exceeded, TDD cells that use this limit are disabled.";
      yexte:disturbances "Changing this attribute can affect traffic.";
      yexte:dependencies "timeAndPhaseSynchAlignment must be true.";
      type erienmnrmlrat:ddt-Lrat_ENodeBFunction_timePhaseMaxDeviationTdd2;
      default 15;
    }
    leaf mfbiSupport {
      config false;
      description "Specifies whether the feature Multiple Frequency Band Indicators is supported in the eNB.";
      notife:notifiable-state-data true;
      type boolean;
    }
    leaf useBandPrioritiesInSCellEval {
      description "When enabled, secondary cell evaluation for CA aware Intra-Cell Handover to Additional Band is done according to priorities in prioritizeAdditionalBands and EUtranCellFDD/EUtranCellTDD::prioAdditionalFreqBandList.";
      yexte:precondition "caAwareMfbiIntraCellHo must be enabled.";
      type boolean;
      default false;
    }
    leaf timePhaseMaxDeviationTdd1 {
      description "Max allowed deviation for time and phase synchronization of eNodeB for TDD cells. If exceeded, TDD cells that use this limit are disabled.";
      yexte:disturbances "Changing this attribute can affect traffic.";
      yexte:dependencies "timeAndPhaseSynchAlignment must be true.";
      type erienmnrmlrat:ddt-Lrat_ENodeBFunction_timePhaseMaxDeviationTdd1;
      default 15;
    }
    leaf sctpRef {
      description "Refers to SCTP instance used to configure SCTP host for S1 and X2 connections unless specified by sctpX2Ref.";
      yexte:takes-effect "At node restart";
      erienmyext:enm-type MOREF;
      type string;
    }
    leaf upIpAddress2Ref {
      description "Reference to an instance of IpAccessHostEt.\nRefers to the AddressIPv4/AddressIPv6 instance to configure the second IP address for S1 user plane connections.";
      yexte:takes-effect "Node restart";
      yexte:precondition "upIpAddressRef must be set.";
      yexte:dependencies "Dependents on license \"Multiple IP Addresses for S1 and X2\".";
      erienmyext:enm-type MOREF;
      type string;
    }
    leaf timePhaseMaxDeviationTdd7 {
      description "Max allowed deviation for time and phase synchronization of eNodeB for TDD cells. If exceeded, TDD cells that use this limit are disabled.";
      yexte:disturbances "Changing this attribute can affect traffic.";
      yexte:dependencies "timeAndPhaseSynchAlignment must be true.";
      type erienmnrmlrat:ddt-Lrat_ENodeBFunction_timePhaseMaxDeviationTdd7;
      default 15;
    }
    leaf timePhaseMaxDeviationTdd6 {
      description "Max allowed deviation for time and phase synchronization of eNodeB for TDD cells. If exceeded, TDD cells that use this limit are disabled.";
      yexte:disturbances "Changing this attribute can affect traffic.";
      yexte:dependencies "timeAndPhaseSynchAlignment must be true.";
      type erienmnrmlrat:ddt-Lrat_ENodeBFunction_timePhaseMaxDeviationTdd6;
      default 15;
    }
    leaf timePhaseMaxDeviationTdd5 {
      description "Max allowed deviation for time and phase synchronization of eNodeB for TDD cells. If exceeded, TDD cells that use this limit are disabled.";
      yexte:disturbances "Changing this attribute can affect traffic.";
      yexte:dependencies "timeAndPhaseSynchAlignment must be true.";
      type erienmnrmlrat:ddt-Lrat_ENodeBFunction_timePhaseMaxDeviationTdd5;
      default 15;
    }
    leaf releaseInactiveUesEnable {
      status deprecated {
        yexte:status-information "Since L16A. Has no functional behavior. Planned to be removed.";
      }
      description "Controls if the release of inactive UEs at handover shall be enabled.";
      type boolean;
      default false;
    }
    leaf timePhaseMaxDeviationIeNbCa {
      description "The maximum allowed time and phase deviation for time and phase synchronization of the eNodeB. It is the maximum deviation that is allowed for Carrier Aggregation to function. When the limit is exceeded, inter-eNB CA or eRAN CA is deactivated. Takes effect immediately.";
      yexte:disturbances "Traffic can be affected if this attribute is changed. It can cause malfunction of the inter-eNB CA or eRAN CA feature due to the time and phase deviation for time and phase synchronization between two eNodeBs.";
      yexte:dependencies "Only effective if timeAndPhaseSynchAlignment is true.";
      type erienmnrmlrat:ddt-Lrat_ENodeBFunction_timePhaseMaxDeviationIeNbCa;
      default 30;
    }
    leaf forcedSiTunnelingActive {
      description "Specifies whether or not the functionality to send NACC information, regardless of UE capability, is activated, provided that the feature Redirect with System Information is active.";
      type boolean;
      default false;
    }
    leaf licUlBbPercentileConf {
      description "The percentile to use for the counter BbProcessingResource::pmLicUlCapActual.";
      type erienmnrmlrat:ddt-Lrat_ENodeBFunction_licUlBbPercentileConf;
      default 90;
    }
    leaf licConnectedUsersPercentileConf {
      description "The percentile to use for the counter pmLicConnectedUsersActual.";
      type erienmnrmlrat:ddt-Lrat_ENodeBFunction_licConnectedUsersPercentileConf;
      default 90;
    }
    leaf-list inactivitySupervisionTimerNb {
      min-elements 0;
      max-elements 3;
      description "Inactivity supervision timer for NbIot cells in relation to estimated MCL for the UEs.\nInactivitySupervisionTimerNb[0] is used for UEs estimated to be in MCL less or equal to 144dB.\nInactivitySupervisionTimerNb[1] is used for UEs estimated to be in MCL greater than 144dB and less or equal to 154dB.\nInactivitySupervisionTimerNb[2] is used for UEs estimated to be in MCL greater than 154dB.\nValue 0 in an array entry means disable the timer for UEs in corresponding MCL.";
      type erienmnrmlrat:ddt-Lrat_ENodeBFunction_inactivitySupervisionTimerNb;
      default 100;
      default 150;
      default 200;
    }
    leaf alignTtiBundWUlTrigSinr {
      description "Configures UL quality measure type utilized for decisions on when to configure and de-configure TTI Bundling. If setting is 'ULTRIG' uplink SINR value from 'Uplink-Triggered Inter-Frequency Mobility' is used for TTI Bundling.";
      yexte:takes-effect "New connection";
      type erienmnrmlrat:enum-TtiBundTriggerAlignment;
      default OFF;
    }
    leaf upIpAddressRef {
      description "Refers to IpAccessHostEt or AddressIPv4/AddressIPv6 instance to configure IP address for S1 and X2 user plane connections unless specified by upX2IpAddressRef.";
      yexte:disturbances "Changing this attribute can affect traffic. A node restart is required.";
      yexte:takes-effect "At node restart";
      erienmyext:enm-type MOREF;
      type string;
    }
    leaf x2GtpuEchoDscp {
      description "DSCP value used for outgoing GTP-U echo request packets on X2-U.";
      type erienmnrmlrat:ddt-Lrat_ENodeBFunction_x2GtpuEchoDscp;
      default 14;
    }
    leaf randUpdateInterval {
      description "Random number update interval\nThis attribute specifies the time interval in minutes between random number generation. When this interval expires, the eNodeB generates a new random number between MinRandc and MaxRandc.";
      type erienmnrmlrat:ddt-Lrat_ENodeBFunction_randUpdateInterval;
      default 200;
    }
    leaf timePhaseSynchStateSib16 {
      erienmyext:no-notification;
      config false;
      description "Set to false when the SIB16 Time Information Broadcast feature is degraded due to time and phase synchronization accuracy requirements not fulfilled, otherwise it is set to true.";
      type boolean;
    }
    leaf timePhaseSynchStateCdma2000 {
      erienmyext:no-notification;
      config false;
      description "Set to false when the features related to CDMA2000 are degraded due to time and phase synchronization accuracy requirements not fulfilled, otherwise it is set to true.";
      type boolean;
    }
    leaf extendedWaitTimeNb {
      description "Wait time. Used for Narrow Band IoT RRC Connection Reject. If 0, value range is random.";
      type erienmnrmlrat:ddt-Lrat_ENodeBFunction_extendedWaitTimeNb;
      default 0;
    }
    leaf timePhaseSyncStateIeNBUlComp {
      erienmyext:no-notification;
      config false;
      description "Set to false when inter-eNodeB UL CoMP feature is degraded due to time and phase synchronization accuracy requirements not fulfilled, otherwise it is set to true.";
      type boolean;
    }
    leaf maxNrOfInterEnbUlCompLbm {
      description "Max number of inter-eNodeB UL CoMP candidate LBMs for each serving or cooperating LBM.";
      yexte:takes-effect "Next tunnel setup";
      type erienmnrmlrat:ddt-Lrat_ENodeBFunction_maxNrOfInterEnbUlCompLbm;
      default 6;
    }
    leaf eranUlCompReSelectLinkTime {
      description "The maximum time that the serving eNodeB can reselect Inter ME Link for Elastic RAN UL CoMP towards a new neighbor eNodeB.";
      yexte:takes-effect "Next tunnel setup";
      type erienmnrmlrat:ddt-Lrat_ENodeBFunction_eranUlCompReSelectLinkTime;
      default 7;
    }
    leaf nnsfMode {
      description "The mode used by the RBS for the non-access stratum node selection.\nRegardless of the mode used, the function attempts to:\n- Reconnect every UE to its registered MME in any of the tracking areas of the cell.\n- Distribute the UEs that are not reconnected among MMEs that serve the Public Land Mobile Network selected by each UE.";
      yexte:disturbances "Changing this attribute can cause loss of traffic.";
      yexte:takes-effect "New connection";
      type erienmnrmlrat:enum-NnsfModeVals;
      default RPLMN_IF_SAME_AS_SPLMN;
    }
    leaf pwsPersistentStorage {
      description "Decides whether or not PWS data must be persistently stored.";
      type erienmnrmlrat:enum-PersistentStorage;
      default OFF;
    }
    leaf checkEmergencySoftLock {
      description "Used to turn on and off the function for checking existence of emergency calls.";
      type boolean;
      default false;
    }
    leaf x2retryTimerStart {
      description "After failed X2 setup and after X2 link break the x2RetryTimer is used to control the time till next retry. x2RetryTimer is used for DNS, SCTP, X2AP retries and x2IpAddrViaS1.\nAfter first failed setup or missing IP address from DNS, x2RetryTimer = max(x2RetryTimerStart,W), where W is the timeToWait received in x2SetupFail. If W is not received, W=0.\nAfter link break, x2RetryTimer = random(0,x2RetryTimerStart). If the first setup after link break fails, the timer values according to the above and below paragraphs shall apply as for failed initial setup.\nAfter 2nd and following fails, if the X2 connection is not being setup by ANR in the S-RBS, x2RetryTimer = max(x2RetryTimerStart,W).\nAfter 2nd and following fails, if the X2 connection is being setup by ANR in the S-RBS, x2RetryTimer = max(min[2^(n-2)*x2RetryTimerStart, x2retryTimerMaxAuto], W), where n is failure number.\nEach W is only used in the first retry after it is received.";
      type erienmnrmlrat:ddt-Lrat_ENodeBFunction_x2retryTimerStart;
      default 30;
    }
    leaf timeAndPhaseSynchCritical {
      description "If set to true, the cell will be disabled if the time and phase synchronization accuracy of the eNodeB is not fulfilled.";
      type boolean;
      default false;
    }
    leaf rpUpIpAddressRef {
      description "Reference to an AddressIPv4/AddressIPv6 instance. Used to configure IP address for intra RAN user plane connections.";
      yexte:takes-effect "Node restart";
      erienmyext:enm-type MOREF;
      type string;
    }
    action collectDynamicCellStatus {
      description "Returns a snapshot of the traffic status of the node divided per cell, in the form; number of attached UEs and set up radio bearers.";
      input {
        leaf dynamicCellStatusOutput {
          mandatory true;
          description "Specifies the format of the returned information. It can be either of:\n- Unformatted text, suitable for on-screen reading.\n- Formatted text, suitable for automated interpretation, currently JSON (JavaScript Object Notation).";
          type erienmnrmlrat:enum-DynamicCellStatusOutput;
        }
      }
      output {
        leaf result {
          type string;
        }
      }
    }
    action updateMMEConnection {
      description "This action shall make it possible to order the RBS to make a new DNS lookup to get possible new MME Pool addresses. The orderCode has two different options:\n\n- Retain: This option will retain all connections that were included in DNS response and the connections that were not included in the response will be removed. For the IP addresses that were unknown for the RBS, the RBS will establish connections to those MMEs.\n\n\n- Renew All existing: The RBS performs a DNS lookup. Release all S1 connections to the MMEs and connect to the MMEs that are included in the DNS response.\n\nThis action should be used only when dnsLookupOnTai has the value ON. The action is rejected if dnsLookupState has the value OFF.";
      input {
        leaf orderCode {
          mandatory true;
          type erienmnrmlrat:enum-OrderCode;
        }
      }
    }
  } // end 'grouping moc-ENodeBFunction'
  grouping moc-TermPointToMme-keys {
    description "Key(s) for MOC TermPointToMme";
    leaf id {
      erienmyext:no-notification;
      description "The value component of the RDN.\n";
      mandatory true;
      yexte:ecim-name termPointToMmeId;
      type string;
    }
  } // end 'grouping moc-TermPointToMme-keys'
  grouping moc-TermPointToMme {
    description "Models the MME termination point of an S1 link between the RBS and the MME node.\n";
    leaf mmeSupportNbIoT {
      description "Enable/disable MME to serve NbIot traffic.";
      type boolean;
      default false;
    }
    leaf usedIpAddress {
      config false;
      description "The destination address used for initialization of the underlying SCTP association of the latest successful S1-Setup.\nThe IP address can be an IPv4 or an IPv6 address.\nNote: usedIpAddress never changes during the lifetime of the SCTP association.";
      notife:notifiable-state-data true;
      type erienmnrmlrat:ddt-Lrat_TermPointToMme_usedIpAddress;
    }
    leaf ipAddress1 {
      description "The primary IP address of the MME. A unique IP address is required for each MME.\nThe input format is four fields of digits, separated by dots. Each field consists of three digits. The value of each field must be in the range 0-255.\nTo set this attribute, administrativeState must be LOCKED.";
      yexte:disturbances "Changing this attribute can cause loss of S1 connectivity.";
      type erienmnrmlrat:ddt-Lrat_TermPointToMme_ipAddress1;
      default 0.0.0.0;
    }
    leaf ipAddress2 {
      description "The secondary IP address of the MME. A unique IP address is required for each MME.\nThe input format is four fields of digits, separated by dots. Each field consists of three digits. The value of each field must be in the range 0-255.\nTo set this attribute, administrativeState must be LOCKED.";
      yexte:disturbances "Changing this attribute can cause loss of S1 connectivity.";
      type erienmnrmlrat:ddt-Lrat_TermPointToMme_ipAddress2;
      default 0.0.0.0;
    }
    list servedPlmnListOtherRATs {
      min-elements 0;
      max-elements 32;
      key auto-generated-struct-key;
      leaf auto-generated-struct-key {
        type uint16;
        description "This leaf has been injected to allow for struct instances in a sequence to be ordered.";
        mandatory true;
      }
      description "Lists PLMN IDs served by the MME for radio technologies other than LTE. The attribute is set by the RBS at S1-SETUP. The PLMN ID consists of:\n\n1. MobileCountryCode, MCC, 3 digits\n2. MobileNetworkCode, MNC, 2 or 3 digits (the correct number of digits is set in the mncLength member of this Struct)\n\nExample: If MCC=125 and MNC=46, then plmnId=12546.";
      erienmyext:enm-type STRUCT;
      uses erienmnrmlrat:struct-PlmnIdentityRO;
    } // end 'list servedPlmnListOtherRATs'
    leaf-list mmeCodeListOtherRATs {
      min-elements 0;
      max-elements 256;
      config false;
      description "MME code for radio technologies other than LTE.";
      notife:notifiable-state-data true;
      type erienmnrmlrat:ddt-Lrat_TermPointToMme_mmeCodeListOtherRATs;
    }
    leaf relativeMmeCapacity {
      config false;
      description "Relative processing capacity of an MME to the other MMEs in the pool. The capacity is used to balance the load between MMEs in a pool.";
      notife:notifiable-state-data true;
      type erienmnrmlrat:ddt-Lrat_TermPointToMme_relativeMmeCapacity;
    }
    leaf mmeName {
      config false;
      description "Used by OSS-RC to identify an MME. The attribute is set by the RBS at S1-SETUP.";
      notife:notifiable-state-data true;
      type erienmnrmlrat:ddt-Lrat_TermPointToMme_mmeName;
    }
    leaf additionalCnRef {
      description "Refers to the AdditionalCoreNetwork instance to point out the source S1AP SCTP endpoint.";
      yexte:disturbances "Changing this attribute can affect traffic.";
      yexte:takes-effect "Next MO unlock";
      erienmyext:enm-type MOREF;
      type string;
    }
    leaf ipv6Address1 {
      description "The primary IPv6 address of the MME. The input format is eight fields, separated by colons.\nEach field consists of four hexadecimal characters. The value of each field must  be in the range 0-FFFF.\nLeading zeroes can be omitted in a field, and multiple groups of 16 bits of zeroes can be compressed to ::. The :: can be used only once in an address.\nTo set this attribute, administrativeState must be LOCKED.";
      yexte:takes-effect "Object enabled";
      type erienmnrmlrat:ddt-Lrat_TermPointToMme_ipv6Address1;
      default ::;
    }
    leaf ipv6Address2 {
      description "The secondary IPv6 address of the MME. The input format is eight fields, separated by colons.\nEach field consists of four hexadecimal characters. The value of each field must be in the range 0-FFFF.\nLeading zeroes can be omitted in a field and multiple groups of 16 bits of zeroes can be compressed to ::.\nThe :: can be used only once in an address.\nTo set this attribute, administrativeState must be LOCKED.";
      yexte:takes-effect "Object enabled";
      type erienmnrmlrat:ddt-Lrat_TermPointToMme_ipv6Address2;
      default ::;
    }
    leaf-list mmeCodeListLTERelated {
      min-elements 0;
      max-elements 256;
      config false;
      description "MME code for LTE.";
      notife:notifiable-state-data true;
      type erienmnrmlrat:ddt-Lrat_TermPointToMme_mmeCodeListLTERelated;
    }
    leaf-list mmeGIListLTERelated {
      min-elements 0;
      max-elements 16;
      config false;
      description "MME group ID for LTE.";
      notife:notifiable-state-data true;
      type erienmnrmlrat:ddt-Lrat_TermPointToMme_mmeGIListLTERelated;
    }
    leaf mmeSupportLegacyLte {
      description "Enable/disable MME to serve legacy LTE traffic.";
      type boolean;
      default true;
    }
    list servedPlmnListLTERelated {
      min-elements 0;
      max-elements 16;
      key auto-generated-struct-key;
      leaf auto-generated-struct-key {
        type uint16;
        description "This leaf has been injected to allow for struct instances in a sequence to be ordered.";
        mandatory true;
      }
      description "Lists the PLMN IDs served by the MME. The attribute is set by the RBS at S1-SETUP. The PLMN ID consists of:\n\n1. MobileCountryCode, MCC, 3 digits\n2. MobileNetworkCode, MNC, 2 or 3 digits (the correct number of digits is set in the mncLength member of this Struct)\n\nExample: If MCC=125 and MNC=46, then plmnId=12546.";
      erienmyext:enm-type STRUCT;
      uses erienmnrmlrat:struct-PlmnIdentityRO;
    } // end 'list servedPlmnListLTERelated'
    leaf administrativeState {
      description "The administrative state.\nNote: If this attribute is set to SHUTTING_DOWN, it will immediately go into the state LOCKED.";
      yexte:disturbances "Changing this attribute to LOCKED or SHUTTINGDOWN causes loss of traffic.";
      yexte:takes-effect Immediatley.;
      type erienmnrmlrat:enum-AdmState;
      default LOCKED;
    }
    leaf domainName {
      description "The fully-qualified domain name of the MME.\nA valid domain name consists of 1 or more labels separated by dots (.).\nValid characters for a label are limited to letters a - z, A - Z, digits 0 - 9, and the character - (dash). Character case is preserved. Length of a label may not exceed 255 characters.\nNOTE: The first and last character in the domain name must be one of the following: alphanumerical a - z, A - Z and digits 0 - 9. For more information refer to RFC 952, 1101 and 1123.\nTo set this attribute, administrativeState must be LOCKED.";
      type erienmnrmlrat:ddt-Lrat_TermPointToMme_domainName;
      default "";
    }
    leaf-list availabilityStatus {
      min-elements 0;
      config false;
      description "The availability status. It contains details about operationalState. This attribute is set by the application in the RBS.\n";
      notife:notifiable-state-data true;
      type erienmnrmlrat:enum-AvailStatus;
    }
    leaf operationalState {
      config false;
      description "The operational state.  This attribute is set by the application in the RBS.\n";
      notife:notifiable-state-data true;
      type erienmnrmlrat:enum-OperState;
    }
    leaf dcnType {
      description "Type of dedicated core network that MME serves. During initial attach, eNodeB selects an MME that belongs to default dedicated core network during NAS node selection.";
      type erienmnrmlrat:enum-DcnType;
      default DEFAULT;
    }
  } // end 'grouping moc-TermPointToMme'
  grouping moc-ReportConfigCsfbUtra-keys {
    description "Key(s) for MOC ReportConfigCsfbUtra";
    leaf id {
      erienmyext:no-notification;
      description "The value component of the RDN.";
      mandatory true;
      yexte:ecim-name reportConfigCsfbUtraId;
      type string;
    }
  } // end 'grouping moc-ReportConfigCsfbUtra-keys'
  grouping moc-ReportConfigCsfbUtra {
    description "Contains report configuration settings for the B1 or B2 event for UTRA measurements, used when searching for a suitable target cell when CS Fallback is triggered for the UE.\n\nThe RDN of this MO is ReportConfigCsfbUtra=1.";
    leaf thresholdRscp {
      description "Received Signal Code Power in the ThresholdUTRA, the threshold value for Event B1 and threshold2 value for Event B2.";
      yexte:takes-effect "New connection";
      yexte:dependencies "Used when measQuantityUtraFDD is set to RSCP.";
      type erienmnrmlrat:ddt-Lrat_ReportConfigCsfbUtra_thresholdRscp;
      default -115;
    }
    leaf timeToTrigger {
      description "The time to trigger value for the event B1 or B2 measurement.";
      yexte:takes-effect "New connection";
      type erienmnrmlrat:ddt-Lrat_ReportConfigCsfbUtra_timeToTrigger;
      default 40;
    }
    leaf thresholdEcNo {
      description "Ratio of energy per modulation bit to noise spectral density  used in the ThresholdUTRA, the threshold value for Event B1 and threshold2 value for Event B2.";
      yexte:takes-effect "New connection";
      yexte:dependencies "Only used when measQuantityUtraFDD is set to ECN0";
      type erienmnrmlrat:ddt-Lrat_ReportConfigCsfbUtra_thresholdEcNo;
      default -240;
    }
    leaf hysteresis {
      description "The hysteresis value for the event B1 and event B2, threshold2, measurement.";
      yexte:takes-effect "New connection";
      type erienmnrmlrat:ddt-Lrat_ReportConfigCsfbUtra_hysteresis;
      default 10;
    }
  } // end 'grouping moc-ReportConfigCsfbUtra'
  grouping moc-PtmSubscriberGroup-keys {
    description "Key(s) for MOC PtmSubscriberGroup";
    leaf id {
      erienmyext:no-notification;
      description "The value component of the RDN.";
      mandatory true;
      yexte:ecim-name ptmSubscriberGroupId;
      type string;
    }
  } // end 'grouping moc-PtmSubscriberGroup-keys'
  grouping moc-PtmSubscriberGroup {
    description "PTM Subscriber Group that can be used in PtmCellProfile configuration. Groups can be referenced from structures IfoConfig, AtoConfig, ResOpUseConfig, and StmConfig in PtmCellProfile.";
    leaf-list spidList {
      min-elements 1;
      max-elements 8;
      description "UEs assigned to this PTM Subscriber Group based on their SPID.\nEach SPID can be used in only one PtmSubscriberGroup.";
      yexte:disturbances "Changing this attribute can affect traffic.";
      type erienmnrmlrat:ddt-Lrat_PtmSubscriberGroup_spidList;
    }
    leaf-list reservedBy {
      min-elements 0;
      config false;
      description "Contains a list of MO instances that reserve this MO instance.";
      notife:notifiable-state-data true;
      erienmyext:enm-type MOREF;
      type string;
    }
    container plmn {
      description "UEs assigned to this PTM Subscriber Group based on their PLMN.";
      erienmyext:enm-type STRUCT;
      uses erienmnrmlrat:struct-PlmnIdentity;
    } // end 'container plmn'
  } // end 'grouping moc-PtmSubscriberGroup'
  grouping moc-EndcProfilePredefined-keys {
    description "Key(s) for MOC EndcProfilePredefined";
    leaf id {
      erienmyext:no-notification;
      description "The value component of the RDN.";
      mandatory true;
      yexte:ecim-name endcProfilePredefinedId;
      type string;
    }
  } // end 'grouping moc-EndcProfilePredefined-keys'
  grouping moc-EndcProfilePredefined {
    description "Predefined EN-DC profiles and EN-DC parameters that map to different QCIs.\n\nThe RDNs of these MOs are EnDcProfilePredefined=1 to EnDcProfilePredefined=3.";
    leaf meNbS1TermReqArpLev {
      config false;
      description "Controls how S1-U is terminated for EN-DC capable UEs.\nIf ARP.PriorityLevel is equal to or lower than meNbS1TermReqArpLev, bearer must not be setup as SN terminated.\nIf ARP.PriorityLevel is higher than meNbS1TermReqArpLev, bearer can be setup as SN terminated.\nValue 0 means the bearer can be set up as SN Terminated irrespectively of ARP.";
      yexte:dependencies "Only relevant if license for Basic Intelligent Connectivity is present and feature is active.";
      notife:notifiable-state-data true;
      type erienmnrmlrat:ddt-Lrat_EndcProfilePredefined_meNbS1TermReqArpLev;
    }
    leaf-list reservedBy {
      min-elements 0;
      config false;
      description "Contains a list of MO instances that reserve this MO instance.";
      notife:notifiable-state-data true;
      erienmyext:enm-type MOREF;
      type string;
    }
    leaf userLabelPredefined {
      config false;
      description "Predefined user label.";
      notife:notifiable-state-data true;
      type erienmnrmlrat:ddt-Lrat_EndcProfilePredefined_userLabelPredefined;
    }
  } // end 'grouping moc-EndcProfilePredefined'
  grouping moc-AutoCellCapEstFunction-keys {
    description "Key(s) for MOC AutoCellCapEstFunction";
    leaf id {
      erienmyext:no-notification;
      description "The value component of the RDN.";
      mandatory true;
      yexte:ecim-name autoCellCapEstFunctionId;
      type string;
    }
  } // end 'grouping moc-AutoCellCapEstFunction-keys'
  grouping moc-AutoCellCapEstFunction {
    description "Parameters for Automated Cell Capacity Estimation feature.\n\nThe RDN of this MO is AutoCellCapEstFunction=1.";
    leaf useEstimatedCellCap {
      description "Switches on the use of estimated cell capacity in load management features.";
      yexte:disturbances "Changing this attribute can cause loss of traffic.";
      type boolean;
      default false;
    }
  } // end 'grouping moc-AutoCellCapEstFunction'
  grouping moc-AnrFunctionUtran-keys {
    description "Key(s) for MOC AnrFunctionUtran";
    leaf id {
      erienmyext:no-notification;
      description "The value component of the Relative Distinguished Name (RDN).";
      mandatory true;
      yexte:ecim-name anrFunctionUtranId;
      type string;
    }
  } // end 'grouping moc-AnrFunctionUtran-keys'
  grouping moc-AnrFunctionUtran {
    description "Parameters and constraints for the UTRAN ANR functions.\n\nThe RDN of this MO is AnrFunctionUtran=1.";
    leaf hoAllowedUtranPolicy {
      description "Starting value of the parameter isHoAllowed when a UtranCellRelation is created by ANR (Automatic Neighbor Relations)";
      type boolean;
      default true;
    }
    leaf srvccPolicy {
      description "Starting value of the parameter srvccCapability when an ExternalUtranCellFDD/TDD is created by ANR (Automatic Neighbor Relations)";
      type erienmnrmlrat:enum-SrvccCapability;
      default CS_ONLY_SUPPORTED;
    }
    leaf rimIntegrationEnabled {
      description "This parameter indicates if ANR should be able to modify RIM associations to UTRAN cells.";
      type boolean;
      default true;
    }
    leaf anrUtranMeasReportMin {
      description "Defines the minimum target number of measurement reports per hour for each UtranFreqRelation/UtranTDDFreqRelation. The number of measurement reports may deviate from the target.\nPlease note that the unit is decMeasurementReport. Thus, the given number of measurement reports will be divided by 10.";
      type erienmnrmlrat:ddt-Lrat_AnrFunctionUtran_anrUtranMeasReportMin;
      default 5;
    }
    leaf anrStateUtran {
      description "Activates or deactivates the Automated Neighbor Relation (ANR) function support for Utran for one RBS. The value of the attribute is irrelevant when no valid license key is installed for the ANR feature.";
      type erienmnrmlrat:enum-ActivationVals;
      default DEACTIVATED;
    }
    leaf utranAnrAgQci1 {
      status deprecated {
        yexte:status-information "Since L16B. Planned to be removed";
      }
      description "Enables or disables eNodeB to order CGI measurement when UTRAN AG capable UE has QCI1.";
      yexte:takes-effect "New connection";
      yexte:dependencies "This attribute is effective only when ANR for UTRAN feature is activated.";
      type boolean;
      default true;
    }
    leaf anrUtranMeasReportMax {
      description "Defines the maximum target number of measurement reports per hour for each UtranFreqRelation/UtranTDDFreqRelation. The number of measurement reports may deviate from the target.\nPlease note that the unit is decMeasurementReport. Thus, the given number of measurement reports will be divided by 10.";
      type erienmnrmlrat:ddt-Lrat_AnrFunctionUtran_anrUtranMeasReportMax;
      default 100;
    }
    leaf anrUtranMeasReportDecr {
      description "Defines the decrease in the target number of measurement reports for each UtranFreqRelation/UtranTDDFreqRelation each time an Automated Neighbor Relations (ANR) UTRAN measurement report is received with only known neighbor cells.\nPlease note that the unit is decMeasurementReport. Thus, the given number of measurement reports will be divided by 10.";
      type erienmnrmlrat:ddt-Lrat_AnrFunctionUtran_anrUtranMeasReportDecr;
      default 1;
    }
    leaf anrUtranMeasReportAcIncr {
      description "Defines the increase in the target number of measurement reports for each UtranFreqRelation/UtranTDDFreqRelation each time a PCI measurement report is received with known cell but the corresponding LAC or RAC missing.\nPlease note that the unit is decMeasurementReport. Thus, the given number of measurement reports will be divided by 10.";
      type erienmnrmlrat:ddt-Lrat_AnrFunctionUtran_anrUtranMeasReportAcIncr;
      default 20;
    }
    leaf anrUtranAcMeasOn {
      description "Indicates whether more CGI measurements shall be initiated to find LAC and/or RAC for cells that were previously added by ANR with missing LAC or RAC.";
      type boolean;
      default true;
    }
    leaf anrUtranMeasReportIncr {
      description "Defines the increase in the target number of measurement reports for each UtranFreqRelation/UtranTDDFreqRelation each time an Automated Neighbor Relations (ANR) UTRAN measurement report is received with unknown neighbor UTRAN cells.\nPlease note that the unit is decMeasurementReport. Thus, the given number of measurement reports will be divided by 10.";
      type erienmnrmlrat:ddt-Lrat_AnrFunctionUtran_anrUtranMeasReportIncr;
      default 10;
    }
    leaf cellAddEcNoThresholdUtranDelta {
      description "This parameter together with b2Threshold2EcNoUtra specifies \"Ratio of energy per modulation bit to noise spectral density\"  threshold value for reported EcNo for a cell to be automatically added as neighbor. The equation for calculating the EcNo threshold is b2Threshold2EcNoUtra + cellAddEcNoThresholdUtranDelta.";
      yexte:takes-effect "New connection";
      type erienmnrmlrat:ddt-Lrat_AnrFunctionUtran_cellAddEcNoThresholdUtranDelta;
      default -10;
    }
    leaf cellAddRscpThresholdUtranDelta {
      description "This parameter together with b2Threshold2RscpUtra specifies \"The Received Signal Code Power\" (RSCP)  threshold value for reported power for a cell to be automatically added as neighbor. The equation for calculating the RSCP threshold is b2Threshold2RscpUtra + cellAddRscpThresholdUtranDelta.";
      yexte:takes-effect "New connection";
      type erienmnrmlrat:ddt-Lrat_AnrFunctionUtran_cellAddRscpThresholdUtranDelta;
      default -1;
    }
  } // end 'grouping moc-AnrFunctionUtran'
  grouping moc-Cdma20001xRttBandRelation-keys {
    description "Key(s) for MOC Cdma20001xRttBandRelation";
    leaf id {
      erienmyext:no-notification;
      description "Value component of the RDN";
      mandatory true;
      yexte:ecim-name cdma20001xRttBandRelationId;
      type string;
    }
  } // end 'grouping moc-Cdma20001xRttBandRelation-keys'
  grouping moc-Cdma20001xRttBandRelation {
    description "The MO represents a mobility relation between an EUtranCellFDD or an EUtranCellTDD and a Cdma20001xRTTFreqBand. It contains parameters that are specific for this relation.";
    leaf userLabel {
      description "Label for free use";
      type erienmnrmlrat:ddt-Lrat_Cdma20001xRttBandRelation_userLabel;
    }
    leaf threshXLow1xRtt {
      description "Threshold used in reselection towards a low priority CDMA2000 1xRTT band class expressed as an unsigned binary number equal to FLOOR ([-2 x 10 x log10 Ec/Io]) in units of 0.5 db.\nIf sServingCell < threshServingLow and sNeighbor > threshXLow (see corresponding attribute), reselection towards this lower prioritized band class is considered. The condition must be valid during the period defined by attribute tReselectionCdma1xRtt.\nsServingCell is the RX level value of the serving cell and sNeighborCell is the RX level value of a neighbor frequency.";
      type erienmnrmlrat:ddt-Lrat_Cdma20001xRttBandRelation_threshXLow1xRtt;
      default 63;
    }
    leaf threshXHigh1xRtt {
      description "Threshold used in reselection towards a high priority CDMA2000 1xRTT band class, expressed as an unsigned binary number equal to FLOOR ([-2 x 10 x log10 Ec/Io]) in units of 0.5 dB\nIf sNonServingCell > threshXHigh1xRtt, reselection is considered towards the band class with higher priority. The condition must be valid during the period defined by attribute tReselectionCdma1xRtt.\nsNonServingCell is the RX-level value of a neighboring cell.";
      type erienmnrmlrat:ddt-Lrat_Cdma20001xRttBandRelation_threshXHigh1xRtt;
      default 63;
    }
    leaf cdma2000FreqBandRef {
      yexte:restricted;
      description "Reference to the CDMA2000 frequency band MO, Cdma2000FreqBand";
      mandatory true;
      yexte:takes-effect "New connection";
      erienmyext:enm-type MOREF;
      type string;
    }
    leaf cellReselectionPriority {
      description "Absolute priority of the RAT (0 means: lowest priority)";
      type erienmnrmlrat:ddt-Lrat_Cdma20001xRttBandRelation_cellReselectionPriority;
      default 6;
    }
  } // end 'grouping moc-Cdma20001xRttBandRelation'
  grouping moc-SectorCarrier-keys {
    description "Key(s) for MOC SectorCarrier";
    leaf id {
      erienmyext:no-notification;
      description "The value component of the RDN.";
      mandatory true;
      yexte:ecim-name sectorCarrierId;
      type string;
    }
  } // end 'grouping moc-SectorCarrier-keys'
  grouping moc-SectorCarrier {
    description "This MO represents the power and frequency usage of the SectorEquipmentFunction that covers an area.";
    leaf noOfMutedTxAntennas {
      erienmyext:no-notification;
      config false;
      description "Number of muted Tx antennas when MIMO sleep mode is activated.";
      type erienmnrmlrat:ddt-Lrat_SectorCarrier_noOfMutedTxAntennas;
    }
    leaf noOfTxAntennas {
      description "Number of antennas SectorCarrier uses for DL transmission.\nIf SectorCarriers have different number of TX antennas in the node, set to the number of TX antennas SectorCarrier uses.\nIf set to 0, and optional features enabling usage of TX antennas are deactivated, SectorCarrier uses one TX branch.\nIf set to 0, and optional features enabling usage of TX antennas are activated, SectorCarrier uses maximum number of TX antennas defined by operable features.\nSet to zero for sectors equipped with AAS capable radio units. System decides optimal number of transmit branches to use.";
      yexte:disturbances "Change can affect traffic";
      yexte:takes-effect "Cell lock/unlock";
      yexte:dependencies "Dependent on optional features and configured radio that enable using multiple Tx antennas.";
      type erienmnrmlrat:ddt-Lrat_SectorCarrier_noOfTxAntennas;
      default 0;
    }
    leaf sectorShape {
      description "Shape of sector carrier.\nSelect a value supported by installed radio equipment. Refer to CPI for installed radio equipment for supported values.";
      yexte:takes-effect "Next cell unlock";
      yexte:dependencies "Only takes effect if radio equipment supports AAS functionality.";
      type erienmnrmlrat:enum-SectorShape;
      default MACRO;
    }
    leaf-list rfBranchTxRef {
      min-elements 0;
      max-elements 16;
      description "Contains references to RF branches whose RF ports are to be used for TX carrier allocations for this particular SectorCarrier. This is used only for deterministic carrier allocation. Values are taken into consideration if noOfTxAntennas > 0. If no reference is specified, carrier allocation is based on RF branch MOM list (default behavior).";
      yexte:disturbances "Modifying this attribute requires blocking and de-blocking the cell.";
      yexte:takes-effect "Object unlocked";
      yexte:precondition "Locked Cell";
      erienmyext:enm-type MOREF;
      type string;
    }
    leaf ulPimCancellationMode {
      status deprecated {
        yexte:status-information "Since 17.Q2. Replaced by PimCancellationConfig::ulPimCancellationMode. Planned to be removed.";
      }
      description "PIM cancellation mode on UL carriers.";
      type erienmnrmlrat:enum-UlPimCancellationMode;
      default EXCLUDED;
    }
    leaf pimMitigLevelThresh {
      description "PIM threshold level, relative to the 20W CW. Determines whether to perform PIM mitigative actions on associated sector carrier.\nWhen set to zero and optional feature PIM Mitigation is enabled, PIM Mitigation is deactivated or not performed for carrier branches in this SectorCarrier.\nWhen changed to a non-zero value and optional feature PIM Mitigation is enabled, PIM Mitigation is performed for carrier branches in this SectorCarrier reporting a PIM level equal to, or exceeding the threshold.";
      yexte:disturbances "Changing this attribute can cause degradation of DL throughput.";
      yexte:dependencies "Only takes effect if license for PIM Mitigation is present and feature is active.";
      type erienmnrmlrat:ddt-Lrat_SectorCarrier_pimMitigLevelThresh;
      default -145;
    }
    leaf pimMitigStatus {
      erienmyext:no-notification;
      config false;
      description "Status of ongoing PIM mitigation operation.";
      yexte:dependencies "Only takes effect if license for PIM Mitigation is present and feature is active.";
      type erienmnrmlrat:enum-PimMitigStatus;
    }
    leaf sectorFunctionRef {
      yexte:restricted;
      description "Reference to an instance of SectorEquipmentFunction MO.";
      mandatory true;
      erienmyext:enm-type MOREF;
      type string;
    }
    leaf txPowerPersistentLock {
      description "Indicates if attribute configuredMaxTxPower is locked or not.\nWhen true, attribute configuredMaxTxPower cannot be changed and parent MO cannot be deleted.\nNote: This attribute is only intended to be used on mRBS and mRRU.";
      yexte:precondition "Once set to true there is no possibility to change the value back to false unless a node re-integration is performed.";
      type boolean;
      default false;
    }
    leaf microSleepTxActivation {
      config false;
      description "Micro Sleep Tx functions in baseband are activated at cell unlock.";
      notife:notifiable-state-data true;
      type boolean;
    }
    leaf pimMitigDlMutingFixed {
      description "Setting to true enables static blanked resource quantity evaluation during DL power muting attempts. Amount of resources is defined with pimMitigDlMutingPerc.";
      yexte:disturbances "Changing this attribute can cause loss of traffic.";
      yexte:dependencies "Only takes effect if license for PIM Mitigation is present and feature is active.";
      type boolean;
      default false;
    }
    leaf prsEnabled {
      description "If true, the Positioning Reference Signal is sent from this sector carrier.\n1: For indoor antennas at the same location, if the sector carriers are isolated, set prsEnabled to true for all sector carriers. Transmission of PDSCH on the PRS subframe is not scheduled.\n2: For combined macro and pico sector carriers, set prsEnabled to true for the macro sector only. The other sector or sectors have prsEnabled = false. However, transmission of PDSCH is still not scheduled on the same subframe to prevent undesirable interferences.\nNote: To reclaim PRS subframe for PDSCH transmission, OTDOA Supl license state must be set to DISABLED.";
      yexte:disturbances "Change can affect traffic";
      yexte:takes-effect "Object disabled/enabled";
      type boolean;
      default true;
    }
    leaf-list availabilityStatus {
      min-elements 0;
      config false;
      description "The availability status. It contains details about operationalState. This attribute is set by the application in the RBS.";
      yexte:disturbances "Change can affect traffic";
      notife:notifiable-state-data true;
      type erienmnrmlrat:enum-AvailStatus;
    }
    container ulCalibrationData {
      description "UL antenna calibration information.";
      erienmyext:enm-type STRUCT;
      uses erienmnrmlrat:struct-UlCalibrationDataRO;
    } // end 'container ulCalibrationData'
    leaf-list rfBranchRxRef {
      min-elements 0;
      max-elements 8;
      description "Contains references to RF branches whose RF ports are to be used for RX carrier allocations for this particular SectorCarrier. This is used only for deterministic carrier allocation. Values are taken into consideration if noOfRxAntennas > 0. If no reference is specified, carrier allocation is based on RF branch MOM list (default behavior).";
      yexte:disturbances "Modifying this attribute requires blocking and de-blocking the cell.";
      yexte:takes-effect "Object unlocked";
      yexte:precondition "Locked Cell";
      erienmyext:enm-type MOREF;
      type string;
    }
    leaf-list virtualComChBeamfrmWtsAmplitude {
      min-elements 0;
      max-elements 8;
      description "Array of eight amplitudes for common channel beamforming weights of virtual sector. One of eight amplitudes must be non-zero for beamforming weights to take effect. Actual value = Set value / 100.";
      yexte:disturbances "Changed coverage can affect traffic.";
      yexte:takes-effect "Next cell unlock";
      type erienmnrmlrat:ddt-Lrat_SectorCarrier_virtualComChBeamfrmWtsAmplitude;
      default 0;
      default 0;
      default 0;
      default 0;
      default 0;
      default 0;
      default 0;
      default 0;
    }
    leaf pimcFunctionReference {
      status deprecated {
        yexte:status-information "Since 17.Q2. Replaced by PimCancellationConfig::pimCancellationFunctionRef. Planned to be removed.";
      }
      description "Reference to PimCancellationFunction MO to indicate PIM cancellation function SectorCarrier is participating in. The value is the LDN of refered PimCancellationFunction MO.";
      type string;
      default "";
    }
    leaf pimMitigAggressiveness {
      description "Mitigation behavior aggressiveness.";
      yexte:disturbances "Changing this attribute can cause degradation of DL throughput.";
      yexte:dependencies "Only takes effect if license for PIM Mitigation is present and feature is active.";
      type erienmnrmlrat:enum-PimMitigAggressiveness;
      default MEDIUM;
    }
    leaf radioTransmitPerformanceMode {
      description "A desired radio transmit operating mode, which is tailored to achieve good throughput performance for a given highest modulation in downlink.";
      yexte:takes-effect "Cell lock/unlock";
      type erienmnrmlrat:enum-RadioOperatingMode;
      default DEFAULT;
    }
    leaf configuredMaxTxPower {
      description "Maximum output power to be used in a SectorCarrier. The output power is evenly distributed over antenna connectors used for TX transmission allocated for the SectorCarrier.\nValue 0 must not be used.\nTo prevent the cell from transmitting, it must be locked.";
      yexte:disturbances "Changing this attribute can affect traffic";
      yexte:takes-effect "Object unlocked";
      yexte:precondition "Attribute can be set only when cell is locked.";
      type erienmnrmlrat:ddt-Lrat_SectorCarrier_configuredMaxTxPower;
      default 20000;
    }
    leaf virtualSector {
      description "Whether or not sector carrier is virtual sector, modelled by MO SectorCarrier.\nSector carriers can have different sector carrier shapes by using custom channel beamforming weights, so called \"virtual sector\".\nVirtual sector cannot carrier aggregate with other virtual sectors in same sector.";
      yexte:takes-effect "Next cell unlock";
      yexte:dependencies "If true, then virtualComChBeamfrmWtsAmplitude must be valid.";
      type boolean;
      default false;
    }
    leaf antCalModeTddAasDl {
      description "Antenna calibration configuration mode for TDD AAS DL.\n0: Guard-period based antenna calibration. DL antenna calibration windows in TDD guard period.\n1: Puncturing antenna calibration. DL antenna calibration windows in TDD DL subframes.\nBaseband samples are punctured in antenna calibration windows.";
      yexte:takes-effect "Next cell unlock";
      type erienmnrmlrat:ddt-Lrat_SectorCarrier_antCalModeTddAasDl;
      default 0;
    }
    leaf partOfSectorPower {
      status deprecated {
        yexte:status-information "Since L16B. Replaced by configuredMaxTxPower. Planned to be removed.";
      }
      description "Requested part of the total power in the SectorEquipment that must be allocated for the sectorCarrier. The output power is evenly distributed over antenna connectors used for TX transmission allocated for the SectorCarrier.\nWhen the total amount of power for each antenna connector of a SectorEquipment exceeds the limit of 100%, an alarm is generated when the cell that uses the SectorCarrier is unlocked.\nTo prevent the cell from transmitting, it must be locked.";
      yexte:disturbances "Change may affect traffic";
      yexte:takes-effect "Object disabled/enabled";
      type erienmnrmlrat:ddt-Lrat_SectorCarrier_partOfSectorPower;
      default 0;
    }
    leaf maximumTransmissionPower {
      config false;
      description "Maximum possible power at the antenna reference point, for all downlink channels in all TX branches used simultaneously in the SectorCarrier.\n-1 is used as an undefined value.\nNote: Setting configuredMaxTxPower (MO SectorCarrier) has an impact on this attribute. See Radio Network Configuration user guide 11/1553-HSC 105 50/1.";
      notife:notifiable-state-data true;
      type erienmnrmlrat:ddt-Lrat_SectorCarrier_maximumTransmissionPower;
    }
    container dlCalibrationData {
      description "Downlink antenna calibration information.";
      erienmyext:enm-type STRUCT;
      uses erienmnrmlrat:struct-DlCalibrationDataRO;
    } // end 'container dlCalibrationData'
    leaf dlPimCandidate {
      status deprecated {
        yexte:status-information "Since 17.Q2. Replaced by PimCancellationConfig::dlPimCandidate. Planned to be removed.";
      }
      description "Include DL carriers for PIM calculation.";
      type boolean;
      default false;
    }
    leaf-list reservedBy {
      min-elements 0;
      config false;
      description "Contains a list of MO instances that reserve this MO instance.";
      notife:notifiable-state-data true;
      erienmyext:enm-type MOREF;
      type string;
    }
    leaf noOfRxAntennas {
      description "Number of antennas that SectorCarrier uses for UL transmission.\nIf SectorCarriers have different number of RX antennas, set it to number of RX antennas SectorCarrier uses.\nIf set to 0, and optional features enabling usage of RX antennas are deactivated, SectorCarrier uses two RX branches.\nIf set to 0, and optional features enabling usage of RX antennas are activated, SectorCarrier uses maximum number of RX antennas defined by operable features.\nSet to zero for sectors equipped with AAS capable radio units. System decides optimal number of receive branches to use.";
      yexte:disturbances "Change can affect traffic";
      yexte:takes-effect "Cell lock/unlock";
      yexte:dependencies "Dependent on optional features and configured radio that enable using multiple Rx antennas.";
      type erienmnrmlrat:ddt-Lrat_SectorCarrier_noOfRxAntennas;
      default 0;
    }
    leaf pimMitigDlMutingPeriod {
      description "Minimum period between PDSCH muting attempts.";
      yexte:disturbances "Changing this attribute can cause degradation of DL throughput.";
      yexte:dependencies "Only takes effect if license for PIM Mitigation is present and feature is active.";
      type erienmnrmlrat:ddt-Lrat_SectorCarrier_pimMitigDlMutingPeriod;
      default 8;
    }
    leaf ulForcedTimingAdvanceCommand {
      description "Forced additional value for Timing Advance Command in Random Access Response according to 3GPP TS 36.213.";
      yexte:takes-effect "Cell lock/unlock";
      type erienmnrmlrat:ddt-Lrat_SectorCarrier_ulForcedTimingAdvanceCommand;
      default 0;
    }
    leaf-list virtualComChBeamfrmWtsPhase {
      min-elements 0;
      max-elements 8;
      description "Array of eight phases for common channel beamforming weights of virtual sector.";
      yexte:disturbances "Changed coverage can affect traffic.";
      yexte:takes-effect "Next cell unlock";
      type erienmnrmlrat:ddt-Lrat_SectorCarrier_virtualComChBeamfrmWtsPhase;
      default 0;
      default 0;
      default 0;
      default 0;
      default 0;
      default 0;
      default 0;
      default 0;
    }
    leaf operationalState {
      config false;
      description "The operational state. This attribute is set by the application in the RBS.";
      yexte:disturbances "Change can affect traffic";
      notife:notifiable-state-data true;
      type erienmnrmlrat:enum-OperState;
    }
    leaf pimMitigDlMutingPerc {
      description "Maximum bandwidth range of PDSCH muting, expressed as a percentage value of total DL bandwidth.";
      yexte:disturbances "Changing this attribute can cause degradation of DL throughput.";
      yexte:dependencies "Only takes effect if license for PIM Mitigation is present and feature is active.";
      type erienmnrmlrat:ddt-Lrat_SectorCarrier_pimMitigDlMutingPerc;
      default 40;
    }
    leaf digitalTilt {
      description "Digitally-controlled tilt through beamforming. Positive value gives downwards tilt and negative value gives upwards tilt.\nOnly MACRO, MACRO_2LOBE, MACRO_NARROW and MACRO_WIDE sector shapes are affected.\nSelect a value supported by installed radio equipment. Refer to CPI for installed radio equipment for supported values.";
      yexte:takes-effect "Next cell unlock";
      yexte:dependencies "Only takes effect if radio equipment supports AAS functionality.";
      type erienmnrmlrat:ddt-Lrat_SectorCarrier_digitalTilt;
      default 30;
    }
  } // end 'grouping moc-SectorCarrier'
  grouping moc-Cdma2000FreqBand-keys {
    description "Key(s) for MOC Cdma2000FreqBand";
    leaf id {
      erienmyext:no-notification;
      description "The value component of the Relative Distinguished Name (RDN).\n";
      mandatory true;
      yexte:ecim-name cdma2000FreqBandId;
      type string;
    }
  } // end 'grouping moc-Cdma2000FreqBand-keys'
  grouping moc-Cdma2000FreqBand {
    description "This Managed Object holds information on a CDMA2000 Bandclass.\n";
    leaf userLabel {
      description "Label for free use.\n";
      type erienmnrmlrat:ddt-Lrat_Cdma2000FreqBand_userLabel;
    }
    leaf cdmaBandClass {
      yexte:restricted;
      description "The CDMA frequency band in which the HRPD or 1xRTT carrier is located\nThe UNDEFINED_VALUE can never be used - either at create or modify of an MO.";
      type erienmnrmlrat:enum-HrpdBandClass;
      default UNDEFINED_VALUE;
    }
    leaf-list reservedBy {
      min-elements 0;
      config false;
      description "Contains a list of MO instances that reserve this MO instance.\n";
      yexte:dependencies "The MO may not be deleted if it is reserved.";
      notife:notifiable-state-data true;
      erienmyext:enm-type MOREF;
      type string;
    }
  } // end 'grouping moc-Cdma2000FreqBand'
  grouping moc-ReportConfigEUtraInterFreqMbms-keys {
    description "Key(s) for MOC ReportConfigEUtraInterFreqMbms";
    leaf id {
      erienmyext:no-notification;
      description "The value component of the Relative Distinguished Name (RDN).";
      mandatory true;
      yexte:ecim-name reportConfigEUtraInterFreqMbmsId;
      type string;
    }
  } // end 'grouping moc-ReportConfigEUtraInterFreqMbms-keys'
  grouping moc-ReportConfigEUtraInterFreqMbms {
    description "Contains the Report Configuration settings for UE measurements initiated for EUTRA Inter-frequency MBMS Interest.\n\nThe RDN of this MO is ReportConfigEUtraInterFreqMbms=1.";
    leaf a5ThresholdRsrp {
      description "The Reference Signal Received Power (RSRP) threshold2 value for eventA5.";
      type erienmnrmlrat:ddt-Lrat_ReportConfigEUtraInterFreqMbms_a5ThresholdRsrp;
      default -44;
    }
    leaf hysteresisA5 {
      description "The hysteresis value for the eventA5 measurement.";
      type erienmnrmlrat:ddt-Lrat_ReportConfigEUtraInterFreqMbms_hysteresisA5;
      default 10;
    }
  } // end 'grouping moc-ReportConfigEUtraInterFreqMbms'
  grouping moc-Cdma2000Freq-keys {
    description "Key(s) for MOC Cdma2000Freq";
    leaf id {
      erienmyext:no-notification;
      description "The value component of the Relative Distinguished Name (RDN).\n";
      mandatory true;
      yexte:ecim-name cdma2000FreqId;
      type string;
    }
  } // end 'grouping moc-Cdma2000Freq-keys'
  grouping moc-Cdma2000Freq {
    description "This Managed Object contains information of a specific CDMA2000 frequency within a Bandclass.\n";
    leaf userLabel {
      description "Label for free use.\n";
      type erienmnrmlrat:ddt-Lrat_Cdma2000Freq_userLabel;
    }
    leaf-list reservedBy {
      min-elements 0;
      config false;
      description "Contains a list of MO instances that reserve this MO instance.";
      notife:notifiable-state-data true;
      erienmyext:enm-type MOREF;
      type string;
    }
    leaf freqCdma {
      description "Identifies the carrier frequency within a CDMA2000 Band.\n";
      mandatory true;
      type erienmnrmlrat:ddt-Lrat_Cdma2000Freq_freqCdma;
    }
  } // end 'grouping moc-Cdma2000Freq'
  grouping moc-DrxProfile-keys {
    description "Key(s) for MOC DrxProfile";
    leaf id {
      erienmyext:no-notification;
      description "The value component of the RDN";
      mandatory true;
      yexte:ecim-name drxProfileId;
      type string;
    }
  } // end 'grouping moc-DrxProfile-keys'
  grouping moc-DrxProfile {
    description "DRX profiles and DRX parameters that map to different QCIs. First instance, DrxProfileId 0, is default DRX profile. Profile eMBMS VoLTE DRX (drxProfile=18) is used when DRX is combined with eMBMS and VoLTE coexistence.\n\nThe RDNs of these MOs are DrxProfile=0 to DrxProfile=18.";
    leaf shortDrxCycleTimer {
      description "Specifies the number of consecutive subframes the UE must follow the short DRX cycle after the DRX Inactivity Timer has expired. Value in multiples of shortDRX-Cycles. A value of 1 corresponds to 1 * shortDRX-Cycle, a value of 2 corresponds to 2 * shortDRX-Cycle and so on. Corresponds to 3GPP timer drxShortCycleTimer. The value 0 means that short DRX cycles are not used.";
      yexte:takes-effect "Next cell unlock";
      type erienmnrmlrat:ddt-Lrat_DrxProfile_shortDrxCycleTimer;
      default 4;
    }
    leaf longDrxCycleOnly {
      description "The longDrxCycleOnly value is used as longDrxCycle when the UE does not support shortDrxCycle. The value of longDrxCycleOnly is in number of sub-frames.";
      yexte:takes-effect "Next cell unlock";
      type erienmnrmlrat:enum-LongDrxCycle;
      default SF160;
    }
    leaf onDurationTimer {
      description "Number of consecutive PDCCH-subframes at beginning of a DRX Cycle. TS36.331 ch. 6.3.2, RRC parameter onDurationTimer.\nEricsson recommends to make shortDrxCycle value larger than onDurationTimer value.";
      yexte:takes-effect "Next cell unlock";
      type erienmnrmlrat:enum-OnDurationTimer;
      default PSF10;
    }
    leaf shortDrxCycle {
      description "Consecutive subframes between on-duration phases, that is period of re-occurring on-duration phases. Parameter is applied when UE follows short DRX cycle. Parameter is ignored if shortDrxCycleTimer = 0, instead longDrxCycle is applied and UE follows long DRX cycle only. Corresponds to 3GPP information element shortDRX-Cycle.\nEricsson recommends to make shortDrxCycle value larger than onDurationTimer value.";
      yexte:takes-effect "Next cell unlock";
      yexte:dependencies "If attribute shortDrxCycleTimer = 0, shortDrxCycles is not used.";
      type erienmnrmlrat:enum-ShortDrxCycle;
      default SF40;
    }
    leaf drxRetransmissionTimer {
      description "Specifies the maximum number of consecutive PDCCH-subframe(s) for as soon as a DL retransmission is expected by the UE. TS36.331 ch. 6.3.2, RRC parameter drx-RetransmissionTimer.";
      yexte:takes-effect "Next cell unlock";
      type erienmnrmlrat:enum-DrxRetransmissionTimer;
      default PSF2;
    }
    leaf drxInactivityTimer {
      description "Specifies the number of consecutive PDCCH-subframe(s) after successfully decoding a PDCCH indicating an initial UL or DL user data transmission for this UE. TS36.331 ch. 6.3.2, RRC parameter drx-InactivityTimer.";
      yexte:takes-effect "Next cell unlock";
      type erienmnrmlrat:enum-DrxInactivityTimer;
      default PSF200;
    }
    leaf drxState {
      description "Whether or not DRX is enabled for this profile. Hence if this DRX profile uses DRX.";
      yexte:takes-effect "Next cell unlock";
      type erienmnrmlrat:enum-DrxOperVals;
      default ENABLED;
    }
    leaf longDrxCycle {
      description "The value of longDrxCycle is in number of sub-frames.  If shortDrxCycle is configured, the value of longDrxCycle shall be a multiple of the shortDrxCycle value.";
      yexte:takes-effect "Next cell unlock";
      yexte:dependencies "Needs to be a multiple of shortDrxCycle";
      type erienmnrmlrat:enum-LongDrxCycle;
      default SF320;
    }
  } // end 'grouping moc-DrxProfile'
  grouping moc-LoadBalancingFunction-keys {
    description "Key(s) for MOC LoadBalancingFunction";
    leaf id {
      erienmyext:no-notification;
      description "The value component of the RDN.";
      mandatory true;
      yexte:ecim-name loadBalancingFunctionId;
      type string;
    }
  } // end 'grouping moc-LoadBalancingFunction-keys'
  grouping moc-LoadBalancingFunction {
    description "Contains parameters and constraints for Idle Mode Load Balancing feature.\n\nThe RDN of this MO is LoadBalancingFunction=1.";
    leaf lbCeiling {
      description "The maximum load (subscription ratio) difference taken into account in load balancing action.";
      yexte:disturbances "Changing this attribute can cause loss of traffic.";
      type erienmnrmlrat:ddt-Lrat_LoadBalancingFunction_lbCeiling;
      default 200;
    }
    leaf lbHitRateEUtranMeasUeThreshold {
      description "Specifies the required minimum number of connected users in the (source) cell to allow initiation of UE measurements for lbHitRate estimation on E-UTRAN frequencies.";
      type erienmnrmlrat:ddt-Lrat_LoadBalancingFunction_lbHitRateEUtranMeasUeThreshold;
      default 10;
    }
    leaf ocdMaxNoHighHitRateCells {
      description "Maximum number of cell relations for each frequency that can be identified as neighbors with a high hit rate by feature Overlaid Cell Detection.";
      type erienmnrmlrat:ddt-Lrat_LoadBalancingFunction_ocdMaxNoHighHitRateCells;
      default 3;
    }
    leaf lbHitRateEUtranAddThreshold {
      description "EUtran cell relations with a lbHitRate value greater than this threshold are considered suitable for load management.";
      yexte:dependencies "lbHitRateEUtranAddThreshold > lbHitRateEUtranRemoveThreshold";
      type erienmnrmlrat:ddt-Lrat_LoadBalancingFunction_lbHitRateEUtranAddThreshold;
      default 15;
    }
    leaf lbHitRateUtranMeasUeThreshold {
      description "Specifies the required minimum number of connected users in the (source) cell to allow initiation of UE measurements for lbHitRate estimation on UTRAN frequencies.";
      type erienmnrmlrat:ddt-Lrat_LoadBalancingFunction_lbHitRateUtranMeasUeThreshold;
      default 200;
    }
    leaf lbDiffCaOffset {
      description "The maximum load difference between the target cell and the source cell in order to redirect a CA capable UE to that target cell. The maximum load difference between the source cell and the target cell in order to apply the capacity criterion when load balancing a CA capable UE.";
      yexte:disturbances "Changing this attribute can affect traffic";
      yexte:takes-effect "New connection";
      yexte:dependencies lbDiffCaOffset>lbThreshold;
      type erienmnrmlrat:ddt-Lrat_LoadBalancingFunction_lbDiffCaOffset;
      default 100;
    }
    leaf lbCauseCodeS1SourceTriggersOffload {
      description "This attribute determines the cause code set by the eNodeB in outgoing S1AP HANDOVER REQUIRED when the handover is triggered by offload to Inter-Frequency EUTRAN neighbor or Inter-RAT UTRAN neighbour. See 3GPP 36.413.\nThe cause code LOAD_BALANCING can not be used for S1 handovers according to 3GPP 36.413. In case LOAD_BALANCING is selected, then the default value is chosen and used by the eNB.";
      type erienmnrmlrat:enum-CauseCodeOffload;
      default REDUCE_LOAD_IN_SERVING_CELL;
    }
    leaf lbUeEvaluationTimer {
      description "Timer to initiate evaluation of a UE for load balancing measurement. The timer is started at UE Context Setup.\nIf value = 0 the timer is not started, and UEs will only be evaluated for load balancing measurement at UE Context Setup.";
      yexte:disturbances "Changing this attribute can affect traffic";
      yexte:takes-effect "New connection";
      type erienmnrmlrat:ddt-Lrat_LoadBalancingFunction_lbUeEvaluationTimer;
      default 90;
    }
    leaf isUlEvalAllowedAtCaTrHo {
      description "Configures whether an uplink evaluation is allowed during a handover triggered by Carrier Aggregation-Aware IFLB. Used when Uplink-Triggered Inter-Frequency Mobility is enabled.";
      yexte:takes-effect "New connection";
      type boolean;
      default false;
    }
    leaf lbCauseCodeX2TargetAcceptsOffload {
      description "This attribute determines the cause code in an incoming X2AP HANDOVER REQUEST used by the eNodeB to determine whether or not the incoming handover is triggered by offload or not. See 3GPP 36.423.";
      type erienmnrmlrat:enum-CauseCodeOffload;
      default REDUCE_LOAD_IN_SERVING_CELL;
    }
    leaf lbHitRateEUtranMeasUeIntensity {
      description "Specifies the number of UE measurements for lbHitRate estimation (per cell and Load Balancing cycle) for each E-UTRAN frequency.";
      type erienmnrmlrat:ddt-Lrat_LoadBalancingFunction_lbHitRateEUtranMeasUeIntensity;
      default 10;
    }
    leaf lbEUtranOffloadBackoffTime {
      description "This attribute indicates a backoff time for eNodeB. The value applies to inhibit further offload to a EUTRAN target cell that rejects incoming offload.";
      type erienmnrmlrat:ddt-Lrat_LoadBalancingFunction_lbEUtranOffloadBackoffTime;
      default 60;
    }
    leaf txPwrForOverlaidCellDetect {
      description "Determines the maximum transmission power of the source cell on which feature Overlaid Cell Detection is allowed to be applied. For source cells with higher transmission power than specified in this attribute, overlaid neighbor cells are not identified.";
      type erienmnrmlrat:ddt-Lrat_LoadBalancingFunction_txPwrForOverlaidCellDetect;
      default 370;
    }
    leaf lbCaThreshold {
      description "The maximum load in the target cell in order to redirect a CA capable UE to that target cell. The maximum load in the current cell in order to apply the capacity criterion when load balancing a CA capable UE.";
      yexte:disturbances "Changing this attribute can affect traffic";
      yexte:takes-effect "New connection";
      type erienmnrmlrat:ddt-Lrat_LoadBalancingFunction_lbCaThreshold;
      default 800;
    }
    leaf lbUtranOffloadBackoffTime {
      description "Backoff time for eNodeB\nThe value applies to inhibit further offload to a UTRAN target cell that rejects incoming offload.";
      type erienmnrmlrat:ddt-Lrat_LoadBalancingFunction_lbUtranOffloadBackoffTime;
      default 60;
    }
    leaf lbMeasScalingLimit {
      description "Scaling factor for the required number of UE candidates needed for load balancing measurements to meet the load balancing target.\nNote: The minimum value of the attribute is internally limited to 10.";
      type erienmnrmlrat:ddt-Lrat_LoadBalancingFunction_lbMeasScalingLimit;
      default 30;
    }
    leaf lbAllowedForEndcUe {
      description "Whether load management actions triggered by load-balancing and off-loading features are allowed on EN-DC capable UE.\nIf set to false, load management actions are not allowed on EN-DC capable UE.";
      yexte:takes-effect "New connection";
      type boolean;
      default true;
    }
    leaf lbCauseCodeX2SourceTriggersOffload {
      description "This attribute determines the cause code set by the eNodeB in an outgoing X2AP HANDOVER REQUEST when the handover is triggered by offload to an Inter-Frequency EUTRAN neighbour. See 3GPP 36.423.";
      type erienmnrmlrat:enum-CauseCodeOffload;
      default REDUCE_LOAD_IN_SERVING_CELL;
    }
    leaf lbHitRateUtranAddThreshold {
      description "Utran cell relations with a lbHitRate value greater than this threshold are considered  suitable for load management.";
      yexte:dependencies "lbHitRateUtranAddThreshold > lbHitRateUtranRemoveThreshold";
      type erienmnrmlrat:ddt-Lrat_LoadBalancingFunction_lbHitRateUtranAddThreshold;
      default 15;
    }
    leaf lbHitRateUtranRemoveThreshold {
      description "Utran cell relations with a lbHitRate value lower than this threshold are NOT considered suitable for load management.";
      yexte:dependencies "lbHitRateUtranAddThreshold > lbHitRateUtranRemoveThreshold";
      type erienmnrmlrat:ddt-Lrat_LoadBalancingFunction_lbHitRateUtranRemoveThreshold;
      default 2;
    }
    leaf lbCauseCodeS1TargetAcceptsOffload {
      description "This attribute determines the cause code in an incoming S1AP HANDOVER REQUEST used by the eNodeB to determine whether or not the incoming handover is triggered by offload or not. See 3GPP 36.413.\nThe cause code LOAD_BALANCING can not be used for S1 handovers according to 3GPP 36.413. In case LOAD_BALANCING is selected, then the default value is chosen and used by the eNB.";
      type erienmnrmlrat:enum-CauseCodeOffload;
      default REDUCE_LOAD_IN_SERVING_CELL;
    }
    leaf lbHitRateEUtranRemoveThreshold {
      description "EUtran cell relations with a lbHitRate value lower than this threshold are NOT considered suitable for load management.";
      yexte:dependencies "lbHitRateEUtranAddThreshold > lbHitRateEUtranRemoveThreshold";
      type erienmnrmlrat:ddt-Lrat_LoadBalancingFunction_lbHitRateEUtranRemoveThreshold;
      default 2;
    }
    leaf lbThreshold {
      description "The minimum load (subscription ratio) difference to trigger load balancing action.";
      yexte:disturbances "Changing this attribute can cause loss of traffic.";
      type erienmnrmlrat:ddt-Lrat_LoadBalancingFunction_lbThreshold;
      default 30;
    }
    leaf lbHitRateUtranMeasUeIntensity {
      description "Specifies the number of UE measurements for lbHitRate estimation (per cell and Load Balancing cycle) for each UTRAN frequency.";
      type erienmnrmlrat:ddt-Lrat_LoadBalancingFunction_lbHitRateUtranMeasUeIntensity;
      default 1;
    }
    leaf lbCaCapHysteresis {
      description "Capacity related hysteresis value considered when checking the capacity criterion for both load balancing of CA capable UEs and CA triggered redirection.";
      yexte:disturbances "Changing this attribute can affect traffic";
      yexte:takes-effect "New connection";
      type erienmnrmlrat:ddt-Lrat_LoadBalancingFunction_lbCaCapHysteresis;
      default 20;
    }
    leaf lbRateOffsetCoefficient {
      description "Coefficient of rate-dependent load balancing offset. Moderates how much the load balancing must be offset towards a cell with higher capacity.";
      yexte:disturbances "Changing this attribute can cause loss of traffic.";
      type erienmnrmlrat:ddt-Lrat_LoadBalancingFunction_lbRateOffsetCoefficient;
      default 320;
    }
    leaf isUlEvalAllowedAtTpLbHo {
      description "Configures whether an uplink evaluation is allowed during a handover triggered by Throughput-Aware IFLB. Used when Uplink-Triggered Inter-Frequency Mobility is enabled.";
      yexte:takes-effect "New connection";
      type boolean;
      default false;
    }
    leaf ocdMinHighHitThresh {
      description "Minimum required hit rate to qualify a cell relation as a neighbor with a high hit rate by feature Overlaid Cell Detection.";
      type erienmnrmlrat:ddt-Lrat_LoadBalancingFunction_ocdMinHighHitThresh;
      default 15;
    }
    leaf lbRateOffsetLoadThreshold {
      description "Specifies the threshold for the source and target cell average load, above which the rate offset is set to zero.";
      yexte:disturbances "Changing this attribute can affect traffic";
      type erienmnrmlrat:ddt-Lrat_LoadBalancingFunction_lbRateOffsetLoadThreshold;
      default 500;
    }
  } // end 'grouping moc-LoadBalancingFunction'
  grouping moc-Cdma2000FreqBandRelation-keys {
    description "Key(s) for MOC Cdma2000FreqBandRelation";
    leaf id {
      erienmyext:no-notification;
      description "The value component of the Relative Distinguished Name (RDN).\n";
      mandatory true;
      yexte:ecim-name cdma2000FreqBandRelationId;
      type string;
    }
  } // end 'grouping moc-Cdma2000FreqBandRelation-keys'
  grouping moc-Cdma2000FreqBandRelation {
    description "This Managed Object represents a mobility relation between an EUtranCellFDD or an EUtranCellTDD and a Cdma2000FreqBand. It contains parameters that are specific for this relation.\n\nDeleting this MO while the parent EUtranCellFDD/EUtranCellTDD has operationalState set to ENABLED is not recommended as it may affect traffic.\n";
    leaf userLabel {
      description "Label for free use.\n";
      type erienmnrmlrat:ddt-Lrat_Cdma2000FreqBandRelation_userLabel;
    }
    leaf threshXHighHrpd {
      description "The threshold used in reselection towards a high priority CDMA2000 HRPD band class, expressed as an unsigned binary number equal to FLOOR ([-2 x 10 x log10 Ec/Io]) in units of 0.5 db.\nIf sNonServingCell > threshXHighHrpd, reselection is considered towards the band class with higher priority. The condition must be valid during the period defined by attribute tReselectionCdmaHrpd.\nsNonServingCell is the RX-level value of a neighboring cell.";
      type erienmnrmlrat:ddt-Lrat_Cdma2000FreqBandRelation_threshXHighHrpd;
      default 63;
    }
    leaf threshXLowHrpd {
      description "The threshold used in reselection towards a low priority CDMA2000 HRPD band class expressed as an unsigned binary number equal to FLOOR ([-2 x 10 x log10 Ec/Io]) in units of 0.5 db.\nIf sServingCell < threshServingLow and sNeighbor > threshXLow (see corresponding attribute), reselection towards this lower prioritized band class is considered. The condition must be valid during the period defined by attribute tReselectionCdmaHrpd.\nsServingCell is the RX level value of the serving cell and sNeighborCell is the RX level value of a neighbor frequency.";
      type erienmnrmlrat:ddt-Lrat_Cdma2000FreqBandRelation_threshXLowHrpd;
      default 63;
    }
    leaf cdma2000FreqBandRef {
      yexte:restricted;
      description "Reference to the Cdma2000 frequency band MO, Cdma2000FreqBand.";
      mandatory true;
      erienmyext:enm-type MOREF;
      type string;
    }
    leaf cellReselectionPriority {
      description "Absolute priority of the RAT (0 means: lowest priority).\n";
      yexte:dependencies "The value must be unique and not already used by other RAT, i.e. equal priorities between RATs are not supported.";
      type erienmnrmlrat:ddt-Lrat_Cdma2000FreqBandRelation_cellReselectionPriority;
      default 6;
    }
  } // end 'grouping moc-Cdma2000FreqBandRelation'
  grouping moc-HoWhiteList-keys {
    description "Key(s) for MOC HoWhiteList";
    leaf id {
      erienmyext:no-notification;
      description "The value component of the RDN";
      mandatory true;
      yexte:ecim-name hoWhiteListId;
      type string;
    }
  } // end 'grouping moc-HoWhiteList-keys'
  grouping moc-HoWhiteList {
    description "Contains a whitelist of SPID values that are allowed to perform a  incoming handover requests when the cell is in the mode \"reserved for operator use\"";
    leaf userLabel {
      description "Label for free use.\n";
      type erienmnrmlrat:ddt-Lrat_HoWhiteList_userLabel;
    }
    leaf-list spidList {
      min-elements 0;
      max-elements 20;
      description "A list of UEs, that are allowed to perform incoming handover to a cell that is in mode \"reserved for operator use\".\nNote: When value is configured to -1000, the parameter is ignored.";
      yexte:takes-effect "Ongoing connection";
      type erienmnrmlrat:ddt-Lrat_HoWhiteList_spidList;
      default -1000;
      default -1000;
      default -1000;
      default -1000;
      default -1000;
      default -1000;
      default -1000;
      default -1000;
      default -1000;
      default -1000;
      default -1000;
      default -1000;
      default -1000;
      default -1000;
      default -1000;
      default -1000;
      default -1000;
      default -1000;
      default -1000;
      default -1000;
    }
  } // end 'grouping moc-HoWhiteList'
  grouping moc-TermPointToENB-keys {
    description "Key(s) for MOC TermPointToENB";
    leaf id {
      erienmyext:no-notification;
      description "The value component of the Relative Distinguished Name (RDN).\n";
      mandatory true;
      yexte:ecim-name termPointToENBId;
      type string;
    }
  } // end 'grouping moc-TermPointToENB-keys'
  grouping moc-TermPointToENB {
    description "Models the local eNB termination point of an X2 link between the eNB and a neighbour eNB.\n";
    leaf usedIpAddress {
      config false;
      description "The destination address used for initialization of the underlying SCTP association of the latest successful X2-Setup.\nThe IP address can be an IPv4 or an IPv6 address.\nNote: usedIpAddress never changes during the lifetime of the SCTP association.";
      notife:notifiable-state-data true;
      type erienmnrmlrat:ddt-Lrat_TermPointToENB_usedIpAddress;
    }
    leaf ipsecEpAddress {
      erienmyext:no-notification;
      config false;
      description "The outer address of the X2 neighbor.";
      type string;
    }
    leaf ipv6Address {
      description "The IP address of the neighboring RBS. The format is eight fields, separated by colons.\nEach field consists of four hexadecimal characters. The value of each field is in the range 0-FFFF.\nLeading zeroes can be omitted in a field, and multiple groups of 16 bits of zeroes can be compressed to ::\nThe :: can appear only once in an address.\nTo set this attribute, administrativeState must be LOCKED.";
      yexte:disturbances "Changing this attribute can cause loss of X2 connectivity.";
      type erienmnrmlrat:ddt-Lrat_TermPointToENB_ipv6Address;
      default ::;
    }
    leaf timeOfCreation {
      erienmyext:no-notification;
      config false;
      description "Indicates the time and date when the MO was created.\nFormat: YYYY-MM-DD HH:MM:SS";
      type erienmnrmlrat:ddt-Lrat_TermPointToENB_timeOfCreation;
    }
    leaf interEnbCaProtVerActive {
      erienmyext:no-notification;
      config false;
      description "Negotiated version for inter-eNodeB CA on this link. If unknown, displayed as -1. If incompatible, displayed as 0.";
      type erienmnrmlrat:ddt-Lrat_TermPointToENB_interEnbCaProtVerActive;
    }
    leaf ipAddress {
      description "The IP address of the neighboring RBS. The input format is four fields of digits, separated by dots. Each field may consist of three digits. The value of each field is in the range 0-255.";
      yexte:disturbances "Changing this attribute can cause loss of X2 connectivity.";
      yexte:dependencies "To set this attribute, administrativeState must be LOCKED.";
      type erienmnrmlrat:ddt-Lrat_TermPointToENB_ipAddress;
      default 0.0.0.0;
    }
    leaf eRanCaProtVerActive {
      erienmyext:no-notification;
      config false;
      description "Negotiated version for Elastic RAN CA on this link. If unknown, displayed as -1. If incompatible, displayed as 0.";
      type erienmnrmlrat:ddt-Lrat_TermPointToENB_eRanCaProtVerActive;
    }
    leaf interEnbSwCompatibilityState {
      erienmyext:no-notification;
      config false;
      description "Reflects whether the eNodeBs designated in the endpoints between eNodeBs have inter-eNodeB-compatible capabilities.";
      yexte:dependencies "If not compatible, no baseband-to-baseband connections are set up between these eNodeBs.";
      type erienmnrmlrat:enum-InterEnbSwCompatibilityState;
    }
    leaf timeOfLastModification {
      config false;
      description "Indicates the time and date when the MO was last modified.\nFormat: YYYY-MM-DD HH:MM:SS";
      notife:notifiable-state-data true;
      type erienmnrmlrat:ddt-Lrat_TermPointToENB_timeOfLastModification;
    }
    leaf administrativeState {
      description "The administrative state.\nNote: If this attribute is set to SHUTTING_DOWN, it will immediately go into the state LOCKED.";
      yexte:disturbances "Changing this attribute to LOCKED or SHUTTINGDOWN causes loss of X2 connectivity.";
      type erienmnrmlrat:enum-AdmState;
      default LOCKED;
    }
    leaf createdBy {
      config false;
      description "Indicates whether the MO has been created by the Automated Neighbor Relations (ANR) function or operator or X2";
      notife:notifiable-state-data true;
      type erienmnrmlrat:enum-CreatedByEutran;
    }
    leaf domainName {
      description "The fully-qualified domain name of the RBS.\nA valid domain name consists of 1 or more labels separated by dots (.). Valid characters for a label are limited to letters a-z, A-Z, digits 0-9, and the character - (dash).\nThe following format is used for automatically created domain names:\nx2.enbidDDDDD.enb.tac-lbEE.tac-hbFF.tac.eutran.mncBBB.mccCCC.3gppnetwork.org.\nThe D's (five or seven) represent hexadecimal coding of ENBID (enodeB Identity) without padding.\nB & C represent BCD (binary coded decimal) coding of MNC (mobile network code) and MCC (mobile country code) respectively.\nE & F represent hexadecimal coding of the least and most significant bytes (low & high byte) of the tracking area code.\nB, C, E & F are always padded with leading zeros to match the number of characters in the format above.";
      type erienmnrmlrat:ddt-Lrat_TermPointToENB_domainName;
      default "";
    }
    leaf lastModification {
      config false;
      description "Indicates whether the MO was last modified by the Automated Neighbor Relations (ANR) function or operator or X2 and if the MO is to be deleted who triggered the deletion";
      notife:notifiable-state-data true;
      type erienmnrmlrat:enum-LastModificationEutran;
    }
    leaf eRanUlCompProtVerActive {
      erienmyext:no-notification;
      config false;
      description "Negotiated version for Elastic RAN UL CoMP on this link. If unknown, displayed as -1. If incompatible, displayed as 0.";
      type erienmnrmlrat:ddt-Lrat_TermPointToENB_eRanUlCompProtVerActive;
    }
    leaf-list availabilityStatus {
      min-elements 0;
      config false;
      description "The availability status. It contains details about operational state. This attribute is set by the application in the RBS.\n";
      notife:notifiable-state-data true;
      type erienmnrmlrat:enum-AvailStatus;
    }
    leaf operationalState {
      config false;
      description "The operational state. This attribute is set by the application in the RBS.\n";
      notife:notifiable-state-data true;
      type erienmnrmlrat:enum-OperState;
    }
    leaf eranUlCompSwCompatibility {
      config false;
      description "Whether eNodeBs designated in endpoints between eNodeBs are compatible for Elastic RAN UL CoMP.";
      yexte:dependencies "If not compatible, no baseband-to-baseband connections are set up between these eNodeBs.";
      notife:notifiable-state-data true;
      type erienmnrmlrat:enum-InterEnbSwCompatibilityState;
    }
    leaf interEnbUlCompProtVerActive {
      erienmyext:no-notification;
      config false;
      description "Negotiated version for inter-eNodeB CoMP on this link. If unknown, displayed as -1. If incompatible, displayed as 0.";
      type erienmnrmlrat:ddt-Lrat_TermPointToENB_interEnbUlCompProtVerActive;
    }
    leaf interEnbUlCompSwCompatibility {
      erienmyext:no-notification;
      config false;
      description "Whether eNodeBs designated in endpoints between eNodeBs are compatible for Inter-eNodeB UL CoMP.";
      yexte:dependencies "If not compatible, no baseband-to-baseband connections are set up between these eNodeBs.";
      type erienmnrmlrat:enum-InterEnbSwCompatibilityState;
    }
  } // end 'grouping moc-TermPointToENB'
  grouping moc-AnrFunction-keys {
    description "Key(s) for MOC AnrFunction";
    leaf id {
      erienmyext:no-notification;
      description "The value component of the Relative Distinguished Name (RDN).";
      mandatory true;
      yexte:ecim-name anrFunctionId;
      type string;
    }
  } // end 'grouping moc-AnrFunction-keys'
  grouping moc-AnrFunction {
    description "Contains parameters and constraints for ANR functions, for example, adding or removing neighbor cells.\n\nThe RDN of this MO is AnrFunction=1.";
    leaf probCellDetectMedHoSuccThres {
      description "Specifies the threshold. Together with AnrFunction::probCellDetectMedHoSuccTime it controls when EUtranCellRelation::hoSuccLevel changes from HIGH to MEDIUM and conversely.\nNote: The handover statistics status must be =< the AnrFunction::probCellDetectMedHoSuccThres at least the AnrFunction::probCellDetectMedHoSuccTime time before hoSuccLevel is changed from HIGH to MEDIUM. The handover statistics status must be > the AnrFunction::probCellDetectMedHoSuccThres at least the AnrFunction::probCellDetectMedHoSuccTime/2 before the hoSuccLevel is changed from MEDIUM to HIGH.\nOnly applicable when AnrFunction::problematicCellPolicy is set to AUTO_DETECT or AUTO_DETECT_AND_BAR.";
      yexte:takes-effect "Ongoing connection";
      yexte:dependencies "probCellDetectMedHoSuccThres >  probCellDetectLowHoSuccThres.";
      type erienmnrmlrat:ddt-Lrat_AnrFunction_probCellDetectMedHoSuccThres;
      default 50;
    }
    leaf pciConflictMobilityEcgiMeas {
      description "Controls if ECGI measurements are requested prior to hand over, in case a PCI conflict is detected.";
      type boolean;
      default false;
    }
    leaf plmnWhiteListUtranEnabled {
      description "If true, ANR Whitelist PLMN ID is enabled for UTRAN.";
      yexte:takes-effect "Ongoing connection";
      type boolean;
      default false;
    }
    leaf prioHoRate {
      description "Defines the weight of \"handover rate\" when determining the relation priority. The priority is used when deciding which relation to remove, when too many relations have been added. The priority is also used when determining which UTRAN cell to perform mobility measurements for.";
      type erienmnrmlrat:ddt-Lrat_AnrFunction_prioHoRate;
      default 100;
    }
    leaf probCellDetectLowHoSuccTime {
      description "Specifies the time. Together with probCellDetectLowHoSuccThreas it controls when EUtranCellRelation::hoSuccLevel changes from MEDIUM to LOW and conversely.\nOnly applicable when AnrFunction::problematicCellPolicy is set to AUTO_DETECT or AUTO_DETECT_AND_BAR.";
      yexte:takes-effect "Ongoing connection";
      type erienmnrmlrat:ddt-Lrat_AnrFunction_probCellDetectLowHoSuccTime;
      default 10;
    }
    leaf perEcgiMeasPlmnWhiteList {
      description "Turns periodic ECGI measurements on or off for ANR Whitelist PLMN IDs for EUTRAN.";
      type boolean;
      default true;
    }
    leaf plmnWhiteListEnabled {
      description "If true, ANR Whitelist PLMN ID for EUTRAN is enabled.";
      yexte:takes-effect "Ongoing connection";
      type boolean;
      default false;
    }
    leaf probCellDetectLowHoSuccThres {
      description "Specifies the threshold. Together with probCellDetectLowHoSuccTime it controls when EUtranCellRelation::hoSuccLevel changes from MEDIUM to LOW and conversely.\nNote: The handover statistics status must be =< the AnrFunction::probCellDetectLowHoSuccThres at least the AnrFunction::probCellDetectLowHoSuccTime time before hoSuccLevel is changed from MEDIUM to LOW. The handover statistics status must be > the AnrFunction::probCellDetectLowHoSuccThres at least the AnrFunction::probCellDetectLowHoSuccTime/2 before the hoSuccLevel is changed from LOW to MEDIUM.\nOnly applicable when AnrFunction::problematicCellPolicy is set to AUTO_DETECT or AUTO_DETECT_AND_BAR.";
      yexte:takes-effect "Ongoing connection";
      yexte:dependencies "probCellDetectMedHoSuccThres > probCellDetectLowHoSuccThres.";
      type erienmnrmlrat:ddt-Lrat_AnrFunction_probCellDetectLowHoSuccThres;
      default 10;
    }
    leaf removeNcellTime {
      description "The length of time that neighbor cells without any neighbor relations remain in the RBS. 1000 means no automatic removal is performed. If set to 0, the neighbor cell MO is removed within 1 minute. Ericsson strongly recommend that value 0 shall not be used, due to the fact that when setting this value to 0, this might lead to that X2 connections are removed together with all external cells and are setup once again every minute this causes one a network level a huge pressure one the nodes.\n";
      type erienmnrmlrat:ddt-Lrat_AnrFunction_removeNcellTime;
      default 30;
    }
    leaf perCgiMeasPlmnWhiteListUtran {
      description "Turns periodic CGI measurements on or off for ANR Whitelist PLMN IDs for UTRAN.";
      type boolean;
      default true;
    }
    leaf removeNrelTime {
      description "The maximum time that a neighbor relation can fall short of the cellRelationHoRateThreshold before MO is removed from the MOM. A removed cell relation is still evaluated in RBS as a candidate neighbor relation as long as there is at least one PCI or CGI reported for removeNrelTime.\n1000 means no automatic removal is performed. If set to 0, the neighbor relation MO is removed within 1 minute. Value 0 must not be used, because new CGI measurements are already performed for any relation not used for handover after 1 minute.";
      type erienmnrmlrat:ddt-Lrat_AnrFunction_removeNrelTime;
      default 7;
    }
    leaf prioHoSuccRate {
      description "Defines the weight of \"handover success rate\" when determining the relation priority. The priority is used when deciding which relation to remove, when too many relations have been added. The priority is also used when determining which UTRAN cell to perform mobility measurements for.";
      type erienmnrmlrat:ddt-Lrat_AnrFunction_prioHoSuccRate;
      default 100;
    }
    leaf prioTime {
      description "Defines the weight of \"time since last use\" when determining the relation priority. The priority is used when deciding which relation to remove, when too many relations have been added. The priority is also used when determining which UTRAN cell to perform mobility measurements for.";
      type erienmnrmlrat:ddt-Lrat_AnrFunction_prioTime;
      default 100;
    }
    leaf perCgiMeasPlmnWhiteListGeran {
      description "Turns periodic CGI measurements on or off for ANR Whitelist PLMN IDs for GERAN.";
      type boolean;
      default true;
    }
    leaf maxTimeEventBasedPciConf {
      description "Defines a maximal time that any UE has to assist ANR function with event based measurements, that is used to measure on EUtran neighbors.\nSpecial Value: 0 means infinity.";
      type erienmnrmlrat:ddt-Lrat_AnrFunction_maxTimeEventBasedPciConf;
      default 30;
    }
    leaf removeNenbTime {
      description "The length of time that neighbor RBSs without any neighbor cells remain in the RBS. 1000 means no automatic removal is performed. If set to 0, the neighbor RBS MO is removed within 1 minute.";
      type erienmnrmlrat:ddt-Lrat_AnrFunction_removeNenbTime;
      default 7;
    }
    leaf maxNoPciReportsInact {
      status deprecated {
        yexte:status-information "Since L16A. Replaced by attribute maxNoMeasReportsInact on UeMeasControl. Planned to be removed.";
      }
      description "Defines a maximal value of reports that any UE has to provide the ANR function with based on periodical PCI measurements, that is used to measure on Utran and Geran neighbors.\nSpecial Value: 0 means infinity.";
      type erienmnrmlrat:ddt-Lrat_AnrFunction_maxNoPciReportsInact;
      default 30;
    }
    leaf plmnWhiteListGeranEnabled {
      description "If true, ANR Whitelist PLMN ID is enabled for GERAN.";
      yexte:takes-effect "Ongoing connection";
      type boolean;
      default false;
    }
    leaf problematicCellPolicy {
      description "Specifies if detection of problematic cell is activated or not.";
      yexte:takes-effect "Ongoing connection";
      type erienmnrmlrat:enum-EUtranProbCellPolicyVals;
      default OFF;
    }
    leaf probCellDetectMedHoSuccTime {
      description "Specifies the time. Together with probCellDetectMedHoSuccThres it controls when EUtranCellRelation::hoSuccLevel changes from HIGH to MEDIUM and conversely.\nOnly applicable when AnrFunction::problematicCellPolicy is set to AUTO_DETECT or AUTO_DETECT_AND_BAR.";
      yexte:takes-effect "Ongoing connection";
      type erienmnrmlrat:ddt-Lrat_AnrFunction_probCellDetectMedHoSuccTime;
      default 4;
    }
    leaf maxNoPciReportsEvent {
      description "Defines a maximal value of reports that any UE has to provide the ANR function with on event based measurements, that is used to measure on EUtran neighbors.\nSpecial Value: 0 means infinity.";
      type erienmnrmlrat:ddt-Lrat_AnrFunction_maxNoPciReportsEvent;
      default 15;
    }
    leaf cellRelHoAttRateThreshold {
      description "The ANR criteria to add or remove MO neighbor relation. A candidate neighbor relation is internally evaluated before creation as MO if the daily HO attempt rate exceeds the threshold. If the value is set to 0, MO cell relations must be immediately created regardless of the HO attempt rate. The condition to remove a relation from the MOM also depends on the attribute removeNrelTime.";
      type erienmnrmlrat:ddt-Lrat_AnrFunction_cellRelHoAttRateThreshold;
      default 0;
    }
    leaf pciConflictDetectionEcgiMeas {
      description "Controls if ECGI measurements are requested in order to detect PCI conflicts.";
      type boolean;
      default false;
    }
  } // end 'grouping moc-AnrFunction'
  augment /erienmnrmcomtop:ManagedElement/erienmnrmlrat:ENodeBFunction/erienmnrmlrat:SectorCarrier {
    list PimCancellationConfig {
      key id;
      max-elements 72;
      description "PIM cancellation configuration data of SectorCarrier participating in PIM cancellation function.";
      erienmyext:enm-type MOC;
      uses moc-PimCancellationConfig-keys;
      container attributes {
        description "Attributes for PimCancellationConfig";
        uses moc-PimCancellationConfig;
      } // end 'container attributes'
    } // end 'list PimCancellationConfig'
  }
  augment /erienmnrmcomtop:ManagedElement/erienmnrmlrat:ENodeBFunction/erienmnrmlrat:FlexibleQoSFunction {
    list FlexibleQoSGroup {
      key id;
      max-elements 18;
      description "Group of members to assign a bearer certain SCI profile. Multiple members in the same group must not be applicable to the same bearer.";
      erienmyext:enm-type MOC;
      uses moc-FlexibleQoSGroup-keys;
      container attributes {
        description "Attributes for FlexibleQoSGroup";
        uses moc-FlexibleQoSGroup;
      } // end 'container attributes'
    } // end 'list FlexibleQoSGroup'
  }
  augment /erienmnrmcomtop:ManagedElement/erienmnrmlrat:ENodeBFunction {
    list Rrc {
      key id;
      max-elements 1;
      description "Models the manageable RRC protocol characteristics.\n\nThe RDN of this MO is Rrc=1.";
      yexte:is-system-created;
      erienmyext:enm-type MOC;
      uses moc-Rrc-keys;
      container attributes {
        description "Attributes for Rrc";
        uses moc-Rrc;
      } // end 'container attributes'
    } // end 'list Rrc'
  }
  augment /erienmnrmcomtop:ManagedElement/erienmnrmlrat:ENodeBFunction/erienmnrmlrat:EUtranCellFDD {
    list UeMeasControl {
      key id;
      max-elements 1;
      description "Models the manageable characteristics for UE measurements.\n\nThe RDN of this MO is UeMeasControl=1.";
      yexte:is-system-created;
      erienmyext:enm-type MOC;
      uses moc-UeMeasControl-keys;
      container attributes {
        description "Attributes for UeMeasControl";
        uses moc-UeMeasControl;
      } // end 'container attributes'
    } // end 'list UeMeasControl'
  }
  augment /erienmnrmcomtop:ManagedElement/erienmnrmlrat:ENodeBFunction/erienmnrmlrat:EUtranCellTDD {
    list UeMeasControl {
      key id;
      max-elements 1;
      description "Models the manageable characteristics for UE measurements.\n\nThe RDN of this MO is UeMeasControl=1.";
      yexte:is-system-created;
      erienmyext:enm-type MOC;
      uses moc-UeMeasControl-keys;
      container attributes {
        description "Attributes for UeMeasControl";
        uses moc-UeMeasControl;
      } // end 'container attributes'
    } // end 'list UeMeasControl'
  }
  augment /erienmnrmcomtop:ManagedElement/erienmnrmlrat:ENodeBFunction {
    list UlCompGroup {
      key id;
      max-elements 24;
      description "Defines a set of sectorCarriers. Uplink Coordinated multi-point reception of antenna signals is possible only between antenna signals from sectorCarriers within the same set of sectorCarriers.";
      erienmyext:enm-type MOC;
      uses moc-UlCompGroup-keys;
      container attributes {
        description "Attributes for UlCompGroup";
        uses moc-UlCompGroup;
      } // end 'container attributes'
    } // end 'list UlCompGroup'
  }
  augment /erienmnrmcomtop:ManagedElement/erienmnrmlrat:ENodeBFunction/erienmnrmlrat:PtmFunction/erienmnrmlrat:PtmCellProfile {
    list PtmResOpUseConfig {
      key id;
      max-elements 1;
      description "Contains PTM specific parameters affecting Cell Reserved For Operator Use functionality.\n\nThe RDN of this MO is PtmResOpUseConfig=1.";
      yexte:is-system-created;
      erienmyext:enm-type MOC;
      uses moc-PtmResOpUseConfig-keys;
      container attributes {
        description "Attributes for PtmResOpUseConfig";
        uses moc-PtmResOpUseConfig;
      } // end 'container attributes'
    } // end 'list PtmResOpUseConfig'
  }
  augment /erienmnrmcomtop:ManagedElement/erienmnrmlrat:ENodeBFunction/erienmnrmlrat:EUtranCellFDD/erienmnrmlrat:UeMeasControl {
    list ReportConfigEUtraIFA3UlTrig {
      key id;
      max-elements 1;
      description "Contains report configuration settings for the A3 event for inter-frequency LTE measurements initiated by Uplink-Triggered Inter-Frequency Mobility.\n\nThe RDN of this MO is ReportConfigEUtraIFA3UlTrig=1.";
      yexte:is-system-created;
      erienmyext:enm-type MOC;
      uses moc-ReportConfigEUtraIFA3UlTrig-keys;
      container attributes {
        description "Attributes for ReportConfigEUtraIFA3UlTrig";
        uses moc-ReportConfigEUtraIFA3UlTrig;
      } // end 'container attributes'
    } // end 'list ReportConfigEUtraIFA3UlTrig'
  }
  augment /erienmnrmcomtop:ManagedElement/erienmnrmlrat:ENodeBFunction/erienmnrmlrat:EUtranCellTDD/erienmnrmlrat:UeMeasControl {
    list ReportConfigEUtraIFA3UlTrig {
      key id;
      max-elements 1;
      description "Contains report configuration settings for the A3 event for inter-frequency LTE measurements initiated by Uplink-Triggered Inter-Frequency Mobility.\n\nThe RDN of this MO is ReportConfigEUtraIFA3UlTrig=1.";
      yexte:is-system-created;
      erienmyext:enm-type MOC;
      uses moc-ReportConfigEUtraIFA3UlTrig-keys;
      container attributes {
        description "Attributes for ReportConfigEUtraIFA3UlTrig";
        uses moc-ReportConfigEUtraIFA3UlTrig;
      } // end 'container attributes'
    } // end 'list ReportConfigEUtraIFA3UlTrig'
  }
  augment /erienmnrmcomtop:ManagedElement/erienmnrmlrat:ENodeBFunction/erienmnrmlrat:EUtranCellFDD/erienmnrmlrat:UeMeasControl {
    list PmUeMeasControl {
      key id;
      max-elements 1;
      description "This managed object contains the settings for PM Initiated UE Measurements.\n";
      erienmyext:enm-type MOC;
      uses moc-PmUeMeasControl-keys;
      container attributes {
        description "Attributes for PmUeMeasControl";
        uses moc-PmUeMeasControl;
      } // end 'container attributes'
    } // end 'list PmUeMeasControl'
  }
  augment /erienmnrmcomtop:ManagedElement/erienmnrmlrat:ENodeBFunction/erienmnrmlrat:EUtranCellTDD/erienmnrmlrat:UeMeasControl {
    list PmUeMeasControl {
      key id;
      max-elements 1;
      description "This managed object contains the settings for PM Initiated UE Measurements.\n";
      erienmyext:enm-type MOC;
      uses moc-PmUeMeasControl-keys;
      container attributes {
        description "Attributes for PmUeMeasControl";
        uses moc-PmUeMeasControl;
      } // end 'container attributes'
    } // end 'list PmUeMeasControl'
  }
  augment /erienmnrmcomtop:ManagedElement/erienmnrmlrat:ENodeBFunction/erienmnrmlrat:AnrFunction {
    list AnrFunctionGeran {
      key id;
      max-elements 1;
      description "Parameters and constraints for GERAN ANR functions.\n\nThe RDN of this MO is AnrFunctionGeran=1.";
      yexte:is-system-created;
      erienmyext:enm-type MOC;
      uses moc-AnrFunctionGeran-keys;
      container attributes {
        description "Attributes for AnrFunctionGeran";
        uses moc-AnrFunctionGeran;
      } // end 'container attributes'
    } // end 'list AnrFunctionGeran'
  }
  augment /erienmnrmcomtop:ManagedElement/erienmnrmlrat:ENodeBFunction/erienmnrmlrat:UtraNetwork/erienmnrmlrat:UtranFrequency {
    list ExternalUtranCellFDD {
      key id;
      max-elements 392;
      description "This Managed Object contains a UTRAN cell for Frequency Division Duplex (FDD).";
      erienmyext:enm-type MOC;
      uses moc-ExternalUtranCellFDD-keys;
      container attributes {
        description "Attributes for ExternalUtranCellFDD";
        uses moc-ExternalUtranCellFDD;
      } // end 'container attributes'
    } // end 'list ExternalUtranCellFDD'
  }
  augment /erienmnrmcomtop:ManagedElement/erienmnrmlrat:ENodeBFunction/erienmnrmlrat:QciTable {
    list LogicalChannelGroup {
      key id;
      max-elements 4;
      description "Represents QoS configuration related to a Logical Channel group.\n\nThe RDNs of these MOs are LogicalChannelGroup=0 to LogicalChannelGroup=3.";
      yexte:is-system-created;
      erienmyext:enm-type MOC;
      uses moc-LogicalChannelGroup-keys;
      container attributes {
        description "Attributes for LogicalChannelGroup";
        uses moc-LogicalChannelGroup;
      } // end 'container attributes'
    } // end 'list LogicalChannelGroup'
  }
  augment /erienmnrmcomtop:ManagedElement/erienmnrmlrat:ENodeBFunction/erienmnrmlrat:EUtranCellFDD/erienmnrmlrat:Cdma20001xRttBandRelation {
    list Cdma20001xRttFreqRelation {
      key id;
      max-elements 64;
      description "The MO represents a mobility relation between an EUtranCellFDD or an EUtranCellTDD and a Cdma20001xRTTFreq. It contains parameters that are specific for this relation.";
      erienmyext:enm-type MOC;
      uses moc-Cdma20001xRttFreqRelation-keys;
      container attributes {
        description "Attributes for Cdma20001xRttFreqRelation";
        uses moc-Cdma20001xRttFreqRelation;
      } // end 'container attributes'
    } // end 'list Cdma20001xRttFreqRelation'
  }
  augment /erienmnrmcomtop:ManagedElement/erienmnrmlrat:ENodeBFunction/erienmnrmlrat:EUtranCellTDD/erienmnrmlrat:Cdma20001xRttBandRelation {
    list Cdma20001xRttFreqRelation {
      key id;
      max-elements 64;
      description "The MO represents a mobility relation between an EUtranCellFDD or an EUtranCellTDD and a Cdma20001xRTTFreq. It contains parameters that are specific for this relation.";
      erienmyext:enm-type MOC;
      uses moc-Cdma20001xRttFreqRelation-keys;
      container attributes {
        description "Attributes for Cdma20001xRttFreqRelation";
        uses moc-Cdma20001xRttFreqRelation;
      } // end 'container attributes'
    } // end 'list Cdma20001xRttFreqRelation'
  }
  augment /erienmnrmcomtop:ManagedElement/erienmnrmlrat:ENodeBFunction/erienmnrmlrat:EUtranCellFDD/erienmnrmlrat:Cdma20001xRttBandRelation/erienmnrmlrat:Cdma20001xRttFreqRelation {
    list Cdma20001xRttCellRelation {
      key id;
      max-elements 64;
      description "The MO represents a mobility relation between an EUtranCellFDD or an EUtranCellTDD and a Cdma20001xRTTCell. It contains parameters that are specific for this relation.";
      erienmyext:enm-type MOC;
      uses moc-Cdma20001xRttCellRelation-keys;
      container attributes {
        description "Attributes for Cdma20001xRttCellRelation";
        uses moc-Cdma20001xRttCellRelation;
      } // end 'container attributes'
    } // end 'list Cdma20001xRttCellRelation'
  }
  augment /erienmnrmcomtop:ManagedElement/erienmnrmlrat:ENodeBFunction/erienmnrmlrat:EUtranCellTDD/erienmnrmlrat:Cdma20001xRttBandRelation/erienmnrmlrat:Cdma20001xRttFreqRelation {
    list Cdma20001xRttCellRelation {
      key id;
      max-elements 64;
      description "The MO represents a mobility relation between an EUtranCellFDD or an EUtranCellTDD and a Cdma20001xRTTCell. It contains parameters that are specific for this relation.";
      erienmyext:enm-type MOC;
      uses moc-Cdma20001xRttCellRelation-keys;
      container attributes {
        description "Attributes for Cdma20001xRttCellRelation";
        uses moc-Cdma20001xRttCellRelation;
      } // end 'container attributes'
    } // end 'list Cdma20001xRttCellRelation'
  }
  augment /erienmnrmcomtop:ManagedElement/erienmnrmlrat:ENodeBFunction/erienmnrmlrat:PtmFunction/erienmnrmlrat:PtmCellProfile {
    list PtmIfoConfig {
      key id;
      max-elements 1;
      description "Contains PTM specific parameters affecting Inter-Frequency Offload feature.\n\nThe RDN of this MO is PtmIfoConfig=1.";
      yexte:is-system-created;
      erienmyext:enm-type MOC;
      uses moc-PtmIfoConfig-keys;
      container attributes {
        description "Attributes for PtmIfoConfig";
        uses moc-PtmIfoConfig;
      } // end 'container attributes'
    } // end 'list PtmIfoConfig'
  }
  augment /erienmnrmcomtop:ManagedElement/erienmnrmlrat:ENodeBFunction/erienmnrmlrat:ResourcePartitions {
    list ResourcePartition {
      key id;
      max-elements 24;
      description "A combination of attributes which specify the resource partition a given UE should be included in.";
      erienmyext:enm-type MOC;
      uses moc-ResourcePartition-keys;
      container attributes {
        description "Attributes for ResourcePartition";
        uses moc-ResourcePartition;
      } // end 'container attributes'
    } // end 'list ResourcePartition'
  }
  augment /erienmnrmcomtop:ManagedElement/erienmnrmlrat:ENodeBFunction/erienmnrmlrat:QciTable {
    list SciProfile {
      key id;
      max-elements 19;
      description "Contains bearer-level eNB specific QoS configuration used for feature FlexibleQoS. SCI profile can be used only when FlexibleQoS is activated.\n\nThe RDNs of these MOs are SciProfile=sci1 to SciProfile=sci18, SciProfile=default.";
      yexte:is-system-created;
      erienmyext:enm-type MOC;
      uses moc-SciProfile-keys;
      container attributes {
        description "Attributes for SciProfile";
        uses moc-SciProfile;
      } // end 'container attributes'
    } // end 'list SciProfile'
  }
  augment /erienmnrmcomtop:ManagedElement/erienmnrmlrat:ENodeBFunction/erienmnrmlrat:EUtranCellFDD/erienmnrmlrat:UeMeasControl {
    list ReportConfigCsfbGeran {
      key id;
      max-elements 1;
      description "Contains report configuration settings for the B1 or B2 event for GERAN measurements, used when searching for a suitable target cell when CS Fallback is triggered for the UE.\n\nThe RDN of this MO is ReportConfigCsfbGeran=1.";
      yexte:is-system-created;
      erienmyext:enm-type MOC;
      uses moc-ReportConfigCsfbGeran-keys;
      container attributes {
        description "Attributes for ReportConfigCsfbGeran";
        uses moc-ReportConfigCsfbGeran;
      } // end 'container attributes'
    } // end 'list ReportConfigCsfbGeran'
  }
  augment /erienmnrmcomtop:ManagedElement/erienmnrmlrat:ENodeBFunction/erienmnrmlrat:EUtranCellTDD/erienmnrmlrat:UeMeasControl {
    list ReportConfigCsfbGeran {
      key id;
      max-elements 1;
      description "Contains report configuration settings for the B1 or B2 event for GERAN measurements, used when searching for a suitable target cell when CS Fallback is triggered for the UE.\n\nThe RDN of this MO is ReportConfigCsfbGeran=1.";
      yexte:is-system-created;
      erienmyext:enm-type MOC;
      uses moc-ReportConfigCsfbGeran-keys;
      container attributes {
        description "Attributes for ReportConfigCsfbGeran";
        uses moc-ReportConfigCsfbGeran;
      } // end 'container attributes'
    } // end 'list ReportConfigCsfbGeran'
  }
  augment /erienmnrmcomtop:ManagedElement/erienmnrmlrat:ENodeBFunction/erienmnrmlrat:EUtranCellFDD/erienmnrmlrat:UeMeasControl {
    list ReportConfigB2CdmaUlTrig {
      key id;
      max-elements 1;
      description "Contains report configuration settings for the B2 event for CDMA2000 measurements initiated by Uplink-Triggered Inter-Frequency Mobility. The actual threshold values used can be adjusted by frequency relation or QCI related offsets if the feature Multi-Layer Service-Triggered Mobility (MLSTM) is enabled.\n\nThe RDN of this MO is ReportConfigB2CdmaUlTrig=1.";
      status deprecated {
        yexte:status-information "Since 17.Q4. Has no functional behavior. Planned to be removed.";
      }
      yexte:is-system-created;
      erienmyext:enm-type MOC;
      uses moc-ReportConfigB2CdmaUlTrig-keys;
      container attributes {
        description "Attributes for ReportConfigB2CdmaUlTrig";
        uses moc-ReportConfigB2CdmaUlTrig;
      } // end 'container attributes'
    } // end 'list ReportConfigB2CdmaUlTrig'
  }
  augment /erienmnrmcomtop:ManagedElement/erienmnrmlrat:ENodeBFunction/erienmnrmlrat:EUtranCellTDD/erienmnrmlrat:UeMeasControl {
    list ReportConfigB2CdmaUlTrig {
      key id;
      max-elements 1;
      description "Contains report configuration settings for the B2 event for CDMA2000 measurements initiated by Uplink-Triggered Inter-Frequency Mobility. The actual threshold values used can be adjusted by frequency relation or QCI related offsets if the feature Multi-Layer Service-Triggered Mobility (MLSTM) is enabled.\n\nThe RDN of this MO is ReportConfigB2CdmaUlTrig=1.";
      status deprecated {
        yexte:status-information "Since 17.Q4. Has no functional behavior. Planned to be removed.";
      }
      yexte:is-system-created;
      erienmyext:enm-type MOC;
      uses moc-ReportConfigB2CdmaUlTrig-keys;
      container attributes {
        description "Attributes for ReportConfigB2CdmaUlTrig";
        uses moc-ReportConfigB2CdmaUlTrig;
      } // end 'container attributes'
    } // end 'list ReportConfigB2CdmaUlTrig'
  }
  augment /erienmnrmcomtop:ManagedElement/erienmnrmlrat:ENodeBFunction {
    list GUtraNetwork {
      key id;
      max-elements 1;
      description "This managed object is a container for Managed Objects related to GUTRA networks.";
      erienmyext:enm-type MOC;
      uses moc-GUtraNetwork-keys;
      container attributes {
        description "Attributes for GUtraNetwork";
        uses moc-GUtraNetwork;
      } // end 'container attributes'
    } // end 'list GUtraNetwork'
  }
  augment /erienmnrmcomtop:ManagedElement/erienmnrmlrat:ENodeBFunction/erienmnrmlrat:EUtranCellFDD/erienmnrmlrat:UeMeasControl {
    list ReportConfigEUtraBestCell {
      key id;
      max-elements 1;
      description "This managed object contains the Report Configuration settings for best cell UE measurements.\n\nThe RDN of this MO is ReportConfigEUtraBestCell=1.";
      yexte:is-system-created;
      erienmyext:enm-type MOC;
      uses moc-ReportConfigEUtraBestCell-keys;
      container attributes {
        description "Attributes for ReportConfigEUtraBestCell";
        uses moc-ReportConfigEUtraBestCell;
      } // end 'container attributes'
    } // end 'list ReportConfigEUtraBestCell'
  }
  augment /erienmnrmcomtop:ManagedElement/erienmnrmlrat:ENodeBFunction/erienmnrmlrat:EUtranCellTDD/erienmnrmlrat:UeMeasControl {
    list ReportConfigEUtraBestCell {
      key id;
      max-elements 1;
      description "This managed object contains the Report Configuration settings for best cell UE measurements.\n\nThe RDN of this MO is ReportConfigEUtraBestCell=1.";
      yexte:is-system-created;
      erienmyext:enm-type MOC;
      uses moc-ReportConfigEUtraBestCell-keys;
      container attributes {
        description "Attributes for ReportConfigEUtraBestCell";
        uses moc-ReportConfigEUtraBestCell;
      } // end 'container attributes'
    } // end 'list ReportConfigEUtraBestCell'
  }
  augment /erienmnrmcomtop:ManagedElement/erienmnrmlrat:ENodeBFunction/erienmnrmlrat:AdmissionControl {
    list DiffAdmCtrlFilteringProfile {
      key id;
      max-elements 6;
      description "Filtering profile for additional level of Differentiated Admission Control.\nAttributes take effect only when AdmissionControl::diffAdmCtrlFilteringEnabled is true.";
      erienmyext:enm-type MOC;
      uses moc-DiffAdmCtrlFilteringProfile-keys;
      container attributes {
        description "Attributes for DiffAdmCtrlFilteringProfile";
        uses moc-DiffAdmCtrlFilteringProfile;
      } // end 'container attributes'
    } // end 'list DiffAdmCtrlFilteringProfile'
  }
  augment /erienmnrmcomtop:ManagedElement/erienmnrmlrat:ENodeBFunction/erienmnrmlrat:EUtranCellTDD {
    list CellPerformance {
      key id;
      max-elements 1;
      description "Contains parameters related to cell level performance improvement.\n\nThe RDN of this MO is CellPerformance=1.";
      yexte:is-system-created;
      erienmyext:enm-type MOC;
      uses moc-CellPerformance-keys;
    } // end 'list CellPerformance'
  }
  augment /erienmnrmcomtop:ManagedElement/erienmnrmlrat:ENodeBFunction/erienmnrmlrat:EUtranCellFDD {
    list CellPerformance {
      key id;
      max-elements 1;
      description "Contains parameters related to cell level performance improvement.\n\nThe RDN of this MO is CellPerformance=1.";
      yexte:is-system-created;
      erienmyext:enm-type MOC;
      uses moc-CellPerformance-keys;
    } // end 'list CellPerformance'
  }
  augment /erienmnrmcomtop:ManagedElement/erienmnrmlrat:ENodeBFunction {
    list MeasCellGroup {
      key id;
      max-elements 24;
      description "Set of measurement group defined for use in the node.";
      erienmyext:enm-type MOC;
      uses moc-MeasCellGroup-keys;
      container attributes {
        description "Attributes for MeasCellGroup";
        uses moc-MeasCellGroup;
      } // end 'container attributes'
    } // end 'list MeasCellGroup'
  }
  augment /erienmnrmcomtop:ManagedElement/erienmnrmlrat:ENodeBFunction/erienmnrmlrat:EUtranCellFDD/erienmnrmlrat:UeMeasControl {
    list ReportConfigA1Prim {
      key id;
      max-elements 1;
      description "This managed object contains report configuration settings for the primary A1 event measurements. The A1 event is used to detect the Bad Coverage Cease condition.\nPrimary and secondary reporting configuration MOs refer to the option to use different settings for two simultaneous measurements for the event A1.\n\nThe RDN of this MO is ReportConfigA1Prim=1.";
      yexte:is-system-created;
      erienmyext:enm-type MOC;
      uses moc-ReportConfigA1Prim-keys;
      container attributes {
        description "Attributes for ReportConfigA1Prim";
        uses moc-ReportConfigA1Prim;
      } // end 'container attributes'
    } // end 'list ReportConfigA1Prim'
  }
  augment /erienmnrmcomtop:ManagedElement/erienmnrmlrat:ENodeBFunction/erienmnrmlrat:EUtranCellTDD/erienmnrmlrat:UeMeasControl {
    list ReportConfigA1Prim {
      key id;
      max-elements 1;
      description "This managed object contains report configuration settings for the primary A1 event measurements. The A1 event is used to detect the Bad Coverage Cease condition.\nPrimary and secondary reporting configuration MOs refer to the option to use different settings for two simultaneous measurements for the event A1.\n\nThe RDN of this MO is ReportConfigA1Prim=1.";
      yexte:is-system-created;
      erienmyext:enm-type MOC;
      uses moc-ReportConfigA1Prim-keys;
      container attributes {
        description "Attributes for ReportConfigA1Prim";
        uses moc-ReportConfigA1Prim;
      } // end 'container attributes'
    } // end 'list ReportConfigA1Prim'
  }
  augment /erienmnrmcomtop:ManagedElement/erienmnrmlrat:ENodeBFunction {
    list PwsCmas {
      key id;
      max-elements 64;
      description "This MO class stores warning information to be broadcast in SIB12.\n\nThe RDNs of these MOs are PwsCmas=1 to PwsCmas=64.";
      yexte:is-system-created;
      erienmyext:enm-type MOC;
      uses moc-PwsCmas-keys;
    } // end 'list PwsCmas'
  }
  augment /erienmnrmcomtop:ManagedElement/erienmnrmlrat:ENodeBFunction/erienmnrmlrat:EUtranCellFDD/erienmnrmlrat:UeMeasControl {
    list ReportConfigB2CdmaRttUlTrig {
      key id;
      max-elements 1;
      description "Contains report configuration settings for the B2 event for CDMA2000 1xRTT measurements initiated by Uplink-Triggered Inter-Frequency Mobility. The actual threshold values used can be adjusted by frequency relation or QCI related offsets if the feature Multi-Layer Service-Triggered Mobility (MLSTM) is enabled.\n\nThe RDN of this MO is ReportConfigB2CdmaRttUlTrig=1.";
      status deprecated {
        yexte:status-information "Since 17.Q4. Has no functional behavior. Planned to be removed.";
      }
      yexte:is-system-created;
      erienmyext:enm-type MOC;
      uses moc-ReportConfigB2CdmaRttUlTrig-keys;
      container attributes {
        description "Attributes for ReportConfigB2CdmaRttUlTrig";
        uses moc-ReportConfigB2CdmaRttUlTrig;
      } // end 'container attributes'
    } // end 'list ReportConfigB2CdmaRttUlTrig'
  }
  augment /erienmnrmcomtop:ManagedElement/erienmnrmlrat:ENodeBFunction/erienmnrmlrat:EUtranCellTDD/erienmnrmlrat:UeMeasControl {
    list ReportConfigB2CdmaRttUlTrig {
      key id;
      max-elements 1;
      description "Contains report configuration settings for the B2 event for CDMA2000 1xRTT measurements initiated by Uplink-Triggered Inter-Frequency Mobility. The actual threshold values used can be adjusted by frequency relation or QCI related offsets if the feature Multi-Layer Service-Triggered Mobility (MLSTM) is enabled.\n\nThe RDN of this MO is ReportConfigB2CdmaRttUlTrig=1.";
      status deprecated {
        yexte:status-information "Since 17.Q4. Has no functional behavior. Planned to be removed.";
      }
      yexte:is-system-created;
      erienmyext:enm-type MOC;
      uses moc-ReportConfigB2CdmaRttUlTrig-keys;
      container attributes {
        description "Attributes for ReportConfigB2CdmaRttUlTrig";
        uses moc-ReportConfigB2CdmaRttUlTrig;
      } // end 'container attributes'
    } // end 'list ReportConfigB2CdmaRttUlTrig'
  }
  augment /erienmnrmcomtop:ManagedElement/erienmnrmlrat:ENodeBFunction/erienmnrmlrat:EUtranCellFDD {
    list InstantUplinkAccess {
      key id;
      max-elements 1;
      description "Parameters for Instant Uplink Access feature for EUtranCellFDD/TDD.\n\nThe RDN of this MO is InstantUplinkAccess=1.";
      yexte:is-system-created;
      erienmyext:enm-type MOC;
      uses moc-InstantUplinkAccess-keys;
      container attributes {
        description "Attributes for InstantUplinkAccess";
        uses moc-InstantUplinkAccess;
      } // end 'container attributes'
    } // end 'list InstantUplinkAccess'
  }
  augment /erienmnrmcomtop:ManagedElement/erienmnrmlrat:ENodeBFunction/erienmnrmlrat:EUtranCellTDD {
    list InstantUplinkAccess {
      key id;
      max-elements 1;
      description "Parameters for Instant Uplink Access feature for EUtranCellFDD/TDD.\n\nThe RDN of this MO is InstantUplinkAccess=1.";
      yexte:is-system-created;
      erienmyext:enm-type MOC;
      uses moc-InstantUplinkAccess-keys;
      container attributes {
        description "Attributes for InstantUplinkAccess";
        uses moc-InstantUplinkAccess;
      } // end 'container attributes'
    } // end 'list InstantUplinkAccess'
  }
  augment /erienmnrmcomtop:ManagedElement/erienmnrmlrat:ENodeBFunction {
    list PreschedProfile {
      key id;
      max-elements 5;
      description "Prescheduling profiles and parameters to map towards different advanced subscriber groups.\n\nThe RDNs of these MOs are PreschedProfile=0 to PreschedProfile=4.";
      yexte:is-system-created;
      erienmyext:enm-type MOC;
      uses moc-PreschedProfile-keys;
      container attributes {
        description "Attributes for PreschedProfile";
        uses moc-PreschedProfile;
      } // end 'container attributes'
    } // end 'list PreschedProfile'
  }
  augment /erienmnrmcomtop:ManagedElement/erienmnrmlrat:ENodeBFunction/erienmnrmlrat:EUtranCellFDD/erienmnrmlrat:UeMeasControl {
    list ReportConfigEUtraBadCovSec {
      key id;
      max-elements 1;
      description "This managed object contains the Report Configuration settings for secondary bad coverage UE measurements.\n\nThe RDN of this MO is ReportConfigEUtraBadCovSec=1.";
      yexte:is-system-created;
      erienmyext:enm-type MOC;
      uses moc-ReportConfigEUtraBadCovSec-keys;
      container attributes {
        description "Attributes for ReportConfigEUtraBadCovSec";
        uses moc-ReportConfigEUtraBadCovSec;
      } // end 'container attributes'
    } // end 'list ReportConfigEUtraBadCovSec'
  }
  augment /erienmnrmcomtop:ManagedElement/erienmnrmlrat:ENodeBFunction/erienmnrmlrat:EUtranCellTDD/erienmnrmlrat:UeMeasControl {
    list ReportConfigEUtraBadCovSec {
      key id;
      max-elements 1;
      description "This managed object contains the Report Configuration settings for secondary bad coverage UE measurements.\n\nThe RDN of this MO is ReportConfigEUtraBadCovSec=1.";
      yexte:is-system-created;
      erienmyext:enm-type MOC;
      uses moc-ReportConfigEUtraBadCovSec-keys;
      container attributes {
        description "Attributes for ReportConfigEUtraBadCovSec";
        uses moc-ReportConfigEUtraBadCovSec;
      } // end 'container attributes'
    } // end 'list ReportConfigEUtraBadCovSec'
  }
  augment /erienmnrmcomtop:ManagedElement/erienmnrmlrat:ENodeBFunction/erienmnrmlrat:Mbms {
    list MbsfnArea {
      key id;
      max-elements 48;
      description "This MO represents a MBMS Single Frequence Network (MBSFN) area and contains MBSFN area related parameters.";
      erienmyext:enm-type MOC;
      uses moc-MbsfnArea-keys;
      container attributes {
        description "Attributes for MbsfnArea";
        uses moc-MbsfnArea;
      } // end 'container attributes'
    } // end 'list MbsfnArea'
  }
  augment /erienmnrmcomtop:ManagedElement/erienmnrmlrat:ENodeBFunction {
    list AirIfLoadProfile {
      key id;
      max-elements 24;
      description "Contains parameters and constraints for Air Interface Load Generator needed to start the function in a Cell.";
      erienmyext:enm-type MOC;
      uses moc-AirIfLoadProfile-keys;
      container attributes {
        description "Attributes for AirIfLoadProfile";
        uses moc-AirIfLoadProfile;
      } // end 'container attributes'
    } // end 'list AirIfLoadProfile'
  }
  augment /erienmnrmcomtop:ManagedElement/erienmnrmlrat:ENodeBFunction/erienmnrmlrat:EUtranCellFDD {
    list GeranFreqGroupRelation {
      key id;
      max-elements 16;
      description "This Managed Object represents a mobility relation between an EUtranCellFDD or an EUtranCellTDD and a GeranFreqGroup. It contains parameters that are specific for this relation.\n\nDeleting this MO while the parent EUtranCellFDD/EUtranCellTDD has operationalState set to ENABLED is not recommended as it may affect traffic.";
      erienmyext:enm-type MOC;
      uses moc-GeranFreqGroupRelation-keys;
      container attributes {
        description "Attributes for GeranFreqGroupRelation";
        uses moc-GeranFreqGroupRelation;
      } // end 'container attributes'
    } // end 'list GeranFreqGroupRelation'
  }
  augment /erienmnrmcomtop:ManagedElement/erienmnrmlrat:ENodeBFunction/erienmnrmlrat:EUtranCellTDD {
    list GeranFreqGroupRelation {
      key id;
      max-elements 16;
      description "This Managed Object represents a mobility relation between an EUtranCellFDD or an EUtranCellTDD and a GeranFreqGroup. It contains parameters that are specific for this relation.\n\nDeleting this MO while the parent EUtranCellFDD/EUtranCellTDD has operationalState set to ENABLED is not recommended as it may affect traffic.";
      erienmyext:enm-type MOC;
      uses moc-GeranFreqGroupRelation-keys;
      container attributes {
        description "Attributes for GeranFreqGroupRelation";
        uses moc-GeranFreqGroupRelation;
      } // end 'container attributes'
    } // end 'list GeranFreqGroupRelation'
  }
  augment /erienmnrmcomtop:ManagedElement/erienmnrmlrat:ENodeBFunction/erienmnrmlrat:EUtranCellTDD {
    list MimoSleepFunction {
      key id;
      max-elements 1;
      description "Contains all MIMO sleep mode function configuration parameters of the in the cell.\n\nThe RDN of this MO is MimoSleepFunction=1.";
      yexte:is-system-created;
      erienmyext:enm-type MOC;
      uses moc-MimoSleepFunction-keys;
      container attributes {
        description "Attributes for MimoSleepFunction";
        uses moc-MimoSleepFunction;
      } // end 'container attributes'
    } // end 'list MimoSleepFunction'
  }
  augment /erienmnrmcomtop:ManagedElement/erienmnrmlrat:ENodeBFunction/erienmnrmlrat:EUtranCellFDD {
    list MimoSleepFunction {
      key id;
      max-elements 1;
      description "Contains all MIMO sleep mode function configuration parameters of the in the cell.\n\nThe RDN of this MO is MimoSleepFunction=1.";
      yexte:is-system-created;
      erienmyext:enm-type MOC;
      uses moc-MimoSleepFunction-keys;
      container attributes {
        description "Attributes for MimoSleepFunction";
        uses moc-MimoSleepFunction;
      } // end 'container attributes'
    } // end 'list MimoSleepFunction'
  }
  augment /erienmnrmcomtop:ManagedElement/erienmnrmlrat:ENodeBFunction/erienmnrmlrat:EUtranCellFDD/erienmnrmlrat:UeMeasControl {
    list ReportConfigEUtraIFBestCell {
      key id;
      max-elements 1;
      description "This managed object contains the report configuration settings for best cell measurements on other LTE frequencies.\n\nThe RDN of this MO is ReportConfigEUtraIFBestCell=1.";
      yexte:is-system-created;
      erienmyext:enm-type MOC;
      uses moc-ReportConfigEUtraIFBestCell-keys;
      container attributes {
        description "Attributes for ReportConfigEUtraIFBestCell";
        uses moc-ReportConfigEUtraIFBestCell;
      } // end 'container attributes'
    } // end 'list ReportConfigEUtraIFBestCell'
  }
  augment /erienmnrmcomtop:ManagedElement/erienmnrmlrat:ENodeBFunction/erienmnrmlrat:EUtranCellTDD/erienmnrmlrat:UeMeasControl {
    list ReportConfigEUtraIFBestCell {
      key id;
      max-elements 1;
      description "This managed object contains the report configuration settings for best cell measurements on other LTE frequencies.\n\nThe RDN of this MO is ReportConfigEUtraIFBestCell=1.";
      yexte:is-system-created;
      erienmyext:enm-type MOC;
      uses moc-ReportConfigEUtraIFBestCell-keys;
      container attributes {
        description "Attributes for ReportConfigEUtraIFBestCell";
        uses moc-ReportConfigEUtraIFBestCell;
      } // end 'container attributes'
    } // end 'list ReportConfigEUtraIFBestCell'
  }
  augment /erienmnrmcomtop:ManagedElement/erienmnrmlrat:ENodeBFunction/erienmnrmlrat:EUtraNetwork {
    list UnlicensedBandProfile {
      key id;
      max-elements 1;
      description "Structure for regulatory requirements for unlicensed bands.";
      erienmyext:enm-type MOC;
      uses moc-UnlicensedBandProfile-keys;
      container attributes {
        description "Attributes for UnlicensedBandProfile";
        uses moc-UnlicensedBandProfile;
      } // end 'container attributes'
    } // end 'list UnlicensedBandProfile'
  }
  augment /erienmnrmcomtop:ManagedElement/erienmnrmlrat:ENodeBFunction {
    list ImeisvTable {
      key id;
      max-elements 1;
      description "Contains eNB specific configuration used for feature Differentiated UE Handling.\n\nThe RDN of this MO is ImeisvTable=1.\n";
      yexte:is-system-created;
      erienmyext:enm-type MOC;
      uses moc-ImeisvTable-keys;
      container attributes {
        description "Attributes for ImeisvTable";
        uses moc-ImeisvTable;
      } // end 'container attributes'
    } // end 'list ImeisvTable'
  }
  augment /erienmnrmcomtop:ManagedElement/erienmnrmlrat:ENodeBFunction/erienmnrmlrat:EUtraNetwork {
    list ExternalENodeBFunction {
      key id;
      max-elements 512;
      description "This managed object represents another ENodeB.\n";
      erienmyext:enm-type MOC;
      uses moc-ExternalENodeBFunction-keys;
      container attributes {
        description "Attributes for ExternalENodeBFunction";
        uses moc-ExternalENodeBFunction;
      } // end 'container attributes'
    } // end 'list ExternalENodeBFunction'
  }
  augment /erienmnrmcomtop:ManagedElement/erienmnrmlrat:ENodeBFunction {
    list PmEventService {
      key id;
      max-elements 1;
      description "Contains the parameters for PM event handling functions.\n\nThe RDN of this MO is PmEventService=1.";
      yexte:is-system-created;
      erienmyext:enm-type MOC;
      uses moc-PmEventService-keys;
      container attributes {
        description "Attributes for PmEventService";
        uses moc-PmEventService;
      } // end 'container attributes'
    } // end 'list PmEventService'
  }
  augment /erienmnrmcomtop:ManagedElement/erienmnrmlrat:ENodeBFunction/erienmnrmlrat:LoadBalancingFunction {
    list IdleModePrioAtRelease {
      key id;
      max-elements 8;
      description "Contains distribution model data for the Pre-Distribution At Release feature that controls the priority of the frequencies in IdleModeMobilityControlInfo in the RRC Connection Release message.";
      erienmyext:enm-type MOC;
      uses moc-IdleModePrioAtRelease-keys;
      container attributes {
        description "Attributes for IdleModePrioAtRelease";
        uses moc-IdleModePrioAtRelease;
      } // end 'container attributes'
    } // end 'list IdleModePrioAtRelease'
  }
  augment /erienmnrmcomtop:ManagedElement/erienmnrmlrat:ENodeBFunction/erienmnrmlrat:EUtranCellFDD/erienmnrmlrat:UeMeasControl {
    list ReportConfigInterRatPm {
      key id;
      max-elements 2;
      description "Contains Report Configuration settings for UE measurements on inter-Rat (GERAN or UTRAN) frequencies initiated by PM.";
      erienmyext:enm-type MOC;
      uses moc-ReportConfigInterRatPm-keys;
      container attributes {
        description "Attributes for ReportConfigInterRatPm";
        uses moc-ReportConfigInterRatPm;
      } // end 'container attributes'
    } // end 'list ReportConfigInterRatPm'
  }
  augment /erienmnrmcomtop:ManagedElement/erienmnrmlrat:ENodeBFunction/erienmnrmlrat:EUtranCellTDD/erienmnrmlrat:UeMeasControl {
    list ReportConfigInterRatPm {
      key id;
      max-elements 2;
      description "Contains Report Configuration settings for UE measurements on inter-Rat (GERAN or UTRAN) frequencies initiated by PM.";
      erienmyext:enm-type MOC;
      uses moc-ReportConfigInterRatPm-keys;
      container attributes {
        description "Attributes for ReportConfigInterRatPm";
        uses moc-ReportConfigInterRatPm;
      } // end 'container attributes'
    } // end 'list ReportConfigInterRatPm'
  }
  augment /erienmnrmcomtop:ManagedElement/erienmnrmlrat:ENodeBFunction/erienmnrmlrat:EUtranCellFDD/erienmnrmlrat:EUtranFreqRelationUnlicensed {
    list EUtranCellRelationUnlicensed {
      key id;
      max-elements 24;
      description "MO handles relationship between two neighboring, unlicensed EUTRAN cells.";
      erienmyext:enm-type MOC;
      uses moc-EUtranCellRelationUnlicensed-keys;
      container attributes {
        description "Attributes for EUtranCellRelationUnlicensed";
        uses moc-EUtranCellRelationUnlicensed;
      } // end 'container attributes'
    } // end 'list EUtranCellRelationUnlicensed'
  }
  augment /erienmnrmcomtop:ManagedElement/erienmnrmlrat:ENodeBFunction/erienmnrmlrat:EUtranCellTDD/erienmnrmlrat:EUtranFreqRelationUnlicensed {
    list EUtranCellRelationUnlicensed {
      key id;
      max-elements 24;
      description "MO handles relationship between two neighboring, unlicensed EUTRAN cells.";
      erienmyext:enm-type MOC;
      uses moc-EUtranCellRelationUnlicensed-keys;
      container attributes {
        description "Attributes for EUtranCellRelationUnlicensed";
        uses moc-EUtranCellRelationUnlicensed;
      } // end 'container attributes'
    } // end 'list EUtranCellRelationUnlicensed'
  }
  augment /erienmnrmcomtop:ManagedElement/erienmnrmlrat:ENodeBFunction/erienmnrmlrat:GeraNetwork {
    list GeranFrequency {
      key id;
      max-elements 512;
      description "This Managed Object contains information of a specific Geran frequency.";
      erienmyext:enm-type MOC;
      uses moc-GeranFrequency-keys;
      container attributes {
        description "Attributes for GeranFrequency";
        uses moc-GeranFrequency;
      } // end 'container attributes'
    } // end 'list GeranFrequency'
  }
  augment /erienmnrmcomtop:ManagedElement/erienmnrmlrat:ENodeBFunction/erienmnrmlrat:RadioBearerTable {
    list SignalingRadioBearer {
      key id;
      max-elements 1;
      description "Signaling Radio Bearer configuration.\n\nThe RDN of this MO is SignalingRadioBearer=1.";
      yexte:is-system-created;
      erienmyext:enm-type MOC;
      uses moc-SignalingRadioBearer-keys;
      container attributes {
        description "Attributes for SignalingRadioBearer";
        uses moc-SignalingRadioBearer;
      } // end 'container attributes'
    } // end 'list SignalingRadioBearer'
  }
  augment /erienmnrmcomtop:ManagedElement/erienmnrmlrat:ENodeBFunction {
    list NbIdleModeLoadDistr {
      key id;
      max-elements 1;
      description "Distribution model data for the Pre-Distribution At Release feature that controls the priority of the frequencies in redirectedCarrierInfo in the RRC Connection Release message.";
      erienmyext:enm-type MOC;
      uses moc-NbIdleModeLoadDistr-keys;
      container attributes {
        description "Attributes for NbIdleModeLoadDistr";
        uses moc-NbIdleModeLoadDistr;
      } // end 'container attributes'
    } // end 'list NbIdleModeLoadDistr'
  }
  augment /erienmnrmcomtop:ManagedElement/erienmnrmlrat:ENodeBFunction {
    list UtraNetwork {
      key id;
      max-elements 1;
      description "This managed object represents a Utra network.\n";
      erienmyext:enm-type MOC;
      uses moc-UtraNetwork-keys;
      container attributes {
        description "Attributes for UtraNetwork";
        uses moc-UtraNetwork;
      } // end 'container attributes'
    } // end 'list UtraNetwork'
  }
  augment /erienmnrmcomtop:ManagedElement/erienmnrmlrat:ENodeBFunction/erienmnrmlrat:EUtranCellFDD/erienmnrmlrat:UeMeasControl {
    list ReportConfigEUtraInterFreqPm {
      key id;
      max-elements 2;
      description "Contains Report Configuration settings for UE measurements on EUTRAN inter-frequencies initiated by PM.";
      erienmyext:enm-type MOC;
      uses moc-ReportConfigEUtraInterFreqPm-keys;
      container attributes {
        description "Attributes for ReportConfigEUtraInterFreqPm";
        uses moc-ReportConfigEUtraInterFreqPm;
      } // end 'container attributes'
    } // end 'list ReportConfigEUtraInterFreqPm'
  }
  augment /erienmnrmcomtop:ManagedElement/erienmnrmlrat:ENodeBFunction/erienmnrmlrat:EUtranCellTDD/erienmnrmlrat:UeMeasControl {
    list ReportConfigEUtraInterFreqPm {
      key id;
      max-elements 2;
      description "Contains Report Configuration settings for UE measurements on EUTRAN inter-frequencies initiated by PM.";
      erienmyext:enm-type MOC;
      uses moc-ReportConfigEUtraInterFreqPm-keys;
      container attributes {
        description "Attributes for ReportConfigEUtraInterFreqPm";
        uses moc-ReportConfigEUtraInterFreqPm;
      } // end 'container attributes'
    } // end 'list ReportConfigEUtraInterFreqPm'
  }
  augment /erienmnrmcomtop:ManagedElement/erienmnrmlrat:ENodeBFunction/erienmnrmlrat:EUtraNetwork/erienmnrmlrat:ExternalENodeBFunction {
    list ExternalEUtranCellTDD {
      key id;
      max-elements 24;
      description "This managed object represents a neighbor EUTRAN cell (TDD) in another ENodeB in any MME pool.\n";
      erienmyext:enm-type MOC;
      uses moc-ExternalEUtranCellTDD-keys;
      container attributes {
        description "Attributes for ExternalEUtranCellTDD";
        uses moc-ExternalEUtranCellTDD;
      } // end 'container attributes'
    } // end 'list ExternalEUtranCellTDD'
  }
  augment /erienmnrmcomtop:ManagedElement/erienmnrmlrat:ENodeBFunction {
    list Mbms {
      key id;
      max-elements 1;
      description "This MO is the top level MO for Multimedia Broadcast Multicast Service (MBMS). It contains attributes, which are common for all parts of MBMS in the node. ";
      erienmyext:enm-type MOC;
      uses moc-Mbms-keys;
      container attributes {
        description "Attributes for Mbms";
        uses moc-Mbms;
      } // end 'container attributes'
    } // end 'list Mbms'
  }
  augment /erienmnrmcomtop:ManagedElement/erienmnrmlrat:ENodeBFunction {
    list CarrierAggregationFunction {
      key id;
      max-elements 1;
      description "Parameters and constraints for Carrier Aggregation feature.\n\nThe RDN of this MO is CarrierAggregationFunction=1.";
      yexte:is-system-created;
      erienmyext:enm-type MOC;
      uses moc-CarrierAggregationFunction-keys;
      container attributes {
        description "Attributes for CarrierAggregationFunction";
        uses moc-CarrierAggregationFunction;
      } // end 'container attributes'
    } // end 'list CarrierAggregationFunction'
  }
  augment /erienmnrmcomtop:ManagedElement/erienmnrmlrat:ENodeBFunction/erienmnrmlrat:EUtranCellFDD/erienmnrmlrat:UeMeasControl {
    list ReportConfigB2Utra {
      key id;
      max-elements 1;
      description "This managed object contains report configuration settings for the B2 event for UTRA measurements. The B2 event is used to detect when a UTRAN cell becomes better than threshold2, and serving cell becomes worse than threshold1. The actual threshold values used can be adjusted by frequency relation related offsets if the feature Multi-Layer Service-Triggered Mobility (MLSTM) is enabled.\n\nThe RDN of this MO is ReportConfigB2Utra=1.";
      yexte:is-system-created;
      erienmyext:enm-type MOC;
      uses moc-ReportConfigB2Utra-keys;
      container attributes {
        description "Attributes for ReportConfigB2Utra";
        uses moc-ReportConfigB2Utra;
      } // end 'container attributes'
    } // end 'list ReportConfigB2Utra'
  }
  augment /erienmnrmcomtop:ManagedElement/erienmnrmlrat:ENodeBFunction/erienmnrmlrat:EUtranCellTDD/erienmnrmlrat:UeMeasControl {
    list ReportConfigB2Utra {
      key id;
      max-elements 1;
      description "This managed object contains report configuration settings for the B2 event for UTRA measurements. The B2 event is used to detect when a UTRAN cell becomes better than threshold2, and serving cell becomes worse than threshold1. The actual threshold values used can be adjusted by frequency relation related offsets if the feature Multi-Layer Service-Triggered Mobility (MLSTM) is enabled.\n\nThe RDN of this MO is ReportConfigB2Utra=1.";
      yexte:is-system-created;
      erienmyext:enm-type MOC;
      uses moc-ReportConfigB2Utra-keys;
      container attributes {
        description "Attributes for ReportConfigB2Utra";
        uses moc-ReportConfigB2Utra;
      } // end 'container attributes'
    } // end 'list ReportConfigB2Utra'
  }
  augment /erienmnrmcomtop:ManagedElement/erienmnrmlrat:ENodeBFunction {
    list Rcs {
      key id;
      max-elements 1;
      description "Models the manageable characteristics of Radio Connection Supervision feature.\n\nThe RDN of this MO is Rcs=1.";
      yexte:is-system-created;
      erienmyext:enm-type MOC;
      uses moc-Rcs-keys;
      container attributes {
        description "Attributes for Rcs";
        uses moc-Rcs;
      } // end 'container attributes'
    } // end 'list Rcs'
  }
  augment /erienmnrmcomtop:ManagedElement/erienmnrmlrat:ENodeBFunction/erienmnrmlrat:Cdma2000Network/erienmnrmlrat:Cdma2000FreqBand/erienmnrmlrat:Cdma2000Freq {
    list ExternalCdma20001xRttCell {
      key id;
      max-elements 392;
      description "The MO represents a CDMA2000 1xRTT cell.";
      erienmyext:enm-type MOC;
      uses moc-ExternalCdma20001xRttCell-keys;
      container attributes {
        description "Attributes for ExternalCdma20001xRttCell";
        uses moc-ExternalCdma20001xRttCell;
      } // end 'container attributes'
    } // end 'list ExternalCdma20001xRttCell'
  }
  augment /erienmnrmcomtop:ManagedElement/erienmnrmlrat:ENodeBFunction {
    list EUtraNetwork {
      key id;
      max-elements 1;
      description "Container for MOs related to EUTRA networks.\n\nThe RDN of this MO is EUtraNetwork=1.";
      yexte:is-system-created;
      erienmyext:enm-type MOC;
      uses moc-EUtraNetwork-keys;
      container attributes {
        description "Attributes for EUtraNetwork";
        uses moc-EUtraNetwork;
      } // end 'container attributes'
    } // end 'list EUtraNetwork'
  }
  augment /erienmnrmcomtop:ManagedElement/erienmnrmlrat:ENodeBFunction/erienmnrmlrat:EUtranCellFDD {
    list UtranFreqRelation {
      key id;
      max-elements 16;
      description "This Managed Object represents a UTRAN FDD mobility relation between a EUtranCellFDD or EUtranCellTDD and an UtranFrequency. It contains parameters that are specific for this relation.\n\nDeleting this MO while the parent EUtranCellFDD/EUtranCellTDD has operationalState set to ENABLED is not recommended as it may affect traffic.";
      erienmyext:enm-type MOC;
      uses moc-UtranFreqRelation-keys;
      container attributes {
        description "Attributes for UtranFreqRelation";
        uses moc-UtranFreqRelation;
      } // end 'container attributes'
    } // end 'list UtranFreqRelation'
  }
  augment /erienmnrmcomtop:ManagedElement/erienmnrmlrat:ENodeBFunction/erienmnrmlrat:EUtranCellTDD {
    list UtranFreqRelation {
      key id;
      max-elements 16;
      description "This Managed Object represents a UTRAN FDD mobility relation between a EUtranCellFDD or EUtranCellTDD and an UtranFrequency. It contains parameters that are specific for this relation.\n\nDeleting this MO while the parent EUtranCellFDD/EUtranCellTDD has operationalState set to ENABLED is not recommended as it may affect traffic.";
      erienmyext:enm-type MOC;
      uses moc-UtranFreqRelation-keys;
      container attributes {
        description "Attributes for UtranFreqRelation";
        uses moc-UtranFreqRelation;
      } // end 'container attributes'
    } // end 'list UtranFreqRelation'
  }
  augment /erienmnrmcomtop:ManagedElement/erienmnrmlrat:ENodeBFunction {
    list EndcProfile {
      key id;
      max-elements 16;
      description "EN-DC profiles and EN-DC parameters that map to different QCIs.";
      erienmyext:enm-type MOC;
      uses moc-EndcProfile-keys;
      container attributes {
        description "Attributes for EndcProfile";
        uses moc-EndcProfile;
      } // end 'container attributes'
    } // end 'list EndcProfile'
  }
  augment /erienmnrmcomtop:ManagedElement/erienmnrmlrat:ENodeBFunction/erienmnrmlrat:EUtranCellFDD/erienmnrmlrat:UeMeasControl {
    list ReportConfigB2UtraUlTrig {
      key id;
      max-elements 1;
      description "Contains report configuration settings for the B2 event for UTRA measurements initiated by Uplink-Triggered Inter-Frequency Mobility. The actual threshold values used can be adjusted by frequency relation or QCI related offsets if the feature Multi-Layer Service-Triggered Mobility (MLSTM) is enabled.\n\nThe RDN of this MO is ReportConfigB2UtraUlTrig=1.";
      yexte:is-system-created;
      erienmyext:enm-type MOC;
      uses moc-ReportConfigB2UtraUlTrig-keys;
      container attributes {
        description "Attributes for ReportConfigB2UtraUlTrig";
        uses moc-ReportConfigB2UtraUlTrig;
      } // end 'container attributes'
    } // end 'list ReportConfigB2UtraUlTrig'
  }
  augment /erienmnrmcomtop:ManagedElement/erienmnrmlrat:ENodeBFunction/erienmnrmlrat:EUtranCellTDD/erienmnrmlrat:UeMeasControl {
    list ReportConfigB2UtraUlTrig {
      key id;
      max-elements 1;
      description "Contains report configuration settings for the B2 event for UTRA measurements initiated by Uplink-Triggered Inter-Frequency Mobility. The actual threshold values used can be adjusted by frequency relation or QCI related offsets if the feature Multi-Layer Service-Triggered Mobility (MLSTM) is enabled.\n\nThe RDN of this MO is ReportConfigB2UtraUlTrig=1.";
      yexte:is-system-created;
      erienmyext:enm-type MOC;
      uses moc-ReportConfigB2UtraUlTrig-keys;
      container attributes {
        description "Attributes for ReportConfigB2UtraUlTrig";
        uses moc-ReportConfigB2UtraUlTrig;
      } // end 'container attributes'
    } // end 'list ReportConfigB2UtraUlTrig'
  }
  augment /erienmnrmcomtop:ManagedElement/erienmnrmlrat:ENodeBFunction/erienmnrmlrat:EUtranCellFDD {
    list EUtranFreqRelation {
      key id;
      max-elements 16;
      description "This MO represents a mobility relation between a EUtranCellFDD and a EUtranFrequency. It contains parameters that are specific for this relation.\nTo include SIB3 in System Information, one instance of this MO must be created which refers to a EUtranFrequency MO with the parameter arfcnValueEUtranDl set to the same value as the parent EUtranCellFDD/EUtranCellTDDs parameter earfcndl.\n\n It is only allowed to remove the EUtranFreqRelation, refering to the same frequency as the parent MO EUtranCellFDD/EUtranCellTDD has, when the EUtranCellFDD/EUtranCellTDD is locked.\n\nDeleting this MO while the parent EUtranCellFDD/EUtranCellTDD has operationalState set to ENABLED is not recommended as it may affect traffic.\n";
      erienmyext:enm-type MOC;
      uses moc-EUtranFreqRelation-keys;
      container attributes {
        description "Attributes for EUtranFreqRelation";
        uses moc-EUtranFreqRelation;
      } // end 'container attributes'
    } // end 'list EUtranFreqRelation'
  }
  augment /erienmnrmcomtop:ManagedElement/erienmnrmlrat:ENodeBFunction/erienmnrmlrat:EUtranCellTDD {
    list EUtranFreqRelation {
      key id;
      max-elements 16;
      description "This MO represents a mobility relation between a EUtranCellFDD and a EUtranFrequency. It contains parameters that are specific for this relation.\nTo include SIB3 in System Information, one instance of this MO must be created which refers to a EUtranFrequency MO with the parameter arfcnValueEUtranDl set to the same value as the parent EUtranCellFDD/EUtranCellTDDs parameter earfcndl.\n\n It is only allowed to remove the EUtranFreqRelation, refering to the same frequency as the parent MO EUtranCellFDD/EUtranCellTDD has, when the EUtranCellFDD/EUtranCellTDD is locked.\n\nDeleting this MO while the parent EUtranCellFDD/EUtranCellTDD has operationalState set to ENABLED is not recommended as it may affect traffic.\n";
      erienmyext:enm-type MOC;
      uses moc-EUtranFreqRelation-keys;
      container attributes {
        description "Attributes for EUtranFreqRelation";
        uses moc-EUtranFreqRelation;
      } // end 'container attributes'
    } // end 'list EUtranFreqRelation'
  }
  augment /erienmnrmcomtop:ManagedElement/erienmnrmlrat:ENodeBFunction/erienmnrmlrat:RadioBearerTable {
    list DataRadioBearer {
      key id;
      max-elements 1;
      description "Radio Bearer configuration.\n\nThe RDN of this MO is DataRadioBearer=1.";
      yexte:is-system-created;
      erienmyext:enm-type MOC;
      uses moc-DataRadioBearer-keys;
      container attributes {
        description "Attributes for DataRadioBearer";
        uses moc-DataRadioBearer;
      } // end 'container attributes'
    } // end 'list DataRadioBearer'
  }
  augment /erienmnrmcomtop:ManagedElement/erienmnrmlrat:ENodeBFunction/erienmnrmlrat:EUtranCellFDD/erienmnrmlrat:UeMeasControl {
    list ReportConfigEUtraBadCovPrim {
      key id;
      max-elements 1;
      description "This managed object contains the Report Configuration settings for primary bad coverage UE measurements.\n\nThe RDN of this MO is ReportConfigEUtraBadCovPrim=1.";
      yexte:is-system-created;
      erienmyext:enm-type MOC;
      uses moc-ReportConfigEUtraBadCovPrim-keys;
      container attributes {
        description "Attributes for ReportConfigEUtraBadCovPrim";
        uses moc-ReportConfigEUtraBadCovPrim;
      } // end 'container attributes'
    } // end 'list ReportConfigEUtraBadCovPrim'
  }
  augment /erienmnrmcomtop:ManagedElement/erienmnrmlrat:ENodeBFunction/erienmnrmlrat:EUtranCellTDD/erienmnrmlrat:UeMeasControl {
    list ReportConfigEUtraBadCovPrim {
      key id;
      max-elements 1;
      description "This managed object contains the Report Configuration settings for primary bad coverage UE measurements.\n\nThe RDN of this MO is ReportConfigEUtraBadCovPrim=1.";
      yexte:is-system-created;
      erienmyext:enm-type MOC;
      uses moc-ReportConfigEUtraBadCovPrim-keys;
      container attributes {
        description "Attributes for ReportConfigEUtraBadCovPrim";
        uses moc-ReportConfigEUtraBadCovPrim;
      } // end 'container attributes'
    } // end 'list ReportConfigEUtraBadCovPrim'
  }
  augment /erienmnrmcomtop:ManagedElement/erienmnrmlrat:ENodeBFunction/erienmnrmlrat:SubscriberProfileID {
    list RATFreqPrio {
      key id;
      max-elements 8;
      description "Contains data that overrides information in the IdleModeMobilityControlInfo and RedirectedCarrierInfo (sent to UE in RRC Connection Release) that is configured for the cell. It also contains attributes that control load balancing and offloading. Only UEs that have a SPID value matching the list in this MOC are affected.";
      erienmyext:enm-type MOC;
      uses moc-RATFreqPrio-keys;
      container attributes {
        description "Attributes for RATFreqPrio";
        uses moc-RATFreqPrio;
      } // end 'container attributes'
    } // end 'list RATFreqPrio'
  }
  augment /erienmnrmcomtop:ManagedElement/erienmnrmlrat:ENodeBFunction {
    list PreschedulingProfile {
      key id;
      max-elements 1;
      description "Contains prescheduling profiles, prescheduling parameters, to map towards the different QCIs.\n\nThe RDN of this MO is PreschedulingProfile=initial.";
      yexte:is-system-created;
      erienmyext:enm-type MOC;
      uses moc-PreschedulingProfile-keys;
      container attributes {
        description "Attributes for PreschedulingProfile";
        uses moc-PreschedulingProfile;
      } // end 'container attributes'
    } // end 'list PreschedulingProfile'
  }
  augment /erienmnrmcomtop:ManagedElement/erienmnrmlrat:ENodeBFunction/erienmnrmlrat:EUtraNetwork/erienmnrmlrat:ExternalENodeBFunction/erienmnrmlrat:TermPointToENB/erienmnrmlrat:TermPointToLbm {
    list GtpuApplicationTunnel {
      key id;
      max-elements 2;
      description "Designates a GTP-U tunnel used to support a baseband-to-baseband application.\n\nThe RDNs of these MOs are GtpuApplicationTunnel=0 to GtpuApplicationTunnel=1.";
      yexte:is-system-created;
      erienmyext:enm-type MOC;
      uses moc-GtpuApplicationTunnel-keys;
    } // end 'list GtpuApplicationTunnel'
  }
  augment /erienmnrmcomtop:ManagedElement/erienmnrmlrat:ENodeBFunction/erienmnrmlrat:EUtraNetwork/erienmnrmlrat:ExternalENodeBFunction {
    list BbLink {
      key id;
      max-elements 32;
      description "Models a eRAN application link between the basebands of the eNodeB and a neighboring eNodeB.\n\nThe RDNs of these MOs are BbLink=1 to BbLink=5.\n\nThe BbLink MO under ExternalENodeBFunction is deprecated since L17A and will be removed. The new parent MO is EranInterMeLink.";
      yexte:is-system-created;
      erienmyext:enm-type MOC;
      uses moc-BbLink-keys;
      container attributes {
        description "Attributes for BbLink";
        uses moc-BbLink;
      } // end 'container attributes'
    } // end 'list BbLink'
  }
  augment /erienmnrmcomtop:ManagedElement/erienmnrmlrat:ENodeBFunction/erienmnrmlrat:EUtraNetwork/erienmnrmlrat:ExternalENodeBFunction/erienmnrmlrat:EranInterMeLink {
    list BbLink {
      key id;
      max-elements 5;
      description "Models a eRAN application link between the basebands of the eNodeB and a neighboring eNodeB.\n\nThe RDNs of these MOs are BbLink=1 to BbLink=5.\n\nThe BbLink MO under ExternalENodeBFunction is deprecated since L17A and will be removed. The new parent MO is EranInterMeLink.";
      yexte:is-system-created;
      erienmyext:enm-type MOC;
      uses moc-BbLink-keys;
      container attributes {
        description "Attributes for BbLink";
        uses moc-BbLink;
      } // end 'container attributes'
    } // end 'list BbLink'
  }
  augment /erienmnrmcomtop:ManagedElement/erienmnrmlrat:ENodeBFunction/erienmnrmlrat:EUtranCellFDD/erienmnrmlrat:UeMeasControl {
    list ReportConfigSearch {
      key id;
      max-elements 1;
      description "Contains report configuration settings for search area measurements that relate to features Mobility Control at Poor Coverage and Multi-Layer Service-Triggered Mobility (MLSTM). Corresponds to parameters needed for A2search, A1Search, A2OuterSearch and A2Critical events and QCI specific offsets to such parameters.\n\nThe RDN of this MO is ReportConfigSearch=1.";
      yexte:is-system-created;
      erienmyext:enm-type MOC;
      uses moc-ReportConfigSearch-keys;
      container attributes {
        description "Attributes for ReportConfigSearch";
        uses moc-ReportConfigSearch;
      } // end 'container attributes'
    } // end 'list ReportConfigSearch'
  }
  augment /erienmnrmcomtop:ManagedElement/erienmnrmlrat:ENodeBFunction/erienmnrmlrat:EUtranCellTDD/erienmnrmlrat:UeMeasControl {
    list ReportConfigSearch {
      key id;
      max-elements 1;
      description "Contains report configuration settings for search area measurements that relate to features Mobility Control at Poor Coverage and Multi-Layer Service-Triggered Mobility (MLSTM). Corresponds to parameters needed for A2search, A1Search, A2OuterSearch and A2Critical events and QCI specific offsets to such parameters.\n\nThe RDN of this MO is ReportConfigSearch=1.";
      yexte:is-system-created;
      erienmyext:enm-type MOC;
      uses moc-ReportConfigSearch-keys;
      container attributes {
        description "Attributes for ReportConfigSearch";
        uses moc-ReportConfigSearch;
      } // end 'container attributes'
    } // end 'list ReportConfigSearch'
  }
  augment /erienmnrmcomtop:ManagedElement/erienmnrmlrat:ENodeBFunction {
    list FlexibleQoSFunction {
      key id;
      max-elements 1;
      description "Contains eNB specific configuration used for feature Flexible QoS.\n\nThe RDN of this MO is FlexibleQoSFunction=1.";
      yexte:is-system-created;
      erienmyext:enm-type MOC;
      uses moc-FlexibleQoSFunction-keys;
    } // end 'list FlexibleQoSFunction'
  }
  augment /erienmnrmcomtop:ManagedElement/erienmnrmlrat:ENodeBFunction {
    list RlfProfile {
      key id;
      max-elements 23;
      description "Contains RLF profiles and RLF parameters to map to the different QCIs. The first instance, RlfProfileId 0, is the default RLF profile.\n\nThe RDNs of these MOs are RlfProfile=0 to RlfProfile=22.\n\nThe timers and constants settings are provided to the UE by dedicated signaling.";
      yexte:is-system-created;
      erienmyext:enm-type MOC;
      uses moc-RlfProfile-keys;
      container attributes {
        description "Attributes for RlfProfile";
        uses moc-RlfProfile;
      } // end 'container attributes'
    } // end 'list RlfProfile'
  }
  augment /erienmnrmcomtop:ManagedElement/erienmnrmlrat:ENodeBFunction {
    list EUtranCellFDD {
      key id;
      max-elements 24;
      description "This MO represents a Cell and contains parameters needed by the cell. It also contains parameters for the mandatory common channels.\n";
      erienmyext:enm-type MOC;
      uses moc-EUtranCellFDD-keys;
      container attributes {
        description "Attributes for EUtranCellFDD";
        uses moc-EUtranCellFDD;
      } // end 'container attributes'
    } // end 'list EUtranCellFDD'
  }
  augment /erienmnrmcomtop:ManagedElement/erienmnrmlrat:ENodeBFunction {
    list Cdma2000Network {
      key id;
      max-elements 1;
      description "This Managed Object is a container for CDMA2000 related Managed Objects.\n";
      erienmyext:enm-type MOC;
      uses moc-Cdma2000Network-keys;
      container attributes {
        description "Attributes for Cdma2000Network";
        uses moc-Cdma2000Network;
      } // end 'container attributes'
    } // end 'list Cdma2000Network'
  }
  augment /erienmnrmcomtop:ManagedElement/erienmnrmlrat:ENodeBFunction {
    list SecurityHandling {
      key id;
      max-elements 1;
      description "Models manageable characteristics of security handling except security handling during X2 handover and S1 handover. These characteristics are then used by all instances of RRC dedicated protocol.\n\nThe RDN of this MO is SecurityHandling=1.";
      yexte:is-system-created;
      erienmyext:enm-type MOC;
      uses moc-SecurityHandling-keys;
      container attributes {
        description "Attributes for SecurityHandling";
        uses moc-SecurityHandling;
      } // end 'container attributes'
    } // end 'list SecurityHandling'
  }
  augment /erienmnrmcomtop:ManagedElement/erienmnrmlrat:ENodeBFunction {
    list ResourcePartitionGroup {
      key id;
      max-elements 24;
      description "Group of resource partitions used together in a cell. All partitions in a group must contain the same empty attribute (plmnList or spidList). Multiple partitions in the same group must not be applicable to the same UE.";
      erienmyext:enm-type MOC;
      uses moc-ResourcePartitionGroup-keys;
      container attributes {
        description "Attributes for ResourcePartitionGroup";
        uses moc-ResourcePartitionGroup;
      } // end 'container attributes'
    } // end 'list ResourcePartitionGroup'
  }
  augment /erienmnrmcomtop:ManagedElement/erienmnrmlrat:ENodeBFunction/erienmnrmlrat:QciTable {
    list QciProfilePredefined {
      key id;
      max-elements 14;
      description "Bearer-level QoS configuration.\nNot possible to create or remove instances of this MO.\nEach QciProfilePredefined corresponds to a standardized QCI as described in 3GPP TS 23.203. Except for a default QCI profile activated whenever a profile related to a specific QCI is not defined.\n\nRDNs of these MOs are QciProfilePredefined=qci1 to QciProfilePredefined=qci9, QciProfilePredefined=qci65, QciProfilePredefined=qci66, QciProfilePredefined=qci69, QciProfilePredefined=qci70, and QciProfilePredefined=default.";
      yexte:is-system-created;
      erienmyext:enm-type MOC;
      uses moc-QciProfilePredefined-keys;
      container attributes {
        description "Attributes for QciProfilePredefined";
        uses moc-QciProfilePredefined;
      } // end 'container attributes'
    } // end 'list QciProfilePredefined'
  }
  augment /erienmnrmcomtop:ManagedElement/erienmnrmlrat:ENodeBFunction/erienmnrmlrat:Mbms/erienmnrmlrat:MbsfnArea {
    list PmchMch {
      key id;
      max-elements 15;
      description "This MO represents configuration related to the Uu physical and transport layers for Multimedia Broadcast Multicast Service (MBMS).";
      erienmyext:enm-type MOC;
      uses moc-PmchMch-keys;
      container attributes {
        description "Attributes for PmchMch";
        uses moc-PmchMch;
      } // end 'container attributes'
    } // end 'list PmchMch'
  }
  augment /erienmnrmcomtop:ManagedElement/erienmnrmlrat:ENodeBFunction/erienmnrmlrat:EUtranCellFDD/erienmnrmlrat:UeMeasControl {
    list ReportConfigA5SoftLock {
      key id;
      max-elements 1;
      description "Contains the Report Configuration settings for the A5 event measurements initiated for Soft-Lock of Cell.\n\nThe RDN of this MO is ReportConfigA5SoftLock=1.";
      yexte:is-system-created;
      erienmyext:enm-type MOC;
      uses moc-ReportConfigA5SoftLock-keys;
      container attributes {
        description "Attributes for ReportConfigA5SoftLock";
        uses moc-ReportConfigA5SoftLock;
      } // end 'container attributes'
    } // end 'list ReportConfigA5SoftLock'
  }
  augment /erienmnrmcomtop:ManagedElement/erienmnrmlrat:ENodeBFunction/erienmnrmlrat:EUtranCellTDD/erienmnrmlrat:UeMeasControl {
    list ReportConfigA5SoftLock {
      key id;
      max-elements 1;
      description "Contains the Report Configuration settings for the A5 event measurements initiated for Soft-Lock of Cell.\n\nThe RDN of this MO is ReportConfigA5SoftLock=1.";
      yexte:is-system-created;
      erienmyext:enm-type MOC;
      uses moc-ReportConfigA5SoftLock-keys;
      container attributes {
        description "Attributes for ReportConfigA5SoftLock";
        uses moc-ReportConfigA5SoftLock;
      } // end 'container attributes'
    } // end 'list ReportConfigA5SoftLock'
  }
  augment /erienmnrmcomtop:ManagedElement/erienmnrmlrat:ENodeBFunction/erienmnrmlrat:EUtranCellFDD/erienmnrmlrat:UeMeasControl {
    list ReportConfigB1Geran {
      key id;
      max-elements 1;
      description "This managed object contains report configuration settings for the B1 event for GERAN measurements. The B1 event is used to detect when a GERAN cell becomes better than threshold.\n\nThe RDN of this MO is ReportConfigB1Geran=1.";
      yexte:is-system-created;
      erienmyext:enm-type MOC;
      uses moc-ReportConfigB1Geran-keys;
      container attributes {
        description "Attributes for ReportConfigB1Geran";
        uses moc-ReportConfigB1Geran;
      } // end 'container attributes'
    } // end 'list ReportConfigB1Geran'
  }
  augment /erienmnrmcomtop:ManagedElement/erienmnrmlrat:ENodeBFunction/erienmnrmlrat:EUtranCellTDD/erienmnrmlrat:UeMeasControl {
    list ReportConfigB1Geran {
      key id;
      max-elements 1;
      description "This managed object contains report configuration settings for the B1 event for GERAN measurements. The B1 event is used to detect when a GERAN cell becomes better than threshold.\n\nThe RDN of this MO is ReportConfigB1Geran=1.";
      yexte:is-system-created;
      erienmyext:enm-type MOC;
      uses moc-ReportConfigB1Geran-keys;
      container attributes {
        description "Attributes for ReportConfigB1Geran";
        uses moc-ReportConfigB1Geran;
      } // end 'container attributes'
    } // end 'list ReportConfigB1Geran'
  }
  augment /erienmnrmcomtop:ManagedElement/erienmnrmlrat:ENodeBFunction/erienmnrmlrat:EUtranCellFDD/erienmnrmlrat:GeranFreqGroupRelation {
    list GeranCellRelation {
      key id;
      max-elements 64;
      description "This Managed Object represents a mobility relation between an EUtranCellFDD or an EUtranCellTDD and a GeranCell. It contains parameters that are specific for this relation";
      erienmyext:enm-type MOC;
      uses moc-GeranCellRelation-keys;
      container attributes {
        description "Attributes for GeranCellRelation";
        uses moc-GeranCellRelation;
      } // end 'container attributes'
    } // end 'list GeranCellRelation'
  }
  augment /erienmnrmcomtop:ManagedElement/erienmnrmlrat:ENodeBFunction/erienmnrmlrat:EUtranCellTDD/erienmnrmlrat:GeranFreqGroupRelation {
    list GeranCellRelation {
      key id;
      max-elements 64;
      description "This Managed Object represents a mobility relation between an EUtranCellFDD or an EUtranCellTDD and a GeranCell. It contains parameters that are specific for this relation";
      erienmyext:enm-type MOC;
      uses moc-GeranCellRelation-keys;
      container attributes {
        description "Attributes for GeranCellRelation";
        uses moc-GeranCellRelation;
      } // end 'container attributes'
    } // end 'list GeranCellRelation'
  }
  augment /erienmnrmcomtop:ManagedElement/erienmnrmlrat:ENodeBFunction {
    list PmFlexCounterFilter {
      key id;
      max-elements 24;
      description "Filter parameters applied to the flexible counters. Same filter combinations between instances of this class are not allowed.";
      erienmyext:enm-type MOC;
      uses moc-PmFlexCounterFilter-keys;
      container attributes {
        description "Attributes for PmFlexCounterFilter";
        uses moc-PmFlexCounterFilter;
      } // end 'container attributes'
    } // end 'list PmFlexCounterFilter'
  }
  augment /erienmnrmcomtop:ManagedElement/erienmnrmlrat:ENodeBFunction/erienmnrmlrat:EUtranCellFDD/erienmnrmlrat:UeMeasControl {
    list ReportConfigB2Cdma2000 {
      key id;
      max-elements 1;
      description "This managed object contains report configuration settings for the B2 event for CDMA2000 measurements. The B2 event is used to detect when a CDMA2000 cell becomes better than threshold2, and serving cell becomes worse than threshold1. The actual threshold values used can be adjusted by frequency relation related offsets if the feature Multi-Layer Service-Triggered Mobility (MLSTM) is enabled.\n\nThe RDN of this MO is ReportConfigB2Cdma2000=1.";
      yexte:is-system-created;
      erienmyext:enm-type MOC;
      uses moc-ReportConfigB2Cdma2000-keys;
      container attributes {
        description "Attributes for ReportConfigB2Cdma2000";
        uses moc-ReportConfigB2Cdma2000;
      } // end 'container attributes'
    } // end 'list ReportConfigB2Cdma2000'
  }
  augment /erienmnrmcomtop:ManagedElement/erienmnrmlrat:ENodeBFunction/erienmnrmlrat:EUtranCellTDD/erienmnrmlrat:UeMeasControl {
    list ReportConfigB2Cdma2000 {
      key id;
      max-elements 1;
      description "This managed object contains report configuration settings for the B2 event for CDMA2000 measurements. The B2 event is used to detect when a CDMA2000 cell becomes better than threshold2, and serving cell becomes worse than threshold1. The actual threshold values used can be adjusted by frequency relation related offsets if the feature Multi-Layer Service-Triggered Mobility (MLSTM) is enabled.\n\nThe RDN of this MO is ReportConfigB2Cdma2000=1.";
      yexte:is-system-created;
      erienmyext:enm-type MOC;
      uses moc-ReportConfigB2Cdma2000-keys;
      container attributes {
        description "Attributes for ReportConfigB2Cdma2000";
        uses moc-ReportConfigB2Cdma2000;
      } // end 'container attributes'
    } // end 'list ReportConfigB2Cdma2000'
  }
  augment /erienmnrmcomtop:ManagedElement/erienmnrmlrat:ENodeBFunction {
    list PlmnAbConfProfile {
      key id;
      max-elements 6;
      description "Access Barring configuration for PLMN.";
      erienmyext:enm-type MOC;
      uses moc-PlmnAbConfProfile-keys;
      container attributes {
        description "Attributes for PlmnAbConfProfile";
        uses moc-PlmnAbConfProfile;
      } // end 'container attributes'
    } // end 'list PlmnAbConfProfile'
  }
  augment /erienmnrmcomtop:ManagedElement/erienmnrmlrat:ENodeBFunction/erienmnrmlrat:EUtranCellFDD/erienmnrmlrat:UtranTDDFreqRelation {
    list UtranCellRelation {
      key id;
      max-elements 64;
      description "This Managed Object represents a mobility relation between an EUtranCellFDD or an EUtranCellTDD and an UtranCell. It contains parameters that are specific for this relation";
      erienmyext:enm-type MOC;
      uses moc-UtranCellRelation-keys;
      container attributes {
        description "Attributes for UtranCellRelation";
        uses moc-UtranCellRelation;
      } // end 'container attributes'
    } // end 'list UtranCellRelation'
  }
  augment /erienmnrmcomtop:ManagedElement/erienmnrmlrat:ENodeBFunction/erienmnrmlrat:EUtranCellTDD/erienmnrmlrat:UtranTDDFreqRelation {
    list UtranCellRelation {
      key id;
      max-elements 64;
      description "This Managed Object represents a mobility relation between an EUtranCellFDD or an EUtranCellTDD and an UtranCell. It contains parameters that are specific for this relation";
      erienmyext:enm-type MOC;
      uses moc-UtranCellRelation-keys;
      container attributes {
        description "Attributes for UtranCellRelation";
        uses moc-UtranCellRelation;
      } // end 'container attributes'
    } // end 'list UtranCellRelation'
  }
  augment /erienmnrmcomtop:ManagedElement/erienmnrmlrat:ENodeBFunction/erienmnrmlrat:EUtranCellFDD/erienmnrmlrat:UtranFreqRelation {
    list UtranCellRelation {
      key id;
      max-elements 64;
      description "This Managed Object represents a mobility relation between an EUtranCellFDD or an EUtranCellTDD and an UtranCell. It contains parameters that are specific for this relation";
      erienmyext:enm-type MOC;
      uses moc-UtranCellRelation-keys;
      container attributes {
        description "Attributes for UtranCellRelation";
        uses moc-UtranCellRelation;
      } // end 'container attributes'
    } // end 'list UtranCellRelation'
  }
  augment /erienmnrmcomtop:ManagedElement/erienmnrmlrat:ENodeBFunction/erienmnrmlrat:EUtranCellTDD/erienmnrmlrat:UtranFreqRelation {
    list UtranCellRelation {
      key id;
      max-elements 64;
      description "This Managed Object represents a mobility relation between an EUtranCellFDD or an EUtranCellTDD and an UtranCell. It contains parameters that are specific for this relation";
      erienmyext:enm-type MOC;
      uses moc-UtranCellRelation-keys;
      container attributes {
        description "Attributes for UtranCellRelation";
        uses moc-UtranCellRelation;
      } // end 'container attributes'
    } // end 'list UtranCellRelation'
  }
  augment /erienmnrmcomtop:ManagedElement/erienmnrmlrat:ENodeBFunction/erienmnrmlrat:EUtranCellFDD/erienmnrmlrat:UeMeasControl {
    list ReportConfigElcA1A2 {
      key id;
      max-elements 1;
      description "Contains the report configuration settings for A1/A2 measurements initiated by Ericsson Lean Carrier.\n\nThe RDN of this MO is ReportConfigElcA1A2=1.";
      yexte:is-system-created;
      erienmyext:enm-type MOC;
      uses moc-ReportConfigElcA1A2-keys;
      container attributes {
        description "Attributes for ReportConfigElcA1A2";
        uses moc-ReportConfigElcA1A2;
      } // end 'container attributes'
    } // end 'list ReportConfigElcA1A2'
  }
  augment /erienmnrmcomtop:ManagedElement/erienmnrmlrat:ENodeBFunction/erienmnrmlrat:EUtranCellTDD/erienmnrmlrat:UeMeasControl {
    list ReportConfigElcA1A2 {
      key id;
      max-elements 1;
      description "Contains the report configuration settings for A1/A2 measurements initiated by Ericsson Lean Carrier.\n\nThe RDN of this MO is ReportConfigElcA1A2=1.";
      yexte:is-system-created;
      erienmyext:enm-type MOC;
      uses moc-ReportConfigElcA1A2-keys;
      container attributes {
        description "Attributes for ReportConfigElcA1A2";
        uses moc-ReportConfigElcA1A2;
      } // end 'container attributes'
    } // end 'list ReportConfigElcA1A2'
  }
  augment /erienmnrmcomtop:ManagedElement/erienmnrmlrat:ENodeBFunction/erienmnrmlrat:RadioBearerTable {
    list MACConfiguration {
      key id;
      max-elements 1;
      description "MAC configuration.\n\nThe RDN of this MO is MACConfiguration=1.";
      yexte:is-system-created;
      erienmyext:enm-type MOC;
      uses moc-MACConfiguration-keys;
      container attributes {
        description "Attributes for MACConfiguration";
        uses moc-MACConfiguration;
      } // end 'container attributes'
    } // end 'list MACConfiguration'
  }
  augment /erienmnrmcomtop:ManagedElement/erienmnrmlrat:ENodeBFunction {
    list Band46UnlicensedProfile {
      key id;
      max-elements 1;
      description "Contains information about the regulatory requirements for each frequency in Band 46.";
      status deprecated {
        yexte:status-information "Since 17.Q2. Has no functional behavior. Planned to be removed.";
      }
      erienmyext:enm-type MOC;
      uses moc-Band46UnlicensedProfile-keys;
      container attributes {
        description "Attributes for Band46UnlicensedProfile";
        uses moc-Band46UnlicensedProfile;
      } // end 'container attributes'
    } // end 'list Band46UnlicensedProfile'
  }
  augment /erienmnrmcomtop:ManagedElement/erienmnrmlrat:ENodeBFunction/erienmnrmlrat:EUtranCellFDD/erienmnrmlrat:UeMeasControl {
    list ReportConfigA5DlComp {
      key id;
      max-elements 1;
      description "This MO contains report configuration settings for the A5 event measurements that assist Downlink Coordinated Multi-Point. The A5 event is used to detect when serving cell becomes worse than threshold1, and neighbor cell becomes better than threshold2.\n\nThe RDN of this MO is ReportConfigA5DlComp=1.";
      yexte:is-system-created;
      erienmyext:enm-type MOC;
      uses moc-ReportConfigA5DlComp-keys;
    } // end 'list ReportConfigA5DlComp'
  }
  augment /erienmnrmcomtop:ManagedElement/erienmnrmlrat:ENodeBFunction/erienmnrmlrat:EUtranCellTDD/erienmnrmlrat:UeMeasControl {
    list ReportConfigA5DlComp {
      key id;
      max-elements 1;
      description "This MO contains report configuration settings for the A5 event measurements that assist Downlink Coordinated Multi-Point. The A5 event is used to detect when serving cell becomes worse than threshold1, and neighbor cell becomes better than threshold2.\n\nThe RDN of this MO is ReportConfigA5DlComp=1.";
      yexte:is-system-created;
      erienmyext:enm-type MOC;
      uses moc-ReportConfigA5DlComp-keys;
    } // end 'list ReportConfigA5DlComp'
  }
  augment /erienmnrmcomtop:ManagedElement/erienmnrmlrat:ENodeBFunction/erienmnrmlrat:ImeisvTable {
    list ImeisvProfile {
      key id;
      max-elements 150;
      description "Contains UE IMEISV configuration used for feature Differentiated UE Handling. Instances of this class are created on demand by the operator. The instances can be created and configured independent of the serviceState for DifferentiatedUeHandling. But the IMEISV profiles cannot be used unless the service state is OPERABLE.\n\n";
      erienmyext:enm-type MOC;
      uses moc-ImeisvProfile-keys;
      container attributes {
        description "Attributes for ImeisvProfile";
        uses moc-ImeisvProfile;
      } // end 'container attributes'
    } // end 'list ImeisvProfile'
  }
  augment /erienmnrmcomtop:ManagedElement/erienmnrmlrat:ENodeBFunction/erienmnrmlrat:FlexibleQoSFunction/erienmnrmlrat:FlexibleQoSGroup {
    list FlexibleQoSGroupMember {
      key id;
      max-elements 6;
      description "Specifies a mapping configuration to decide what SciProfile should be assigned to a bearer.";
      erienmyext:enm-type MOC;
      uses moc-FlexibleQoSGroupMember-keys;
      container attributes {
        description "Attributes for FlexibleQoSGroupMember";
        uses moc-FlexibleQoSGroupMember;
      } // end 'container attributes'
    } // end 'list FlexibleQoSGroupMember'
  }
  augment /erienmnrmcomtop:ManagedElement/erienmnrmlrat:ENodeBFunction {
    list CellSleepNodeFunction {
      key id;
      max-elements 1;
      description "Contains parameters for Cell Sleep Mode support in the node that are common for all cells.\nThe RDN of this MO is CellSleepNodeFunction=1.";
      yexte:is-system-created;
      erienmyext:enm-type MOC;
      uses moc-CellSleepNodeFunction-keys;
      container attributes {
        description "Attributes for CellSleepNodeFunction";
        uses moc-CellSleepNodeFunction;
      } // end 'container attributes'
    } // end 'list CellSleepNodeFunction'
  }
  augment /erienmnrmcomtop:ManagedElement/erienmnrmlrat:ENodeBFunction/erienmnrmlrat:GUtraNetwork/erienmnrmlrat:ExternalGNodeBFunction {
    list TermPointToGNB {
      key id;
      max-elements 1;
      description "Models the local eNB termination point of an X2 link between the gNB and an eNB.";
      erienmyext:enm-type MOC;
      uses moc-TermPointToGNB-keys;
      container attributes {
        description "Attributes for TermPointToGNB";
        uses moc-TermPointToGNB;
      } // end 'container attributes'
    } // end 'list TermPointToGNB'
  }
  augment /erienmnrmcomtop:ManagedElement/erienmnrmlrat:ENodeBFunction/erienmnrmlrat:EUtraNetwork {
    list EUtranFrequency {
      key id;
      max-elements 24;
      description "This Managed Object contains information of a specific EUtran frequency.\nMO is created manually, and when executing action changeFrequency in MO ExternalEUtranCellFDD/TDD.\nMO is also created automatically at X2 link setup with neighbor eNB.\n\nThe RDNs of these MOs are EUtranFrequency=<number>, for example EUtranFrequency=2586.\nRDN must match attribute arfcnValueEUtranDl. If it does not match, automatic creation of MO can fail, leading to X2 link setup failure with neighbor eNB.";
      erienmyext:enm-type MOC;
      uses moc-EUtranFrequency-keys;
      container attributes {
        description "Attributes for EUtranFrequency";
        uses moc-EUtranFrequency;
      } // end 'container attributes'
    } // end 'list EUtranFrequency'
  }
  augment /erienmnrmcomtop:ManagedElement/erienmnrmlrat:ENodeBFunction/erienmnrmlrat:PtmFunction/erienmnrmlrat:PtmCellProfile {
    list PtmAtoConfig {
      key id;
      max-elements 1;
      description "Contains PTM specific parameters affecting Admission Triggered Offload feature.\n\nThe RDN of this MO is PtmAtoConfig=1.";
      yexte:is-system-created;
      erienmyext:enm-type MOC;
      uses moc-PtmAtoConfig-keys;
      container attributes {
        description "Attributes for PtmAtoConfig";
        uses moc-PtmAtoConfig;
      } // end 'container attributes'
    } // end 'list PtmAtoConfig'
  }
  augment /erienmnrmcomtop:ManagedElement/erienmnrmlrat:ENodeBFunction {
    list RadioBearerTable {
      key id;
      max-elements 1;
      description "Contains Radio Bearer configurations.\n\nThe RDN of this MO is RadioBearerTable=default.";
      yexte:is-system-created;
      erienmyext:enm-type MOC;
      uses moc-RadioBearerTable-keys;
    } // end 'list RadioBearerTable'
  }
  augment /erienmnrmcomtop:ManagedElement/erienmnrmlrat:ENodeBFunction/erienmnrmlrat:EUtranCellFDD/erienmnrmlrat:UeMeasControl {
    list ReportConfigInterEnbUlComp {
      key id;
      max-elements 1;
      description "Contains the Report Configuration settings for UE measurements initiated for Inter-eNB UL CoMP.\n\nThe RDN of this MO is ReportConfigInterEnbUlComp=1.";
      yexte:is-system-created;
      erienmyext:enm-type MOC;
      uses moc-ReportConfigInterEnbUlComp-keys;
      container attributes {
        description "Attributes for ReportConfigInterEnbUlComp";
        uses moc-ReportConfigInterEnbUlComp;
      } // end 'container attributes'
    } // end 'list ReportConfigInterEnbUlComp'
  }
  augment /erienmnrmcomtop:ManagedElement/erienmnrmlrat:ENodeBFunction/erienmnrmlrat:EUtranCellTDD/erienmnrmlrat:UeMeasControl {
    list ReportConfigInterEnbUlComp {
      key id;
      max-elements 1;
      description "Contains the Report Configuration settings for UE measurements initiated for Inter-eNB UL CoMP.\n\nThe RDN of this MO is ReportConfigInterEnbUlComp=1.";
      yexte:is-system-created;
      erienmyext:enm-type MOC;
      uses moc-ReportConfigInterEnbUlComp-keys;
      container attributes {
        description "Attributes for ReportConfigInterEnbUlComp";
        uses moc-ReportConfigInterEnbUlComp;
      } // end 'container attributes'
    } // end 'list ReportConfigInterEnbUlComp'
  }
  augment /erienmnrmcomtop:ManagedElement/erienmnrmlrat:ENodeBFunction/erienmnrmlrat:Cdma2000Network/erienmnrmlrat:Cdma2000FreqBand/erienmnrmlrat:Cdma2000Freq {
    list ExternalCdma2000Cell {
      key id;
      max-elements 392;
      description "The MO represents a CDMA2000 HRPD cell.";
      erienmyext:enm-type MOC;
      uses moc-ExternalCdma2000Cell-keys;
      container attributes {
        description "Attributes for ExternalCdma2000Cell";
        uses moc-ExternalCdma2000Cell;
      } // end 'container attributes'
    } // end 'list ExternalCdma2000Cell'
  }
  augment /erienmnrmcomtop:ManagedElement/erienmnrmlrat:ENodeBFunction/erienmnrmlrat:AnrFunction {
    list AnrFunctionEUtran {
      key id;
      max-elements 1;
      description "Parameters and constraints for LTE ANR functions.\n\nThe RDN of this MO is AnrFunctionEUtran=1.";
      yexte:is-system-created;
      erienmyext:enm-type MOC;
      uses moc-AnrFunctionEUtran-keys;
      container attributes {
        description "Attributes for AnrFunctionEUtran";
        uses moc-AnrFunctionEUtran;
      } // end 'container attributes'
    } // end 'list AnrFunctionEUtran'
  }
  augment /erienmnrmcomtop:ManagedElement/erienmnrmlrat:ENodeBFunction {
    list TermPointToSGW {
      key id;
      max-elements 64;
      description "Models SGW termination point of S1 link between RBS and SGW node.\n\nThe RDNs of these MOs are TermPointToSGW=1 to TermPointToSGW=64.";
      yexte:is-system-created;
      erienmyext:enm-type MOC;
      uses moc-TermPointToSGW-keys;
      container attributes {
        description "Attributes for TermPointToSGW";
        uses moc-TermPointToSGW;
      } // end 'container attributes'
    } // end 'list TermPointToSGW'
  }
  augment /erienmnrmcomtop:ManagedElement/erienmnrmlrat:ENodeBFunction/erienmnrmlrat:EUtranCellFDD {
    list UtranTDDFreqRelation {
      key id;
      max-elements 16;
      description "This Managed Object represents a UTRAN TDD mobility relation between a EUtranCellFDD or EUtranCellTDD and a UtranFrequency. It contains parameters that are specific for this relation.\n\nDeleting this MO while the parent EUtranCellFDD/EUtranCellTDD has operationalState set to ENABLED is not recommended as it may affect traffic.";
      erienmyext:enm-type MOC;
      uses moc-UtranTDDFreqRelation-keys;
      container attributes {
        description "Attributes for UtranTDDFreqRelation";
        uses moc-UtranTDDFreqRelation;
      } // end 'container attributes'
    } // end 'list UtranTDDFreqRelation'
  }
  augment /erienmnrmcomtop:ManagedElement/erienmnrmlrat:ENodeBFunction/erienmnrmlrat:EUtranCellTDD {
    list UtranTDDFreqRelation {
      key id;
      max-elements 16;
      description "This Managed Object represents a UTRAN TDD mobility relation between a EUtranCellFDD or EUtranCellTDD and a UtranFrequency. It contains parameters that are specific for this relation.\n\nDeleting this MO while the parent EUtranCellFDD/EUtranCellTDD has operationalState set to ENABLED is not recommended as it may affect traffic.";
      erienmyext:enm-type MOC;
      uses moc-UtranTDDFreqRelation-keys;
      container attributes {
        description "Attributes for UtranTDDFreqRelation";
        uses moc-UtranTDDFreqRelation;
      } // end 'container attributes'
    } // end 'list UtranTDDFreqRelation'
  }
  augment /erienmnrmcomtop:ManagedElement/erienmnrmlrat:ENodeBFunction/erienmnrmlrat:PtmFunction/erienmnrmlrat:PtmCellProfile {
    list PtmStmConfig {
      key id;
      max-elements 1;
      description "Contains PTM specific parameters affecting Subscriber Triggered Mobility feature.\n\nThe RDN of this MO is PtmStmConfig=1.";
      yexte:is-system-created;
      erienmyext:enm-type MOC;
      uses moc-PtmStmConfig-keys;
      container attributes {
        description "Attributes for PtmStmConfig";
        uses moc-PtmStmConfig;
      } // end 'container attributes'
    } // end 'list PtmStmConfig'
  }
  augment /erienmnrmcomtop:ManagedElement/erienmnrmlrat:ENodeBFunction/erienmnrmlrat:EUtranCellFDD/erienmnrmlrat:UeMeasControl {
    list ReportConfigB2Geran {
      key id;
      max-elements 1;
      description "This managed object contains report configuration settings for the B2 event for GERAN measurements. The B2 event is used to detect when a GERAN cell becomes better than threshold2, and serving cell becomes worse than threshold1. The actual threshold values used can be adjusted by frequency relation related offsets if the feature Multi-Layer Service-Triggered Mobility (MLSTM) is enabled.\n\nThe RDN of this MO is ReportConfigB2Geran=1.";
      yexte:is-system-created;
      erienmyext:enm-type MOC;
      uses moc-ReportConfigB2Geran-keys;
      container attributes {
        description "Attributes for ReportConfigB2Geran";
        uses moc-ReportConfigB2Geran;
      } // end 'container attributes'
    } // end 'list ReportConfigB2Geran'
  }
  augment /erienmnrmcomtop:ManagedElement/erienmnrmlrat:ENodeBFunction/erienmnrmlrat:EUtranCellTDD/erienmnrmlrat:UeMeasControl {
    list ReportConfigB2Geran {
      key id;
      max-elements 1;
      description "This managed object contains report configuration settings for the B2 event for GERAN measurements. The B2 event is used to detect when a GERAN cell becomes better than threshold2, and serving cell becomes worse than threshold1. The actual threshold values used can be adjusted by frequency relation related offsets if the feature Multi-Layer Service-Triggered Mobility (MLSTM) is enabled.\n\nThe RDN of this MO is ReportConfigB2Geran=1.";
      yexte:is-system-created;
      erienmyext:enm-type MOC;
      uses moc-ReportConfigB2Geran-keys;
      container attributes {
        description "Attributes for ReportConfigB2Geran";
        uses moc-ReportConfigB2Geran;
      } // end 'container attributes'
    } // end 'list ReportConfigB2Geran'
  }
  augment /erienmnrmcomtop:ManagedElement/erienmnrmlrat:ENodeBFunction/erienmnrmlrat:EUtraNetwork/erienmnrmlrat:ExternalENodeBFunction {
    list EranInterMeLink {
      key id;
      max-elements 4;
      description "Models a eRAN link between a ME and a neighboring ME.\n\nThe RDNs of these MOs are EranInterMeLink=1 to EranInterMeLink=4.";
      yexte:is-system-created;
      erienmyext:enm-type MOC;
      uses moc-EranInterMeLink-keys;
      container attributes {
        description "Attributes for EranInterMeLink";
        uses moc-EranInterMeLink;
      } // end 'container attributes'
    } // end 'list EranInterMeLink'
  }
  augment /erienmnrmcomtop:ManagedElement/erienmnrmlrat:ENodeBFunction/erienmnrmlrat:EUtranCellFDD {
    list EUtranFreqRelationUnlicensed {
      key id;
      max-elements 1;
      description "MO represents mobility relation between EUtranCellFDD (or-TDD) and EUtranFrequencyUnlicensed. Contains parameters specific for this relation.\nOne instance of this MO must refer to Band46UnlicensedProfile MO.";
      erienmyext:enm-type MOC;
      uses moc-EUtranFreqRelationUnlicensed-keys;
      container attributes {
        description "Attributes for EUtranFreqRelationUnlicensed";
        uses moc-EUtranFreqRelationUnlicensed;
      } // end 'container attributes'
    } // end 'list EUtranFreqRelationUnlicensed'
  }
  augment /erienmnrmcomtop:ManagedElement/erienmnrmlrat:ENodeBFunction/erienmnrmlrat:EUtranCellTDD {
    list EUtranFreqRelationUnlicensed {
      key id;
      max-elements 1;
      description "MO represents mobility relation between EUtranCellFDD (or-TDD) and EUtranFrequencyUnlicensed. Contains parameters specific for this relation.\nOne instance of this MO must refer to Band46UnlicensedProfile MO.";
      erienmyext:enm-type MOC;
      uses moc-EUtranFreqRelationUnlicensed-keys;
      container attributes {
        description "Attributes for EUtranFreqRelationUnlicensed";
        uses moc-EUtranFreqRelationUnlicensed;
      } // end 'container attributes'
    } // end 'list EUtranFreqRelationUnlicensed'
  }
  augment /erienmnrmcomtop:ManagedElement/erienmnrmlrat:ENodeBFunction {
    list GeraNetwork {
      key id;
      max-elements 1;
      description "This managed object represents a Gera network.\n";
      erienmyext:enm-type MOC;
      uses moc-GeraNetwork-keys;
      container attributes {
        description "Attributes for GeraNetwork";
        uses moc-GeraNetwork;
      } // end 'container attributes'
    } // end 'list GeraNetwork'
  }
  augment /erienmnrmcomtop:ManagedElement/erienmnrmlrat:ENodeBFunction/erienmnrmlrat:EUtranCellFDD/erienmnrmlrat:UeMeasControl {
    list ReportConfigA1Sec {
      key id;
      max-elements 1;
      description "This managed object contains report configuration settings for the secondary A1 event measurements. The A1 event is used to the detect traffic-related Bad Coverage Cease condition.\nPrimary and secondary reporting configuration MOs refer to the option to use different settings for two simultaneous measurements for the event A1.\n\nThe RDN of this MO is ReportConfigA1Sec=1.";
      yexte:is-system-created;
      erienmyext:enm-type MOC;
      uses moc-ReportConfigA1Sec-keys;
      container attributes {
        description "Attributes for ReportConfigA1Sec";
        uses moc-ReportConfigA1Sec;
      } // end 'container attributes'
    } // end 'list ReportConfigA1Sec'
  }
  augment /erienmnrmcomtop:ManagedElement/erienmnrmlrat:ENodeBFunction/erienmnrmlrat:EUtranCellTDD/erienmnrmlrat:UeMeasControl {
    list ReportConfigA1Sec {
      key id;
      max-elements 1;
      description "This managed object contains report configuration settings for the secondary A1 event measurements. The A1 event is used to the detect traffic-related Bad Coverage Cease condition.\nPrimary and secondary reporting configuration MOs refer to the option to use different settings for two simultaneous measurements for the event A1.\n\nThe RDN of this MO is ReportConfigA1Sec=1.";
      yexte:is-system-created;
      erienmyext:enm-type MOC;
      uses moc-ReportConfigA1Sec-keys;
      container attributes {
        description "Attributes for ReportConfigA1Sec";
        uses moc-ReportConfigA1Sec;
      } // end 'container attributes'
    } // end 'list ReportConfigA1Sec'
  }
  augment /erienmnrmcomtop:ManagedElement/erienmnrmlrat:ENodeBFunction/erienmnrmlrat:EUtranCellFDD {
    list CellPortion {
      key id;
      max-elements 256;
      description "This MO represents the area within a Cell, which can be used for feature, e.g. UE Positioning.";
      erienmyext:enm-type MOC;
      uses moc-CellPortion-keys;
      container attributes {
        description "Attributes for CellPortion";
        uses moc-CellPortion;
      } // end 'container attributes'
    } // end 'list CellPortion'
  }
  augment /erienmnrmcomtop:ManagedElement/erienmnrmlrat:ENodeBFunction/erienmnrmlrat:EUtranCellFDD/erienmnrmlrat:UeMeasControl {
    list ReportConfigA1A2Br {
      key id;
      max-elements 1;
      description "Contains report configuration settings for A1/A2 measurements for CAT-M UE.\n\nThe RDN of this MO is ReportConfigA1A2Br=1.";
      yexte:is-system-created;
      erienmyext:enm-type MOC;
      uses moc-ReportConfigA1A2Br-keys;
      container attributes {
        description "Attributes for ReportConfigA1A2Br";
        uses moc-ReportConfigA1A2Br;
      } // end 'container attributes'
    } // end 'list ReportConfigA1A2Br'
  }
  augment /erienmnrmcomtop:ManagedElement/erienmnrmlrat:ENodeBFunction/erienmnrmlrat:EUtranCellTDD/erienmnrmlrat:UeMeasControl {
    list ReportConfigA1A2Br {
      key id;
      max-elements 1;
      description "Contains report configuration settings for A1/A2 measurements for CAT-M UE.\n\nThe RDN of this MO is ReportConfigA1A2Br=1.";
      yexte:is-system-created;
      erienmyext:enm-type MOC;
      uses moc-ReportConfigA1A2Br-keys;
      container attributes {
        description "Attributes for ReportConfigA1A2Br";
        uses moc-ReportConfigA1A2Br;
      } // end 'container attributes'
    } // end 'list ReportConfigA1A2Br'
  }
  augment /erienmnrmcomtop:ManagedElement/erienmnrmlrat:ENodeBFunction/erienmnrmlrat:Mbms/erienmnrmlrat:MbsfnArea {
    list MbsfnAreaCellRelation {
      key id;
      max-elements 24;
      description "This managed object represents the relationship between a MBSFN Area and a EUTRAN cell.";
      erienmyext:enm-type MOC;
      uses moc-MbsfnAreaCellRelation-keys;
      container attributes {
        description "Attributes for MbsfnAreaCellRelation";
        uses moc-MbsfnAreaCellRelation;
      } // end 'container attributes'
    } // end 'list MbsfnAreaCellRelation'
  }
  augment /erienmnrmcomtop:ManagedElement/erienmnrmlrat:ENodeBFunction/erienmnrmlrat:EUtranCellFDD/erienmnrmlrat:UeMeasControl {
    list ReportConfigSCellA6 {
      key id;
      max-elements 1;
      description "This managed object contains the report configuration settings for A6 measurements on the frequency of any serving SCell when this cell is used as PCell.\n\nThe RDN of this MO is ReportConfigSCellA6=1.";
      yexte:is-system-created;
      erienmyext:enm-type MOC;
      uses moc-ReportConfigSCellA6-keys;
      container attributes {
        description "Attributes for ReportConfigSCellA6";
        uses moc-ReportConfigSCellA6;
      } // end 'container attributes'
    } // end 'list ReportConfigSCellA6'
  }
  augment /erienmnrmcomtop:ManagedElement/erienmnrmlrat:ENodeBFunction/erienmnrmlrat:EUtranCellTDD/erienmnrmlrat:UeMeasControl {
    list ReportConfigSCellA6 {
      key id;
      max-elements 1;
      description "This managed object contains the report configuration settings for A6 measurements on the frequency of any serving SCell when this cell is used as PCell.\n\nThe RDN of this MO is ReportConfigSCellA6=1.";
      yexte:is-system-created;
      erienmyext:enm-type MOC;
      uses moc-ReportConfigSCellA6-keys;
      container attributes {
        description "Attributes for ReportConfigSCellA6";
        uses moc-ReportConfigSCellA6;
      } // end 'container attributes'
    } // end 'list ReportConfigSCellA6'
  }
  augment /erienmnrmcomtop:ManagedElement/erienmnrmlrat:ENodeBFunction {
    list SubscriberProfileID {
      key id;
      max-elements 1;
      description "Parent for all SPID related MOCs";
      erienmyext:enm-type MOC;
      uses moc-SubscriberProfileID-keys;
      container attributes {
        description "Attributes for SubscriberProfileID";
        uses moc-SubscriberProfileID;
      } // end 'container attributes'
    } // end 'list SubscriberProfileID'
  }
  augment /erienmnrmcomtop:ManagedElement/erienmnrmlrat:ENodeBFunction/erienmnrmlrat:EUtranCellFDD/erienmnrmlrat:UeMeasControl {
    list ReportConfigSCellA4 {
      key id;
      max-elements 1;
      description "This managed object contains the report configuration settings for A4 measurements on the frequency of any non-serving SCell candidate when this cell is used as PCell.\nNote: This MO class is valid only for FDD cells.\n\nThe RDN of this MO is ReportConfigSCellA4=1.";
      yexte:is-system-created;
      erienmyext:enm-type MOC;
      uses moc-ReportConfigSCellA4-keys;
      container attributes {
        description "Attributes for ReportConfigSCellA4";
        uses moc-ReportConfigSCellA4;
      } // end 'container attributes'
    } // end 'list ReportConfigSCellA4'
  }
  augment /erienmnrmcomtop:ManagedElement/erienmnrmlrat:ENodeBFunction/erienmnrmlrat:EUtranCellTDD/erienmnrmlrat:UeMeasControl {
    list ReportConfigSCellA4 {
      key id;
      max-elements 1;
      description "This managed object contains the report configuration settings for A4 measurements on the frequency of any non-serving SCell candidate when this cell is used as PCell.\nNote: This MO class is valid only for FDD cells.\n\nThe RDN of this MO is ReportConfigSCellA4=1.";
      yexte:is-system-created;
      erienmyext:enm-type MOC;
      uses moc-ReportConfigSCellA4-keys;
      container attributes {
        description "Attributes for ReportConfigSCellA4";
        uses moc-ReportConfigSCellA4;
      } // end 'container attributes'
    } // end 'list ReportConfigSCellA4'
  }
  augment /erienmnrmcomtop:ManagedElement/erienmnrmlrat:ENodeBFunction/erienmnrmlrat:PtmFunction {
    list PtmCellProfile {
      key id;
      max-elements 4;
      description "Parameters that can be used to define a PTM Cell Profile, describing per cell configuration of Preferential Traffic Management. PtmCellProfile can be referenced from multiple cells on the eNodeB by using EUtranCellFDD.PtmCellProfileRef or EUtranCellTDD.PtmCellProfileRef.";
      erienmyext:enm-type MOC;
      uses moc-PtmCellProfile-keys;
      container attributes {
        description "Attributes for PtmCellProfile";
        uses moc-PtmCellProfile;
      } // end 'container attributes'
    } // end 'list PtmCellProfile'
  }
  augment /erienmnrmcomtop:ManagedElement/erienmnrmlrat:ENodeBFunction/erienmnrmlrat:UtraNetwork/erienmnrmlrat:UtranFrequency {
    list ExternalUtranCellTDD {
      key id;
      max-elements 392;
      description "This Managed Object contains a UTRAN cell for TDD (Time Division Duplex).";
      erienmyext:enm-type MOC;
      uses moc-ExternalUtranCellTDD-keys;
      container attributes {
        description "Attributes for ExternalUtranCellTDD";
        uses moc-ExternalUtranCellTDD;
      } // end 'container attributes'
    } // end 'list ExternalUtranCellTDD'
  }
  augment /erienmnrmcomtop:ManagedElement/erienmnrmlrat:ENodeBFunction/erienmnrmlrat:GUtraNetwork/erienmnrmlrat:ExternalGNodeBFunction {
    list ExternalGUtranCell {
      key id;
      max-elements 48;
      description "This managed object contains a GUtran cell.";
      erienmyext:enm-type MOC;
      uses moc-ExternalGUtranCell-keys;
      container attributes {
        description "Attributes for ExternalGUtranCell";
        uses moc-ExternalGUtranCell;
      } // end 'container attributes'
    } // end 'list ExternalGUtranCell'
  }
  augment /erienmnrmcomtop:ManagedElement/erienmnrmlrat:ENodeBFunction/erienmnrmlrat:ResourcePartitionGroup {
    list ResourcePartitionGroupMember {
      key id;
      max-elements 6;
      description "Specifies a resource partition configuration and the share of resources it should be granted in the cell.";
      erienmyext:enm-type MOC;
      uses moc-ResourcePartitionGroupMember-keys;
      container attributes {
        description "Attributes for ResourcePartitionGroupMember";
        uses moc-ResourcePartitionGroupMember;
      } // end 'container attributes'
    } // end 'list ResourcePartitionGroupMember'
  }
  augment /erienmnrmcomtop:ManagedElement/erienmnrmlrat:ENodeBFunction/erienmnrmlrat:EUtraNetwork/erienmnrmlrat:ExternalENodeBFunction/erienmnrmlrat:TermPointToENB {
    list TermPointToLbm {
      key id;
      max-elements 27;
      description "Designates endpoints from a baseband unit on the local eNodeB to reach a particular baseband unit on the remote eNodeB indicated by TermPointToENB.\n\nThe RDNs of these MOs are TermPointToLbm=1 to TermPointToLbm=27.";
      yexte:is-system-created;
      erienmyext:enm-type MOC;
      uses moc-TermPointToLbm-keys;
      container attributes {
        description "Attributes for TermPointToLbm";
        uses moc-TermPointToLbm;
      } // end 'container attributes'
    } // end 'list TermPointToLbm'
  }
  augment /erienmnrmcomtop:ManagedElement/erienmnrmlrat:ENodeBFunction/erienmnrmlrat:EUtranCellFDD/erienmnrmlrat:UeMeasControl/erienmnrmlrat:ReportConfigA5 {
    list ReportConfigA5Anr {
      key id;
      max-elements 1;
      description "The Automated Neighbor Relations (ANR) delta report configuration settings for the A5 event measurements as compared to mobility provided in the parent MO class.\n\nThe RDN of this MO is ReportConfigA5Anr=1.";
      yexte:is-system-created;
      erienmyext:enm-type MOC;
      uses moc-ReportConfigA5Anr-keys;
      container attributes {
        description "Attributes for ReportConfigA5Anr";
        uses moc-ReportConfigA5Anr;
      } // end 'container attributes'
    } // end 'list ReportConfigA5Anr'
  }
  augment /erienmnrmcomtop:ManagedElement/erienmnrmlrat:ENodeBFunction/erienmnrmlrat:EUtranCellTDD/erienmnrmlrat:UeMeasControl/erienmnrmlrat:ReportConfigA5 {
    list ReportConfigA5Anr {
      key id;
      max-elements 1;
      description "The Automated Neighbor Relations (ANR) delta report configuration settings for the A5 event measurements as compared to mobility provided in the parent MO class.\n\nThe RDN of this MO is ReportConfigA5Anr=1.";
      yexte:is-system-created;
      erienmyext:enm-type MOC;
      uses moc-ReportConfigA5Anr-keys;
      container attributes {
        description "Attributes for ReportConfigA5Anr";
        uses moc-ReportConfigA5Anr;
      } // end 'container attributes'
    } // end 'list ReportConfigA5Anr'
  }
  augment /erienmnrmcomtop:ManagedElement/erienmnrmlrat:ENodeBFunction {
    list UnlicensedAccessFunction {
      key id;
      max-elements 1;
      description "Definitions of LAA properties, for example LBT and DRS attributes.";
      erienmyext:enm-type MOC;
      uses moc-UnlicensedAccessFunction-keys;
      container attributes {
        description "Attributes for UnlicensedAccessFunction";
        uses moc-UnlicensedAccessFunction;
      } // end 'container attributes'
    } // end 'list UnlicensedAccessFunction'
  }
  augment /erienmnrmcomtop:ManagedElement/erienmnrmlrat:ENodeBFunction {
    list EricssonLeanCarrierFunction {
      key id;
      max-elements 1;
      description "Contains set of Ericsson Lean Carrier feature related parameters.\nAttributes take effect only if license for Ericsson Lean Carrier is present and the feature is active.\n\nThe RDN of this MO is EricssonLeanCarrierFunction=1.";
      yexte:is-system-created;
      erienmyext:enm-type MOC;
      uses moc-EricssonLeanCarrierFunction-keys;
      container attributes {
        description "Attributes for EricssonLeanCarrierFunction";
        uses moc-EricssonLeanCarrierFunction;
      } // end 'container attributes'
    } // end 'list EricssonLeanCarrierFunction'
  }
  augment /erienmnrmcomtop:ManagedElement/erienmnrmlrat:ENodeBFunction/erienmnrmlrat:SectorCarrier {
    list PmUlInterferenceReport {
      key id;
      max-elements 8;
      description "Contains RF branch information used for the feature Uplink Interference Reporting. Created when the feature license is activated.\n\nThe RDNs of these MOs are PmUlInterferenceReport=1 to PmUlInterferenceReport=8.";
      yexte:is-system-created;
      erienmyext:enm-type MOC;
      uses moc-PmUlInterferenceReport-keys;
      container attributes {
        description "Attributes for PmUlInterferenceReport";
        uses moc-PmUlInterferenceReport;
      } // end 'container attributes'
    } // end 'list PmUlInterferenceReport'
  }
  augment /erienmnrmcomtop:ManagedElement/erienmnrmlrat:ENodeBFunction/erienmnrmlrat:EUtranCellFDD/erienmnrmlrat:UeMeasControl {
    list ReportConfigEUtraInterFreqLb {
      key id;
      max-elements 1;
      description "Contains the Report Configuration settings for UE measurements initiated for EUTRA Inter-frequency Load Balancing.\n\nThe RDN of this MO is ReportConfigEUtraInterFreqLb=1.";
      yexte:is-system-created;
      erienmyext:enm-type MOC;
      uses moc-ReportConfigEUtraInterFreqLb-keys;
      container attributes {
        description "Attributes for ReportConfigEUtraInterFreqLb";
        uses moc-ReportConfigEUtraInterFreqLb;
      } // end 'container attributes'
    } // end 'list ReportConfigEUtraInterFreqLb'
  }
  augment /erienmnrmcomtop:ManagedElement/erienmnrmlrat:ENodeBFunction/erienmnrmlrat:EUtranCellTDD/erienmnrmlrat:UeMeasControl {
    list ReportConfigEUtraInterFreqLb {
      key id;
      max-elements 1;
      description "Contains the Report Configuration settings for UE measurements initiated for EUTRA Inter-frequency Load Balancing.\n\nThe RDN of this MO is ReportConfigEUtraInterFreqLb=1.";
      yexte:is-system-created;
      erienmyext:enm-type MOC;
      uses moc-ReportConfigEUtraInterFreqLb-keys;
      container attributes {
        description "Attributes for ReportConfigEUtraInterFreqLb";
        uses moc-ReportConfigEUtraInterFreqLb;
      } // end 'container attributes'
    } // end 'list ReportConfigEUtraInterFreqLb'
  }
  augment /erienmnrmcomtop:ManagedElement/erienmnrmlrat:ENodeBFunction/erienmnrmlrat:UtraNetwork {
    list UtranFrequency {
      key id;
      max-elements 64;
      description "This Managed Object contains information of a specific Utran frequency.\n";
      erienmyext:enm-type MOC;
      uses moc-UtranFrequency-keys;
      container attributes {
        description "Attributes for UtranFrequency";
        uses moc-UtranFrequency;
      } // end 'container attributes'
    } // end 'list UtranFrequency'
  }
  augment /erienmnrmcomtop:ManagedElement/erienmnrmlrat:ENodeBFunction {
    list Paging {
      key id;
      max-elements 1;
      description "Configuration parameters for Paging feature in the RBS and applies to all cells.\n\nThe RDN of this MO is Paging=1.";
      yexte:is-system-created;
      erienmyext:enm-type MOC;
      uses moc-Paging-keys;
      container attributes {
        description "Attributes for Paging";
        uses moc-Paging;
      } // end 'container attributes'
    } // end 'list Paging'
  }
  augment /erienmnrmcomtop:ManagedElement/erienmnrmlrat:ENodeBFunction/erienmnrmlrat:EUtranCellTDD {
    list PrefTrafficMgmt {
      key id;
      max-elements 1;
      description "Contains cell specific configuration for the preferential traffic management functionality.";
      erienmyext:enm-type MOC;
      uses moc-PrefTrafficMgmt-keys;
      container attributes {
        description "Attributes for PrefTrafficMgmt";
        uses moc-PrefTrafficMgmt;
      } // end 'container attributes'
    } // end 'list PrefTrafficMgmt'
  }
  augment /erienmnrmcomtop:ManagedElement/erienmnrmlrat:ENodeBFunction/erienmnrmlrat:EUtranCellFDD {
    list PrefTrafficMgmt {
      key id;
      max-elements 1;
      description "Contains cell specific configuration for the preferential traffic management functionality.";
      erienmyext:enm-type MOC;
      uses moc-PrefTrafficMgmt-keys;
      container attributes {
        description "Attributes for PrefTrafficMgmt";
        uses moc-PrefTrafficMgmt;
      } // end 'container attributes'
    } // end 'list PrefTrafficMgmt'
  }
  augment /erienmnrmcomtop:ManagedElement/erienmnrmlrat:ENodeBFunction/erienmnrmlrat:CellResources {
    list CellResource {
      key id;
      max-elements 24;
      description "A combination of attributes which specify which cell resource partition a given UE should be included in.";
      status deprecated {
        yexte:status-information "Since 18.Q2. Planned to be removed.";
      }
      erienmyext:enm-type MOC;
      uses moc-CellResource-keys;
      container attributes {
        description "Attributes for CellResource";
        uses moc-CellResource;
      } // end 'container attributes'
    } // end 'list CellResource'
  }
  augment /erienmnrmcomtop:ManagedElement/erienmnrmlrat:ENodeBFunction/erienmnrmlrat:GeraNetwork {
    list ExternalGeranCell {
      key id;
      max-elements 8192;
      description "This Managed Object contains a GERAN cell.";
      erienmyext:enm-type MOC;
      uses moc-ExternalGeranCell-keys;
      container attributes {
        description "Attributes for ExternalGeranCell";
        uses moc-ExternalGeranCell;
      } // end 'container attributes'
    } // end 'list ExternalGeranCell'
  }
  augment /erienmnrmcomtop:ManagedElement/erienmnrmlrat:ENodeBFunction {
    list AnrPciConflictDrxProfile {
      key id;
      max-elements 1;
      description "DRX profiles, DRX parameters to map with ANR PCI conflict CGI reading.\n\nThe RDN of this MO is AnrPciConflictDrxProfile=1.";
      yexte:is-system-created;
      erienmyext:enm-type MOC;
      uses moc-AnrPciConflictDrxProfile-keys;
      container attributes {
        description "Attributes for AnrPciConflictDrxProfile";
        uses moc-AnrPciConflictDrxProfile;
      } // end 'container attributes'
    } // end 'list AnrPciConflictDrxProfile'
  }
  augment /erienmnrmcomtop:ManagedElement/erienmnrmlrat:ENodeBFunction {
    list AdditionalCoreNetwork {
      key id;
      max-elements 5;
      description "MO contains information of additional core network configuration.";
      erienmyext:enm-type MOC;
      uses moc-AdditionalCoreNetwork-keys;
      container attributes {
        description "Attributes for AdditionalCoreNetwork";
        uses moc-AdditionalCoreNetwork;
      } // end 'container attributes'
    } // end 'list AdditionalCoreNetwork'
  }
  augment /erienmnrmcomtop:ManagedElement/erienmnrmlrat:ENodeBFunction {
    list TimerProfile {
      key id;
      max-elements 22;
      description "Contains internal eNodeB timer profiles to be mapped to different QCIs.";
      erienmyext:enm-type MOC;
      uses moc-TimerProfile-keys;
      container attributes {
        description "Attributes for TimerProfile";
        uses moc-TimerProfile;
      } // end 'container attributes'
    } // end 'list TimerProfile'
  }
  augment /erienmnrmcomtop:ManagedElement/erienmnrmlrat:ENodeBFunction/erienmnrmlrat:EUtranCellFDD {
    list CellSleepFunction {
      key id;
      max-elements 1;
      description "Contains configuration parameters for function Cell Sleep Mode.\nThe RDN of this MO is CellSleepFunction=1. ";
      yexte:is-system-created;
      erienmyext:enm-type MOC;
      uses moc-CellSleepFunction-keys;
      container attributes {
        description "Attributes for CellSleepFunction";
        uses moc-CellSleepFunction;
      } // end 'container attributes'
    } // end 'list CellSleepFunction'
  }
  augment /erienmnrmcomtop:ManagedElement/erienmnrmlrat:ENodeBFunction/erienmnrmlrat:EUtranCellTDD {
    list CellSleepFunction {
      key id;
      max-elements 1;
      description "Contains configuration parameters for function Cell Sleep Mode.\nThe RDN of this MO is CellSleepFunction=1. ";
      yexte:is-system-created;
      erienmyext:enm-type MOC;
      uses moc-CellSleepFunction-keys;
      container attributes {
        description "Attributes for CellSleepFunction";
        uses moc-CellSleepFunction;
      } // end 'container attributes'
    } // end 'list CellSleepFunction'
  }
  augment /erienmnrmcomtop:ManagedElement/erienmnrmlrat:ENodeBFunction/erienmnrmlrat:EUtranCellFDD/erienmnrmlrat:UeMeasControl/erienmnrmlrat:ReportConfigEUtraBestCell {
    list ReportConfigEUtraBestCellAnr {
      key id;
      max-elements 1;
      description "The ANR delta report configuration settings for the A3 event measurements as compared to mobility provided in the parent MO class.\n\nThe RDN of this MO is ReportConfigEUtraBestCellAnr=1.";
      yexte:is-system-created;
      erienmyext:enm-type MOC;
      uses moc-ReportConfigEUtraBestCellAnr-keys;
      container attributes {
        description "Attributes for ReportConfigEUtraBestCellAnr";
        uses moc-ReportConfigEUtraBestCellAnr;
      } // end 'container attributes'
    } // end 'list ReportConfigEUtraBestCellAnr'
  }
  augment /erienmnrmcomtop:ManagedElement/erienmnrmlrat:ENodeBFunction/erienmnrmlrat:EUtranCellTDD/erienmnrmlrat:UeMeasControl/erienmnrmlrat:ReportConfigEUtraBestCell {
    list ReportConfigEUtraBestCellAnr {
      key id;
      max-elements 1;
      description "The ANR delta report configuration settings for the A3 event measurements as compared to mobility provided in the parent MO class.\n\nThe RDN of this MO is ReportConfigEUtraBestCellAnr=1.";
      yexte:is-system-created;
      erienmyext:enm-type MOC;
      uses moc-ReportConfigEUtraBestCellAnr-keys;
      container attributes {
        description "Attributes for ReportConfigEUtraBestCellAnr";
        uses moc-ReportConfigEUtraBestCellAnr;
      } // end 'container attributes'
    } // end 'list ReportConfigEUtraBestCellAnr'
  }
  augment /erienmnrmcomtop:ManagedElement/erienmnrmlrat:ENodeBFunction/erienmnrmlrat:GUtraNetwork {
    list ExternalGNodeBFunction {
      key id;
      max-elements 64;
      description "This managed object represents an GNodeB.";
      erienmyext:enm-type MOC;
      uses moc-ExternalGNodeBFunction-keys;
      container attributes {
        description "Attributes for ExternalGNodeBFunction";
        uses moc-ExternalGNodeBFunction;
      } // end 'container attributes'
    } // end 'list ExternalGNodeBFunction'
  }
  augment /erienmnrmcomtop:ManagedElement/erienmnrmlrat:ENodeBFunction/erienmnrmlrat:EUtranCellFDD/erienmnrmlrat:UeMeasControl {
    list ReportConfigSCellA1A2 {
      key id;
      max-elements 1;
      description "This managed object contains the report configuration settings for A2/A1 measurements on the frequency of any serving SCell when this cell is used as PCell.\n\nThe RDN of this MO is ReportConfigSCellA1A2=1.";
      yexte:is-system-created;
      erienmyext:enm-type MOC;
      uses moc-ReportConfigSCellA1A2-keys;
      container attributes {
        description "Attributes for ReportConfigSCellA1A2";
        uses moc-ReportConfigSCellA1A2;
      } // end 'container attributes'
    } // end 'list ReportConfigSCellA1A2'
  }
  augment /erienmnrmcomtop:ManagedElement/erienmnrmlrat:ENodeBFunction/erienmnrmlrat:EUtranCellTDD/erienmnrmlrat:UeMeasControl {
    list ReportConfigSCellA1A2 {
      key id;
      max-elements 1;
      description "This managed object contains the report configuration settings for A2/A1 measurements on the frequency of any serving SCell when this cell is used as PCell.\n\nThe RDN of this MO is ReportConfigSCellA1A2=1.";
      yexte:is-system-created;
      erienmyext:enm-type MOC;
      uses moc-ReportConfigSCellA1A2-keys;
      container attributes {
        description "Attributes for ReportConfigSCellA1A2";
        uses moc-ReportConfigSCellA1A2;
      } // end 'container attributes'
    } // end 'list ReportConfigSCellA1A2'
  }
  augment /erienmnrmcomtop:ManagedElement/erienmnrmlrat:ENodeBFunction/erienmnrmlrat:Mbms/erienmnrmlrat:MbsfnArea/erienmnrmlrat:PmchMch {
    list MbmsService {
      key id;
      max-elements 28;
      description "MO represents configuration related to MBMS bearer service. If Autoconfiguration of LTE Broadcast Subframes\nis used, this MO will be created by the system.";
      erienmyext:enm-type MOC;
      uses moc-MbmsService-keys;
      container attributes {
        description "Attributes for MbmsService";
        uses moc-MbmsService;
      } // end 'container attributes'
    } // end 'list MbmsService'
  }
  augment /erienmnrmcomtop:ManagedElement/erienmnrmlrat:ENodeBFunction {
    list AmoFunction {
      key id;
      max-elements 1;
      description "Contains parameters for Automated Mobility Optimization function.\n\nThe RDN of this MO is AmoFunction=1.";
      yexte:is-system-created;
      erienmyext:enm-type MOC;
      uses moc-AmoFunction-keys;
      container attributes {
        description "Attributes for AmoFunction";
        uses moc-AmoFunction;
      } // end 'container attributes'
    } // end 'list AmoFunction'
  }
  augment /erienmnrmcomtop:ManagedElement/erienmnrmlrat:ENodeBFunction/erienmnrmlrat:GUtraNetwork {
    list GUtranSyncSignalFrequency {
      key id;
      max-elements 24;
      description "Contains information of a specific GUtran frequency.";
      erienmyext:enm-type MOC;
      uses moc-GUtranSyncSignalFrequency-keys;
      container attributes {
        description "Attributes for GUtranSyncSignalFrequency";
        uses moc-GUtranSyncSignalFrequency;
      } // end 'container attributes'
    } // end 'list GUtranSyncSignalFrequency'
  }
  augment /erienmnrmcomtop:ManagedElement/erienmnrmlrat:ENodeBFunction {
    list PlmnInfo {
      key id;
      max-elements 6;
      description "PLMN specific configuration parameters.";
      erienmyext:enm-type MOC;
      uses moc-PlmnInfo-keys;
      container attributes {
        description "Attributes for PlmnInfo";
        uses moc-PlmnInfo;
      } // end 'container attributes'
    } // end 'list PlmnInfo'
  }
  augment /erienmnrmcomtop:ManagedElement/erienmnrmlrat:ENodeBFunction/erienmnrmlrat:EUtranCellFDD/erienmnrmlrat:UeMeasControl {
    list ReportConfigInterRatLb {
      key id;
      max-elements 1;
      description "The MO contains the report configuration settings for UE measurements that are initiated for Inter-RAT load balancing actions.\n\nThe RDN of this MO is ReportConfigInterRatLb=1.";
      yexte:is-system-created;
      erienmyext:enm-type MOC;
      uses moc-ReportConfigInterRatLb-keys;
      container attributes {
        description "Attributes for ReportConfigInterRatLb";
        uses moc-ReportConfigInterRatLb;
      } // end 'container attributes'
    } // end 'list ReportConfigInterRatLb'
  }
  augment /erienmnrmcomtop:ManagedElement/erienmnrmlrat:ENodeBFunction/erienmnrmlrat:EUtranCellTDD/erienmnrmlrat:UeMeasControl {
    list ReportConfigInterRatLb {
      key id;
      max-elements 1;
      description "The MO contains the report configuration settings for UE measurements that are initiated for Inter-RAT load balancing actions.\n\nThe RDN of this MO is ReportConfigInterRatLb=1.";
      yexte:is-system-created;
      erienmyext:enm-type MOC;
      uses moc-ReportConfigInterRatLb-keys;
      container attributes {
        description "Attributes for ReportConfigInterRatLb";
        uses moc-ReportConfigInterRatLb;
      } // end 'container attributes'
    } // end 'list ReportConfigInterRatLb'
  }
  augment /erienmnrmcomtop:ManagedElement/erienmnrmlrat:ENodeBFunction/erienmnrmlrat:EUtranCellFDD/erienmnrmlrat:Cdma2000FreqBandRelation {
    list Cdma2000CellRelation {
      key id;
      max-elements 64;
      description "This Managed Object represents a mobility relation between a EUtranCellFDD or an EUtranCellTDD and an Cdma2000Cell. It contains parameters that are specific for this relation.\n";
      erienmyext:enm-type MOC;
      uses moc-Cdma2000CellRelation-keys;
      container attributes {
        description "Attributes for Cdma2000CellRelation";
        uses moc-Cdma2000CellRelation;
      } // end 'container attributes'
    } // end 'list Cdma2000CellRelation'
  }
  augment /erienmnrmcomtop:ManagedElement/erienmnrmlrat:ENodeBFunction/erienmnrmlrat:EUtranCellTDD/erienmnrmlrat:Cdma2000FreqBandRelation {
    list Cdma2000CellRelation {
      key id;
      max-elements 64;
      description "This Managed Object represents a mobility relation between a EUtranCellFDD or an EUtranCellTDD and an Cdma2000Cell. It contains parameters that are specific for this relation.\n";
      erienmyext:enm-type MOC;
      uses moc-Cdma2000CellRelation-keys;
      container attributes {
        description "Attributes for Cdma2000CellRelation";
        uses moc-Cdma2000CellRelation;
      } // end 'container attributes'
    } // end 'list Cdma2000CellRelation'
  }
  augment /erienmnrmcomtop:ManagedElement/erienmnrmlrat:ENodeBFunction {
    list NbIotCell {
      key id;
      max-elements 24;
      description "This MO represents a Nb-Iot cell and contains parameters needed by the cell.";
      erienmyext:enm-type MOC;
      uses moc-NbIotCell-keys;
      container attributes {
        description "Attributes for NbIotCell";
        uses moc-NbIotCell;
      } // end 'container attributes'
    } // end 'list NbIotCell'
  }
  augment /erienmnrmcomtop:ManagedElement/erienmnrmlrat:ENodeBFunction {
    list ParameterChangeRequests {
      key id;
      max-elements 1;
      description "Contains list of parameter change requests produced by open loop SON functions.\n\nThe RDN of this MO is ParameterChangeRequests=1.";
      yexte:is-system-created;
      erienmyext:enm-type MOC;
      uses moc-ParameterChangeRequests-keys;
      container attributes {
        description "Attributes for ParameterChangeRequests";
        uses moc-ParameterChangeRequests;
      } // end 'container attributes'
    } // end 'list ParameterChangeRequests'
  }
  augment /erienmnrmcomtop:ManagedElement/erienmnrmlrat:ENodeBFunction {
    list MdtConfiguration {
      key id;
      max-elements 1;
      description "Contains the parameters for the Minimization of Drive Tests (MDT).\n\nThe RDN of this MO is MdtConfiguration=1.";
      yexte:is-system-created;
      erienmyext:enm-type MOC;
      uses moc-MdtConfiguration-keys;
      container attributes {
        description "Attributes for MdtConfiguration";
        uses moc-MdtConfiguration;
      } // end 'container attributes'
    } // end 'list MdtConfiguration'
  }
  augment /erienmnrmcomtop:ManagedElement/erienmnrmlrat:ENodeBFunction/erienmnrmlrat:EUtranCellFDD/erienmnrmlrat:UeMeasControl {
    list ReportConfigB2Cdma20001xRtt {
      key id;
      max-elements 1;
      description "This managed object contains report configuration settings for the B2 event for CDMA2000 1xRTT measurements, used when searching for a suitable target cell when SRVCC is triggered for the UE. The B2 event is used to detect when a CDMA2000 1xRTT cell becomes better than threshold2, and serving cell becomes worse than threshold1. The actual threshold values used can be adjusted by frequency relation related offsets if the feature Multi-Layer Service-Triggered Mobility (MLSTM) is enabled.\n\nThe RDN of this MO is ReportConfigB2Cdma20001xRtt=1.";
      yexte:is-system-created;
      erienmyext:enm-type MOC;
      uses moc-ReportConfigB2Cdma20001xRtt-keys;
      container attributes {
        description "Attributes for ReportConfigB2Cdma20001xRtt";
        uses moc-ReportConfigB2Cdma20001xRtt;
      } // end 'container attributes'
    } // end 'list ReportConfigB2Cdma20001xRtt'
  }
  augment /erienmnrmcomtop:ManagedElement/erienmnrmlrat:ENodeBFunction/erienmnrmlrat:EUtranCellTDD/erienmnrmlrat:UeMeasControl {
    list ReportConfigB2Cdma20001xRtt {
      key id;
      max-elements 1;
      description "This managed object contains report configuration settings for the B2 event for CDMA2000 1xRTT measurements, used when searching for a suitable target cell when SRVCC is triggered for the UE. The B2 event is used to detect when a CDMA2000 1xRTT cell becomes better than threshold2, and serving cell becomes worse than threshold1. The actual threshold values used can be adjusted by frequency relation related offsets if the feature Multi-Layer Service-Triggered Mobility (MLSTM) is enabled.\n\nThe RDN of this MO is ReportConfigB2Cdma20001xRtt=1.";
      yexte:is-system-created;
      erienmyext:enm-type MOC;
      uses moc-ReportConfigB2Cdma20001xRtt-keys;
      container attributes {
        description "Attributes for ReportConfigB2Cdma20001xRtt";
        uses moc-ReportConfigB2Cdma20001xRtt;
      } // end 'container attributes'
    } // end 'list ReportConfigB2Cdma20001xRtt'
  }
  augment /erienmnrmcomtop:ManagedElement/erienmnrmlrat:ENodeBFunction/erienmnrmlrat:EUtranCellFDD/erienmnrmlrat:UeMeasControl {
    list ReportConfigEUtraIntraFreqPm {
      key id;
      max-elements 2;
      description "This managed object contains the Report Configuration settings for UE measurements on EUTRA intra frequencies initiated by PM.\n";
      erienmyext:enm-type MOC;
      uses moc-ReportConfigEUtraIntraFreqPm-keys;
      container attributes {
        description "Attributes for ReportConfigEUtraIntraFreqPm";
        uses moc-ReportConfigEUtraIntraFreqPm;
      } // end 'container attributes'
    } // end 'list ReportConfigEUtraIntraFreqPm'
  }
  augment /erienmnrmcomtop:ManagedElement/erienmnrmlrat:ENodeBFunction/erienmnrmlrat:EUtranCellTDD/erienmnrmlrat:UeMeasControl {
    list ReportConfigEUtraIntraFreqPm {
      key id;
      max-elements 2;
      description "This managed object contains the Report Configuration settings for UE measurements on EUTRA intra frequencies initiated by PM.\n";
      erienmyext:enm-type MOC;
      uses moc-ReportConfigEUtraIntraFreqPm-keys;
      container attributes {
        description "Attributes for ReportConfigEUtraIntraFreqPm";
        uses moc-ReportConfigEUtraIntraFreqPm;
      } // end 'container attributes'
    } // end 'list ReportConfigEUtraIntraFreqPm'
  }
  augment /erienmnrmcomtop:ManagedElement/erienmnrmlrat:ENodeBFunction/erienmnrmlrat:CarrierAggregationFunction {
    list BandCombCompression {
      key id;
      max-elements 1;
      description "Compression of CA combinations. Attributes take effect only if license for Carrier Aggregation is present and the feature is active.\n\nThe RDN of this MO is BandCombCompression=1.";
      yexte:is-system-created;
      erienmyext:enm-type MOC;
      uses moc-BandCombCompression-keys;
      container attributes {
        description "Attributes for BandCombCompression";
        uses moc-BandCombCompression;
      } // end 'container attributes'
    } // end 'list BandCombCompression'
  }
  augment /erienmnrmcomtop:ManagedElement/erienmnrmlrat:ENodeBFunction/erienmnrmlrat:FlexibleQoSFunction {
    list UserProfile {
      key id;
      max-elements 50;
      description "A combination of attributes specifies which SCI profile a given bearer should be assigned.";
      erienmyext:enm-type MOC;
      uses moc-UserProfile-keys;
      container attributes {
        description "Attributes for UserProfile";
        uses moc-UserProfile;
      } // end 'container attributes'
    } // end 'list UserProfile'
  }
  augment /erienmnrmcomtop:ManagedElement/erienmnrmlrat:ENodeBFunction/erienmnrmlrat:EUtranCellFDD/erienmnrmlrat:UeMeasControl {
    list ReportConfigB1GUtra {
      key id;
      max-elements 1;
      description "Contains report configuration settings for event B1 GUtra measurements.\n\nThe RDN of this MO is ReportConfigB1GUtra=1.";
      yexte:is-system-created;
      erienmyext:enm-type MOC;
      uses moc-ReportConfigB1GUtra-keys;
      container attributes {
        description "Attributes for ReportConfigB1GUtra";
        uses moc-ReportConfigB1GUtra;
      } // end 'container attributes'
    } // end 'list ReportConfigB1GUtra'
  }
  augment /erienmnrmcomtop:ManagedElement/erienmnrmlrat:ENodeBFunction/erienmnrmlrat:EUtranCellTDD/erienmnrmlrat:UeMeasControl {
    list ReportConfigB1GUtra {
      key id;
      max-elements 1;
      description "Contains report configuration settings for event B1 GUtra measurements.\n\nThe RDN of this MO is ReportConfigB1GUtra=1.";
      yexte:is-system-created;
      erienmyext:enm-type MOC;
      uses moc-ReportConfigB1GUtra-keys;
      container attributes {
        description "Attributes for ReportConfigB1GUtra";
        uses moc-ReportConfigB1GUtra;
      } // end 'container attributes'
    } // end 'list ReportConfigB1GUtra'
  }
  augment /erienmnrmcomtop:ManagedElement/erienmnrmlrat:ENodeBFunction {
    list AdmissionControl {
      key id;
      max-elements 1;
      description "Contains parameters for admission control function.\n\nThe RDN of this MO is AdmissionControl=1.";
      yexte:is-system-created;
      erienmyext:enm-type MOC;
      uses moc-AdmissionControl-keys;
      container attributes {
        description "Attributes for AdmissionControl";
        uses moc-AdmissionControl;
      } // end 'container attributes'
    } // end 'list AdmissionControl'
  }
  augment /erienmnrmcomtop:ManagedElement/erienmnrmlrat:ENodeBFunction/erienmnrmlrat:EUtranCellFDD/erienmnrmlrat:EUtranFreqRelation {
    list EUtranCellRelation {
      key id;
      max-elements 128;
      description "This managed object represents the handover relationship between two neighboring EUTRAN cells.\n";
      erienmyext:enm-type MOC;
      uses moc-EUtranCellRelation-keys;
      container attributes {
        description "Attributes for EUtranCellRelation";
        uses moc-EUtranCellRelation;
      } // end 'container attributes'
    } // end 'list EUtranCellRelation'
  }
  augment /erienmnrmcomtop:ManagedElement/erienmnrmlrat:ENodeBFunction/erienmnrmlrat:EUtranCellTDD/erienmnrmlrat:EUtranFreqRelation {
    list EUtranCellRelation {
      key id;
      max-elements 128;
      description "This managed object represents the handover relationship between two neighboring EUTRAN cells.\n";
      erienmyext:enm-type MOC;
      uses moc-EUtranCellRelation-keys;
      container attributes {
        description "Attributes for EUtranCellRelation";
        uses moc-EUtranCellRelation;
      } // end 'container attributes'
    } // end 'list EUtranCellRelation'
  }
  augment /erienmnrmcomtop:ManagedElement/erienmnrmlrat:ENodeBFunction {
    list EUtranCellTDD {
      key id;
      max-elements 24;
      description "This MO represents a TDD cell and contains parameters needed by the cell. It also contains parameters for the mandatory common channels. The cell need to have the same duplex mode (FDD or TDD) as the already existing intra-RBS cells, if any.\n";
      erienmyext:enm-type MOC;
      uses moc-EUtranCellTDD-keys;
      container attributes {
        description "Attributes for EUtranCellTDD";
        uses moc-EUtranCellTDD;
      } // end 'container attributes'
    } // end 'list EUtranCellTDD'
  }
  augment /erienmnrmcomtop:ManagedElement/erienmnrmlrat:ENodeBFunction/erienmnrmlrat:EUtranCellFDD/erienmnrmlrat:UeMeasControl {
    list ReportConfigB2GeranUlTrig {
      key id;
      max-elements 1;
      description "Contains report configuration settings for the B2 event for GERAN measurements initiated by Uplink-Triggered Inter-Frequency Mobility. The actual threshold values used can be adjusted by frequency relation or QCI related offsets if the feature Multi-Layer Service-Triggered Mobility (MLSTM) is enabled.\n\nThe RDN of this MO is ReportConfigB2GeranUlTrig=1.";
      yexte:is-system-created;
      erienmyext:enm-type MOC;
      uses moc-ReportConfigB2GeranUlTrig-keys;
      container attributes {
        description "Attributes for ReportConfigB2GeranUlTrig";
        uses moc-ReportConfigB2GeranUlTrig;
      } // end 'container attributes'
    } // end 'list ReportConfigB2GeranUlTrig'
  }
  augment /erienmnrmcomtop:ManagedElement/erienmnrmlrat:ENodeBFunction/erienmnrmlrat:EUtranCellTDD/erienmnrmlrat:UeMeasControl {
    list ReportConfigB2GeranUlTrig {
      key id;
      max-elements 1;
      description "Contains report configuration settings for the B2 event for GERAN measurements initiated by Uplink-Triggered Inter-Frequency Mobility. The actual threshold values used can be adjusted by frequency relation or QCI related offsets if the feature Multi-Layer Service-Triggered Mobility (MLSTM) is enabled.\n\nThe RDN of this MO is ReportConfigB2GeranUlTrig=1.";
      yexte:is-system-created;
      erienmyext:enm-type MOC;
      uses moc-ReportConfigB2GeranUlTrig-keys;
      container attributes {
        description "Attributes for ReportConfigB2GeranUlTrig";
        uses moc-ReportConfigB2GeranUlTrig;
      } // end 'container attributes'
    } // end 'list ReportConfigB2GeranUlTrig'
  }
  augment /erienmnrmcomtop:ManagedElement/erienmnrmlrat:ENodeBFunction/erienmnrmlrat:QciTable {
    list QciProfileOperatorDefined {
      key id;
      max-elements 9;
      description "Contains bearer-level QoS configuration. Instances of this class are created on demand by the operator. Each QciProfileOperatorDefined instance corresponds to a unique operator defined QCI number within the range 10-255. The instances can be created and configured independent of the serviceStateOperatorDefinedQci. However the configured QCI profiles can not be used at bearer setup / modify unless the service state is OPERABLE.\n";
      erienmyext:enm-type MOC;
      uses moc-QciProfileOperatorDefined-keys;
      container attributes {
        description "Attributes for QciProfileOperatorDefined";
        uses moc-QciProfileOperatorDefined;
      } // end 'container attributes'
    } // end 'list QciProfileOperatorDefined'
  }
  augment /erienmnrmcomtop:ManagedElement/erienmnrmlrat:ENodeBFunction/erienmnrmlrat:EUtranCellFDD {
    list Etws {
      key id;
      max-elements 1;
      description "Stores warning information for cell to be broadcast in SIB10 or SIB11.\n\nThe RDN of this MO is Etws=1.";
      yexte:is-system-created;
      erienmyext:enm-type MOC;
      uses moc-Etws-keys;
    } // end 'list Etws'
  }
  augment /erienmnrmcomtop:ManagedElement/erienmnrmlrat:ENodeBFunction/erienmnrmlrat:EUtranCellTDD {
    list Etws {
      key id;
      max-elements 1;
      description "Stores warning information for cell to be broadcast in SIB10 or SIB11.\n\nThe RDN of this MO is Etws=1.";
      yexte:is-system-created;
      erienmyext:enm-type MOC;
      uses moc-Etws-keys;
    } // end 'list Etws'
  }
  augment /erienmnrmcomtop:ManagedElement/erienmnrmlrat:ENodeBFunction {
    list DlComp {
      key id;
      max-elements 1;
      description "This MO contains configuration settings for Downlink Coordinated Multi-Point.\n\nThe RDN of this MO is DlComp=1.";
      yexte:is-system-created;
      erienmyext:enm-type MOC;
      uses moc-DlComp-keys;
    } // end 'list DlComp'
  }
  augment /erienmnrmcomtop:ManagedElement/erienmnrmlrat:ENodeBFunction {
    list PtmFunction {
      key id;
      max-elements 1;
      description "Contains eNodeB-specific configuration for Preferential Traffic Management.\n\nThe RDN of this MO is PtmFunction=1.";
      yexte:is-system-created;
      erienmyext:enm-type MOC;
      uses moc-PtmFunction-keys;
      container attributes {
        description "Attributes for PtmFunction";
        uses moc-PtmFunction;
      } // end 'container attributes'
    } // end 'list PtmFunction'
  }
  augment /erienmnrmcomtop:ManagedElement/erienmnrmlrat:ENodeBFunction/erienmnrmlrat:EUtraNetwork/erienmnrmlrat:ExternalENodeBFunction {
    list ExternalEUtranCellFDD {
      key id;
      max-elements 24;
      description "This managed object represents a neighbor EUTRAN cell (FDD) in another ENodeB in any MME pool.\n";
      erienmyext:enm-type MOC;
      uses moc-ExternalEUtranCellFDD-keys;
      container attributes {
        description "Attributes for ExternalEUtranCellFDD";
        uses moc-ExternalEUtranCellFDD;
      } // end 'container attributes'
    } // end 'list ExternalEUtranCellFDD'
  }
  augment /erienmnrmcomtop:ManagedElement/erienmnrmlrat:ENodeBFunction/erienmnrmlrat:GeraNetwork {
    list GeranFreqGroup {
      key id;
      max-elements 192;
      description "This managed object contains information about a set of Geran ARFCN values, which represent a group of Geran frequencies.\nIt is not possible to include Geran frequencies from both band 1800 and 1900 within the same GeranFreqGroup.\n\n";
      erienmyext:enm-type MOC;
      uses moc-GeranFreqGroup-keys;
      container attributes {
        description "Attributes for GeranFreqGroup";
        uses moc-GeranFreqGroup;
      } // end 'container attributes'
    } // end 'list GeranFreqGroup'
  }
  augment /erienmnrmcomtop:ManagedElement/erienmnrmlrat:ENodeBFunction {
    list ResourcePartitions {
      key id;
      max-elements 1;
      description "Set of resource partitions defined for use in the node.\n\nThe RDN of this MO is ResourcePartitions=1.";
      yexte:is-system-created;
      erienmyext:enm-type MOC;
      uses moc-ResourcePartitions-keys;
    } // end 'list ResourcePartitions'
  }
  augment /erienmnrmcomtop:ManagedElement/erienmnrmlrat:ENodeBFunction/erienmnrmlrat:EUtranCellFDD/erienmnrmlrat:UeMeasControl {
    list ReportConfigA5 {
      key id;
      max-elements 1;
      description "This managed object contains report configuration settings for the A5 event measurements. The A5 event is used to detect when serving cell becomes worse than threshold1, and neighbor cell becomes better than threshold2. The actual threshold values used can be adjusted by frequency relation related offsets if the feature Multi-Layer Service-Triggered Mobility (MLSTM) is enabled.\n\nThe RDN of this MO is ReportConfigA5=1.";
      yexte:is-system-created;
      erienmyext:enm-type MOC;
      uses moc-ReportConfigA5-keys;
      container attributes {
        description "Attributes for ReportConfigA5";
        uses moc-ReportConfigA5;
      } // end 'container attributes'
    } // end 'list ReportConfigA5'
  }
  augment /erienmnrmcomtop:ManagedElement/erienmnrmlrat:ENodeBFunction/erienmnrmlrat:EUtranCellTDD/erienmnrmlrat:UeMeasControl {
    list ReportConfigA5 {
      key id;
      max-elements 1;
      description "This managed object contains report configuration settings for the A5 event measurements. The A5 event is used to detect when serving cell becomes worse than threshold1, and neighbor cell becomes better than threshold2. The actual threshold values used can be adjusted by frequency relation related offsets if the feature Multi-Layer Service-Triggered Mobility (MLSTM) is enabled.\n\nThe RDN of this MO is ReportConfigA5=1.";
      yexte:is-system-created;
      erienmyext:enm-type MOC;
      uses moc-ReportConfigA5-keys;
      container attributes {
        description "Attributes for ReportConfigA5";
        uses moc-ReportConfigA5;
      } // end 'container attributes'
    } // end 'list ReportConfigA5'
  }
  augment /erienmnrmcomtop:ManagedElement/erienmnrmlrat:ENodeBFunction {
    list SubscriberGroupProfile {
      key id;
      max-elements 5;
      description "Contains set of trigger conditions used to select subset of all subscribers as well as a number of parameters/functions that are applied to this group.";
      erienmyext:enm-type MOC;
      uses moc-SubscriberGroupProfile-keys;
      container attributes {
        description "Attributes for SubscriberGroupProfile";
        uses moc-SubscriberGroupProfile;
      } // end 'container attributes'
    } // end 'list SubscriberGroupProfile'
  }
  augment /erienmnrmcomtop:ManagedElement/erienmnrmlrat:ENodeBFunction/erienmnrmlrat:PtmFunction/erienmnrmlrat:PtmCellProfile {
    list PtmIflbConfig {
      key id;
      max-elements 1;
      description "Contains PTM specific parameters affecting Inter-Frequency Load Balancing feature.\n\nThe RDN of this MO is PtmIflbConfig=1.";
      yexte:is-system-created;
      erienmyext:enm-type MOC;
      uses moc-PtmIflbConfig-keys;
      container attributes {
        description "Attributes for PtmIflbConfig";
        uses moc-PtmIflbConfig;
      } // end 'container attributes'
    } // end 'list PtmIflbConfig'
  }
  augment /erienmnrmcomtop:ManagedElement/erienmnrmlrat:ENodeBFunction/erienmnrmlrat:EUtranCellFDD/erienmnrmlrat:UeMeasControl {
    list ReportConfigA4 {
      key id;
      max-elements 1;
      description "This managed object contains report configuration settings for the A4 event measurements. The A4 event is used to detect when neighbor cell becomes better than threshold.\n\nThe RDN of this MO is ReportConfigA4=1.";
      yexte:is-system-created;
      erienmyext:enm-type MOC;
      uses moc-ReportConfigA4-keys;
      container attributes {
        description "Attributes for ReportConfigA4";
        uses moc-ReportConfigA4;
      } // end 'container attributes'
    } // end 'list ReportConfigA4'
  }
  augment /erienmnrmcomtop:ManagedElement/erienmnrmlrat:ENodeBFunction/erienmnrmlrat:EUtranCellTDD/erienmnrmlrat:UeMeasControl {
    list ReportConfigA4 {
      key id;
      max-elements 1;
      description "This managed object contains report configuration settings for the A4 event measurements. The A4 event is used to detect when neighbor cell becomes better than threshold.\n\nThe RDN of this MO is ReportConfigA4=1.";
      yexte:is-system-created;
      erienmyext:enm-type MOC;
      uses moc-ReportConfigA4-keys;
      container attributes {
        description "Attributes for ReportConfigA4";
        uses moc-ReportConfigA4;
      } // end 'container attributes'
    } // end 'list ReportConfigA4'
  }
  augment /erienmnrmcomtop:ManagedElement/erienmnrmlrat:ENodeBFunction/erienmnrmlrat:EUtranCellFDD/erienmnrmlrat:UeMeasControl {
    list ReportConfigCsfbCdma2000 {
      key id;
      max-elements 1;
      description "The MO contains report configuration settings for the B1 or B2 event for CDMA2000 1xRTT measurements, used when searching for a suitable target cell when CS Fallback is triggered for the UE.\n\nThe RDN of this MO is ReportConfigCsfbCdma2000=1.";
      yexte:is-system-created;
      erienmyext:enm-type MOC;
      uses moc-ReportConfigCsfbCdma2000-keys;
      container attributes {
        description "Attributes for ReportConfigCsfbCdma2000";
        uses moc-ReportConfigCsfbCdma2000;
      } // end 'container attributes'
    } // end 'list ReportConfigCsfbCdma2000'
  }
  augment /erienmnrmcomtop:ManagedElement/erienmnrmlrat:ENodeBFunction/erienmnrmlrat:EUtranCellTDD/erienmnrmlrat:UeMeasControl {
    list ReportConfigCsfbCdma2000 {
      key id;
      max-elements 1;
      description "The MO contains report configuration settings for the B1 or B2 event for CDMA2000 1xRTT measurements, used when searching for a suitable target cell when CS Fallback is triggered for the UE.\n\nThe RDN of this MO is ReportConfigCsfbCdma2000=1.";
      yexte:is-system-created;
      erienmyext:enm-type MOC;
      uses moc-ReportConfigCsfbCdma2000-keys;
      container attributes {
        description "Attributes for ReportConfigCsfbCdma2000";
        uses moc-ReportConfigCsfbCdma2000;
      } // end 'container attributes'
    } // end 'list ReportConfigCsfbCdma2000'
  }
  augment /erienmnrmcomtop:ManagedElement/erienmnrmlrat:ENodeBFunction {
    list NonPlannedPciDrxProfile {
      key id;
      max-elements 1;
      description "Contains DRX profiles, DRX parameters, to map with non-planned PCI, CSG cell and Hybrid CSG cell CGI reading.\n\nThe RDN of this MO is NonPlannedPciDrxProfile=1.";
      yexte:is-system-created;
      erienmyext:enm-type MOC;
      uses moc-NonPlannedPciDrxProfile-keys;
      container attributes {
        description "Attributes for NonPlannedPciDrxProfile";
        uses moc-NonPlannedPciDrxProfile;
      } // end 'container attributes'
    } // end 'list NonPlannedPciDrxProfile'
  }
  augment /erienmnrmcomtop:ManagedElement/erienmnrmlrat:ENodeBFunction/erienmnrmlrat:EUtranCellFDD/erienmnrmlrat:Cdma2000FreqBandRelation {
    list Cdma2000FreqRelation {
      key id;
      max-elements 64;
      description "This Managed Object represents a mobility relation between a EUtranCellFDD or an EUtranCellTDD and a CDMA2000Frequency. It contains parameters that are specific for this relation.\n\nDeleting this MO while the parent EUtranCellFDD/EUtranCellTDD has operationalState set to ENABLED is not recommended as it may affect traffic.\n";
      erienmyext:enm-type MOC;
      uses moc-Cdma2000FreqRelation-keys;
      container attributes {
        description "Attributes for Cdma2000FreqRelation";
        uses moc-Cdma2000FreqRelation;
      } // end 'container attributes'
    } // end 'list Cdma2000FreqRelation'
  }
  augment /erienmnrmcomtop:ManagedElement/erienmnrmlrat:ENodeBFunction/erienmnrmlrat:EUtranCellTDD/erienmnrmlrat:Cdma2000FreqBandRelation {
    list Cdma2000FreqRelation {
      key id;
      max-elements 64;
      description "This Managed Object represents a mobility relation between a EUtranCellFDD or an EUtranCellTDD and a CDMA2000Frequency. It contains parameters that are specific for this relation.\n\nDeleting this MO while the parent EUtranCellFDD/EUtranCellTDD has operationalState set to ENABLED is not recommended as it may affect traffic.\n";
      erienmyext:enm-type MOC;
      uses moc-Cdma2000FreqRelation-keys;
      container attributes {
        description "Attributes for Cdma2000FreqRelation";
        uses moc-Cdma2000FreqRelation;
      } // end 'container attributes'
    } // end 'list Cdma2000FreqRelation'
  }
  augment /erienmnrmcomtop:ManagedElement/erienmnrmlrat:ENodeBFunction/erienmnrmlrat:EUtraNetwork/erienmnrmlrat:ExternalENodeBFunction/erienmnrmlrat:TermPointToENB {
    list GtpPath {
      key id;
      max-elements 1;
      description "Models GTP-U path between RBS and another node, either SGW or neighbor RBS.\n\nThe RDN of this MO is GtpPath=1.";
      yexte:is-system-created;
      erienmyext:enm-type MOC;
      uses moc-GtpPath-keys;
      container attributes {
        description "Attributes for GtpPath";
        uses moc-GtpPath;
      } // end 'container attributes'
    } // end 'list GtpPath'
  }
  augment /erienmnrmcomtop:ManagedElement/erienmnrmlrat:ENodeBFunction/erienmnrmlrat:TermPointToSGW {
    list GtpPath {
      key id;
      max-elements 1;
      description "Models GTP-U path between RBS and another node, either SGW or neighbor RBS.\n\nThe RDN of this MO is GtpPath=1.";
      yexte:is-system-created;
      erienmyext:enm-type MOC;
      uses moc-GtpPath-keys;
      container attributes {
        description "Attributes for GtpPath";
        uses moc-GtpPath;
      } // end 'container attributes'
    } // end 'list GtpPath'
  }
  augment /erienmnrmcomtop:ManagedElement/erienmnrmlrat:ENodeBFunction {
    list QciTable {
      key id;
      max-elements 1;
      description "Contains mapping from QCIs to parameters that has impact on QoS for DRBs.\n\nThe RDN of this MO is QciTable=default.";
      yexte:is-system-created;
      erienmyext:enm-type MOC;
      uses moc-QciTable-keys;
      container attributes {
        description "Attributes for QciTable";
        uses moc-QciTable;
      } // end 'container attributes'
    } // end 'list QciTable'
  }
  augment /erienmnrmcomtop:ManagedElement/erienmnrmlrat:ENodeBFunction {
    list CellResources {
      key id;
      max-elements 1;
      description "Set of cell resource partitions defined for use in the node.\n\nThe RDN of this MO is CellResources=1.";
      status deprecated {
        yexte:status-information "Since 18.Q2. Planned to be removed.";
      }
      yexte:is-system-created;
      erienmyext:enm-type MOC;
      uses moc-CellResources-keys;
    } // end 'list CellResources'
  }
  augment /erienmnrmcomtop:ManagedElement/erienmnrmlrat:ENodeBFunction {
    list NodePerformance {
      key id;
      max-elements 1;
      description "Contains parameters related to node level performance improvement.\n\nThe RDN of this MO is NodePerformance=1.";
      yexte:is-system-created;
      erienmyext:enm-type MOC;
      uses moc-NodePerformance-keys;
    } // end 'list NodePerformance'
  }
  augment /erienmnrmcomtop:ManagedElement/erienmnrmlrat:ENodeBFunction/erienmnrmlrat:EUtranCellFDD/erienmnrmlrat:UeMeasControl {
    list ReportConfigB1Utra {
      key id;
      max-elements 1;
      description "This managed object contains report configuration settings for the B1 event for WCDMA measurements. The B1 event is used to detect when a WCDMA cell becomes better than threshold.\n\nThe RDN of this MO is ReportConfigB1Utra=1.";
      yexte:is-system-created;
      erienmyext:enm-type MOC;
      uses moc-ReportConfigB1Utra-keys;
      container attributes {
        description "Attributes for ReportConfigB1Utra";
        uses moc-ReportConfigB1Utra;
      } // end 'container attributes'
    } // end 'list ReportConfigB1Utra'
  }
  augment /erienmnrmcomtop:ManagedElement/erienmnrmlrat:ENodeBFunction/erienmnrmlrat:EUtranCellTDD/erienmnrmlrat:UeMeasControl {
    list ReportConfigB1Utra {
      key id;
      max-elements 1;
      description "This managed object contains report configuration settings for the B1 event for WCDMA measurements. The B1 event is used to detect when a WCDMA cell becomes better than threshold.\n\nThe RDN of this MO is ReportConfigB1Utra=1.";
      yexte:is-system-created;
      erienmyext:enm-type MOC;
      uses moc-ReportConfigB1Utra-keys;
      container attributes {
        description "Attributes for ReportConfigB1Utra";
        uses moc-ReportConfigB1Utra;
      } // end 'container attributes'
    } // end 'list ReportConfigB1Utra'
  }
  augment /erienmnrmcomtop:ManagedElement/erienmnrmlrat:ENodeBFunction/erienmnrmlrat:EUtranCellFDD/erienmnrmlrat:UeMeasControl {
    list ReportConfigCsg {
      key id;
      max-elements 1;
      description "Report configuration setting for A5 measurement that assists UE to redirect another EUTRA Inter-frequency. Used for feature Mobility to CSG Cells.\n\nThe RDN of this MO is ReportConfigCsg=1.";
      yexte:is-system-created;
      erienmyext:enm-type MOC;
      uses moc-ReportConfigCsg-keys;
      container attributes {
        description "Attributes for ReportConfigCsg";
        uses moc-ReportConfigCsg;
      } // end 'container attributes'
    } // end 'list ReportConfigCsg'
  }
  augment /erienmnrmcomtop:ManagedElement/erienmnrmlrat:ENodeBFunction/erienmnrmlrat:EUtranCellTDD/erienmnrmlrat:UeMeasControl {
    list ReportConfigCsg {
      key id;
      max-elements 1;
      description "Report configuration setting for A5 measurement that assists UE to redirect another EUTRA Inter-frequency. Used for feature Mobility to CSG Cells.\n\nThe RDN of this MO is ReportConfigCsg=1.";
      yexte:is-system-created;
      erienmyext:enm-type MOC;
      uses moc-ReportConfigCsg-keys;
      container attributes {
        description "Attributes for ReportConfigCsg";
        uses moc-ReportConfigCsg;
      } // end 'container attributes'
    } // end 'list ReportConfigCsg'
  }
  augment /erienmnrmcomtop:ManagedElement/erienmnrmlrat:ENodeBFunction/erienmnrmlrat:EUtranCellFDD/erienmnrmlrat:UeMeasControl {
    list ReportConfigA5UlTrig {
      key id;
      max-elements 1;
      description "Contains report configuration settings for the A5 event for inter-frequency LTE measurements initiated by Uplink-Triggered Inter-Frequency Mobility. The actual threshold values used can be adjusted by frequency relation or QCI related offsets if the feature Multi-Layer Service-Triggered Mobility (MLSTM) is enabled.\n\nThe RDN of this MO is ReportConfigA5UlTrig=1.";
      yexte:is-system-created;
      erienmyext:enm-type MOC;
      uses moc-ReportConfigA5UlTrig-keys;
      container attributes {
        description "Attributes for ReportConfigA5UlTrig";
        uses moc-ReportConfigA5UlTrig;
      } // end 'container attributes'
    } // end 'list ReportConfigA5UlTrig'
  }
  augment /erienmnrmcomtop:ManagedElement/erienmnrmlrat:ENodeBFunction/erienmnrmlrat:EUtranCellTDD/erienmnrmlrat:UeMeasControl {
    list ReportConfigA5UlTrig {
      key id;
      max-elements 1;
      description "Contains report configuration settings for the A5 event for inter-frequency LTE measurements initiated by Uplink-Triggered Inter-Frequency Mobility. The actual threshold values used can be adjusted by frequency relation or QCI related offsets if the feature Multi-Layer Service-Triggered Mobility (MLSTM) is enabled.\n\nThe RDN of this MO is ReportConfigA5UlTrig=1.";
      yexte:is-system-created;
      erienmyext:enm-type MOC;
      uses moc-ReportConfigA5UlTrig-keys;
      container attributes {
        description "Attributes for ReportConfigA5UlTrig";
        uses moc-ReportConfigA5UlTrig;
      } // end 'container attributes'
    } // end 'list ReportConfigA5UlTrig'
  }
  augment /erienmnrmcomtop:ManagedElement {
    list ENodeBFunction {
      key id;
      max-elements 1;
      description "The RDN of this MO is ENodeBFunction=1.";
      erienmyext:enm-type MOC;
      uses moc-ENodeBFunction-keys;
      container attributes {
        description "Attributes for ENodeBFunction";
        uses moc-ENodeBFunction;
      } // end 'container attributes'
    } // end 'list ENodeBFunction'
  }
  augment /erienmnrmcomtop:ManagedElement/erienmnrmlrat:ENodeBFunction {
    list TermPointToMme {
      key id;
      max-elements 64;
      description "Models the MME termination point of an S1 link between the RBS and the MME node.\n";
      erienmyext:enm-type MOC;
      uses moc-TermPointToMme-keys;
      container attributes {
        description "Attributes for TermPointToMme";
        uses moc-TermPointToMme;
      } // end 'container attributes'
    } // end 'list TermPointToMme'
  }
  augment /erienmnrmcomtop:ManagedElement/erienmnrmlrat:ENodeBFunction/erienmnrmlrat:EUtranCellFDD/erienmnrmlrat:UeMeasControl {
    list ReportConfigCsfbUtra {
      key id;
      max-elements 1;
      description "Contains report configuration settings for the B1 or B2 event for UTRA measurements, used when searching for a suitable target cell when CS Fallback is triggered for the UE.\n\nThe RDN of this MO is ReportConfigCsfbUtra=1.";
      yexte:is-system-created;
      erienmyext:enm-type MOC;
      uses moc-ReportConfigCsfbUtra-keys;
      container attributes {
        description "Attributes for ReportConfigCsfbUtra";
        uses moc-ReportConfigCsfbUtra;
      } // end 'container attributes'
    } // end 'list ReportConfigCsfbUtra'
  }
  augment /erienmnrmcomtop:ManagedElement/erienmnrmlrat:ENodeBFunction/erienmnrmlrat:EUtranCellTDD/erienmnrmlrat:UeMeasControl {
    list ReportConfigCsfbUtra {
      key id;
      max-elements 1;
      description "Contains report configuration settings for the B1 or B2 event for UTRA measurements, used when searching for a suitable target cell when CS Fallback is triggered for the UE.\n\nThe RDN of this MO is ReportConfigCsfbUtra=1.";
      yexte:is-system-created;
      erienmyext:enm-type MOC;
      uses moc-ReportConfigCsfbUtra-keys;
      container attributes {
        description "Attributes for ReportConfigCsfbUtra";
        uses moc-ReportConfigCsfbUtra;
      } // end 'container attributes'
    } // end 'list ReportConfigCsfbUtra'
  }
  augment /erienmnrmcomtop:ManagedElement/erienmnrmlrat:ENodeBFunction/erienmnrmlrat:PtmFunction {
    list PtmSubscriberGroup {
      key id;
      max-elements 12;
      description "PTM Subscriber Group that can be used in PtmCellProfile configuration. Groups can be referenced from structures IfoConfig, AtoConfig, ResOpUseConfig, and StmConfig in PtmCellProfile.";
      erienmyext:enm-type MOC;
      uses moc-PtmSubscriberGroup-keys;
      container attributes {
        description "Attributes for PtmSubscriberGroup";
        uses moc-PtmSubscriberGroup;
      } // end 'container attributes'
    } // end 'list PtmSubscriberGroup'
  }
  augment /erienmnrmcomtop:ManagedElement/erienmnrmlrat:ENodeBFunction {
    list EndcProfilePredefined {
      key id;
      max-elements 3;
      description "Predefined EN-DC profiles and EN-DC parameters that map to different QCIs.\n\nThe RDNs of these MOs are EnDcProfilePredefined=1 to EnDcProfilePredefined=3.";
      yexte:is-system-created;
      erienmyext:enm-type MOC;
      uses moc-EndcProfilePredefined-keys;
      container attributes {
        description "Attributes for EndcProfilePredefined";
        uses moc-EndcProfilePredefined;
      } // end 'container attributes'
    } // end 'list EndcProfilePredefined'
  }
  augment /erienmnrmcomtop:ManagedElement/erienmnrmlrat:ENodeBFunction {
    list AutoCellCapEstFunction {
      key id;
      max-elements 1;
      description "Parameters for Automated Cell Capacity Estimation feature.\n\nThe RDN of this MO is AutoCellCapEstFunction=1.";
      yexte:is-system-created;
      erienmyext:enm-type MOC;
      uses moc-AutoCellCapEstFunction-keys;
      container attributes {
        description "Attributes for AutoCellCapEstFunction";
        uses moc-AutoCellCapEstFunction;
      } // end 'container attributes'
    } // end 'list AutoCellCapEstFunction'
  }
  augment /erienmnrmcomtop:ManagedElement/erienmnrmlrat:ENodeBFunction/erienmnrmlrat:AnrFunction {
    list AnrFunctionUtran {
      key id;
      max-elements 1;
      description "Parameters and constraints for the UTRAN ANR functions.\n\nThe RDN of this MO is AnrFunctionUtran=1.";
      yexte:is-system-created;
      erienmyext:enm-type MOC;
      uses moc-AnrFunctionUtran-keys;
      container attributes {
        description "Attributes for AnrFunctionUtran";
        uses moc-AnrFunctionUtran;
      } // end 'container attributes'
    } // end 'list AnrFunctionUtran'
  }
  augment /erienmnrmcomtop:ManagedElement/erienmnrmlrat:ENodeBFunction/erienmnrmlrat:EUtranCellFDD {
    list Cdma20001xRttBandRelation {
      key id;
      max-elements 32;
      description "The MO represents a mobility relation between an EUtranCellFDD or an EUtranCellTDD and a Cdma20001xRTTFreqBand. It contains parameters that are specific for this relation.";
      erienmyext:enm-type MOC;
      uses moc-Cdma20001xRttBandRelation-keys;
      container attributes {
        description "Attributes for Cdma20001xRttBandRelation";
        uses moc-Cdma20001xRttBandRelation;
      } // end 'container attributes'
    } // end 'list Cdma20001xRttBandRelation'
  }
  augment /erienmnrmcomtop:ManagedElement/erienmnrmlrat:ENodeBFunction/erienmnrmlrat:EUtranCellTDD {
    list Cdma20001xRttBandRelation {
      key id;
      max-elements 32;
      description "The MO represents a mobility relation between an EUtranCellFDD or an EUtranCellTDD and a Cdma20001xRTTFreqBand. It contains parameters that are specific for this relation.";
      erienmyext:enm-type MOC;
      uses moc-Cdma20001xRttBandRelation-keys;
      container attributes {
        description "Attributes for Cdma20001xRttBandRelation";
        uses moc-Cdma20001xRttBandRelation;
      } // end 'container attributes'
    } // end 'list Cdma20001xRttBandRelation'
  }
  augment /erienmnrmcomtop:ManagedElement/erienmnrmlrat:ENodeBFunction {
    list SectorCarrier {
      key id;
      max-elements 48;
      description "This MO represents the power and frequency usage of the SectorEquipmentFunction that covers an area.";
      erienmyext:enm-type MOC;
      uses moc-SectorCarrier-keys;
      container attributes {
        description "Attributes for SectorCarrier";
        uses moc-SectorCarrier;
      } // end 'container attributes'
    } // end 'list SectorCarrier'
  }
  augment /erienmnrmcomtop:ManagedElement/erienmnrmlrat:ENodeBFunction/erienmnrmlrat:Cdma2000Network {
    list Cdma2000FreqBand {
      key id;
      max-elements 18;
      description "This Managed Object holds information on a CDMA2000 Bandclass.\n";
      erienmyext:enm-type MOC;
      uses moc-Cdma2000FreqBand-keys;
      container attributes {
        description "Attributes for Cdma2000FreqBand";
        uses moc-Cdma2000FreqBand;
      } // end 'container attributes'
    } // end 'list Cdma2000FreqBand'
  }
  augment /erienmnrmcomtop:ManagedElement/erienmnrmlrat:ENodeBFunction/erienmnrmlrat:EUtranCellFDD/erienmnrmlrat:UeMeasControl {
    list ReportConfigEUtraInterFreqMbms {
      key id;
      max-elements 1;
      description "Contains the Report Configuration settings for UE measurements initiated for EUTRA Inter-frequency MBMS Interest.\n\nThe RDN of this MO is ReportConfigEUtraInterFreqMbms=1.";
      yexte:is-system-created;
      erienmyext:enm-type MOC;
      uses moc-ReportConfigEUtraInterFreqMbms-keys;
      container attributes {
        description "Attributes for ReportConfigEUtraInterFreqMbms";
        uses moc-ReportConfigEUtraInterFreqMbms;
      } // end 'container attributes'
    } // end 'list ReportConfigEUtraInterFreqMbms'
  }
  augment /erienmnrmcomtop:ManagedElement/erienmnrmlrat:ENodeBFunction/erienmnrmlrat:EUtranCellTDD/erienmnrmlrat:UeMeasControl {
    list ReportConfigEUtraInterFreqMbms {
      key id;
      max-elements 1;
      description "Contains the Report Configuration settings for UE measurements initiated for EUTRA Inter-frequency MBMS Interest.\n\nThe RDN of this MO is ReportConfigEUtraInterFreqMbms=1.";
      yexte:is-system-created;
      erienmyext:enm-type MOC;
      uses moc-ReportConfigEUtraInterFreqMbms-keys;
      container attributes {
        description "Attributes for ReportConfigEUtraInterFreqMbms";
        uses moc-ReportConfigEUtraInterFreqMbms;
      } // end 'container attributes'
    } // end 'list ReportConfigEUtraInterFreqMbms'
  }
  augment /erienmnrmcomtop:ManagedElement/erienmnrmlrat:ENodeBFunction/erienmnrmlrat:Cdma2000Network/erienmnrmlrat:Cdma2000FreqBand {
    list Cdma2000Freq {
      key id;
      max-elements 64;
      description "This Managed Object contains information of a specific CDMA2000 frequency within a Bandclass.\n";
      erienmyext:enm-type MOC;
      uses moc-Cdma2000Freq-keys;
      container attributes {
        description "Attributes for Cdma2000Freq";
        uses moc-Cdma2000Freq;
      } // end 'container attributes'
    } // end 'list Cdma2000Freq'
  }
  augment /erienmnrmcomtop:ManagedElement/erienmnrmlrat:ENodeBFunction {
    list DrxProfile {
      key id;
      max-elements 19;
      description "DRX profiles and DRX parameters that map to different QCIs. First instance, DrxProfileId 0, is default DRX profile. Profile eMBMS VoLTE DRX (drxProfile=18) is used when DRX is combined with eMBMS and VoLTE coexistence.\n\nThe RDNs of these MOs are DrxProfile=0 to DrxProfile=18.";
      yexte:is-system-created;
      erienmyext:enm-type MOC;
      uses moc-DrxProfile-keys;
      container attributes {
        description "Attributes for DrxProfile";
        uses moc-DrxProfile;
      } // end 'container attributes'
    } // end 'list DrxProfile'
  }
  augment /erienmnrmcomtop:ManagedElement/erienmnrmlrat:ENodeBFunction {
    list LoadBalancingFunction {
      key id;
      max-elements 1;
      description "Contains parameters and constraints for Idle Mode Load Balancing feature.\n\nThe RDN of this MO is LoadBalancingFunction=1.";
      yexte:is-system-created;
      erienmyext:enm-type MOC;
      uses moc-LoadBalancingFunction-keys;
      container attributes {
        description "Attributes for LoadBalancingFunction";
        uses moc-LoadBalancingFunction;
      } // end 'container attributes'
    } // end 'list LoadBalancingFunction'
  }
  augment /erienmnrmcomtop:ManagedElement/erienmnrmlrat:ENodeBFunction/erienmnrmlrat:EUtranCellFDD {
    list Cdma2000FreqBandRelation {
      key id;
      max-elements 32;
      description "This Managed Object represents a mobility relation between an EUtranCellFDD or an EUtranCellTDD and a Cdma2000FreqBand. It contains parameters that are specific for this relation.\n\nDeleting this MO while the parent EUtranCellFDD/EUtranCellTDD has operationalState set to ENABLED is not recommended as it may affect traffic.\n";
      erienmyext:enm-type MOC;
      uses moc-Cdma2000FreqBandRelation-keys;
      container attributes {
        description "Attributes for Cdma2000FreqBandRelation";
        uses moc-Cdma2000FreqBandRelation;
      } // end 'container attributes'
    } // end 'list Cdma2000FreqBandRelation'
  }
  augment /erienmnrmcomtop:ManagedElement/erienmnrmlrat:ENodeBFunction/erienmnrmlrat:EUtranCellTDD {
    list Cdma2000FreqBandRelation {
      key id;
      max-elements 16;
      description "This Managed Object represents a mobility relation between an EUtranCellFDD or an EUtranCellTDD and a Cdma2000FreqBand. It contains parameters that are specific for this relation.\n\nDeleting this MO while the parent EUtranCellFDD/EUtranCellTDD has operationalState set to ENABLED is not recommended as it may affect traffic.\n";
      erienmyext:enm-type MOC;
      uses moc-Cdma2000FreqBandRelation-keys;
      container attributes {
        description "Attributes for Cdma2000FreqBandRelation";
        uses moc-Cdma2000FreqBandRelation;
      } // end 'container attributes'
    } // end 'list Cdma2000FreqBandRelation'
  }
  augment /erienmnrmcomtop:ManagedElement/erienmnrmlrat:ENodeBFunction/erienmnrmlrat:SubscriberProfileID {
    list HoWhiteList {
      key id;
      max-elements 1;
      description "Contains a whitelist of SPID values that are allowed to perform a  incoming handover requests when the cell is in the mode \"reserved for operator use\"";
      erienmyext:enm-type MOC;
      uses moc-HoWhiteList-keys;
      container attributes {
        description "Attributes for HoWhiteList";
        uses moc-HoWhiteList;
      } // end 'container attributes'
    } // end 'list HoWhiteList'
  }
  augment /erienmnrmcomtop:ManagedElement/erienmnrmlrat:ENodeBFunction/erienmnrmlrat:EUtraNetwork/erienmnrmlrat:ExternalENodeBFunction {
    list TermPointToENB {
      key id;
      max-elements 1;
      description "Models the local eNB termination point of an X2 link between the eNB and a neighbour eNB.\n";
      erienmyext:enm-type MOC;
      uses moc-TermPointToENB-keys;
      container attributes {
        description "Attributes for TermPointToENB";
        uses moc-TermPointToENB;
      } // end 'container attributes'
    } // end 'list TermPointToENB'
  }
  augment /erienmnrmcomtop:ManagedElement/erienmnrmlrat:ENodeBFunction {
    list AnrFunction {
      key id;
      max-elements 1;
      description "Contains parameters and constraints for ANR functions, for example, adding or removing neighbor cells.\n\nThe RDN of this MO is AnrFunction=1.";
      yexte:is-system-created;
      erienmyext:enm-type MOC;
      uses moc-AnrFunction-keys;
      container attributes {
        description "Attributes for AnrFunction";
        uses moc-AnrFunction;
      } // end 'container attributes'
    } // end 'list AnrFunction'
  }
}
