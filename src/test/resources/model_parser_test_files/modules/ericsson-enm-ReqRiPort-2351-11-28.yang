module ericsson-enm-ReqRiPort {
  yang-version 1.1;
  namespace urn:rdns:com:ericsson:ericsson-enm-ReqRiPort;
  prefix erienmnrmreqriport;
  yexte:ecim-name ReqRiPort;
  revision 2351-11-28 {
    yexte:version 6;
    yexte:release 1;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqFieldReplaceableUnit {
    prefix erienmnrmreqfieldreplaceableunit;
  }
  import ericsson-enm-ReqEquipment {
    prefix erienmnrmreqequipment;
  }
  typedef enum-AdmState {
    description "Administrative state of a resource.";
    type enumeration {
      enum LOCKED {
        description "The resource is administratively prohibited from performing services for its users.";
        value 0;
      }
      enum UNLOCKED {
        description "The resource is administratively permitted to perform services for its users.\nThis is independent of its inherent operability.";
        value 1;
      }
      enum SHUTTINGDOWN {
        description "Use of the resource is administratively permitted to existing instances of use only.\nWhile the system remains in the shutting down state the manager may at any time cause the managed object to revert to the locked state.";
        value 2;
      }
    }
  }
  typedef enum-OperState {
    description "Operational states of a resource.";
    type enumeration {
      enum DISABLED {
        description "The resource is  totally inoperable.";
        value 0;
      }
      enum ENABLED {
        description "The resource is partially or fully operable.";
        value 1;
      }
    }
  }
  typedef enum-TransmissionStandard {
    description "Transmission standard for communication between DU and RU.";
    type enumeration {
      enum CPRI {
        description CPRI.;
        value 0;
      }
      enum ETHERNET {
        description Ethernet.;
        value 1;
      }
    }
  }
  typedef enum-AvailStatus {
    description "The availability status is used to qualify the operational state.\nIt indicates why the operational state has changed its value.";
    type enumeration {
      enum IN_TEST {
        description "The resource is undergoing a test procedure.\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.\nThis routine operation is to place the resource online and make it available for use. The operation may be manual or automatic, or both.\nThe operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.\nThe semantics are defined in CCITT Rec. X.735 | ISO/IEC 10164-6.";
        value 8;
      }
      enum DEPENDENCY_LOCKED {
        description "The administrative state of a resource that this resource depends on is locked.\nAlternatively, the availability status of the other resource is dependency locked.";
        value 9;
      }
      enum DEPENDENCY_FAILED {
        description "The availability status of a resource that this resource depends on is failed or dependency failed.";
        value 10;
      }
      enum DEPENDENCY_SHUTTINGDOWN {
        description "The administrative state of a resource that this resource depends on is shutting down.\nAlternatively, the availability status of the other resource is dependency shutting down.";
        value 11;
      }
      enum DEPENDENCY_RECOVERY {
        description "Resource that this resource depends on is undergoing a recovery procedure.";
        value 12;
      }
    }
  }
  typedef ddt-ReqRiPort_SfpProductData_manufacturerId {
    type string {
      length 0..16;
    }
  }
  typedef ddt-ReqRiPort_SfpProductData_manufacturerDesignation {
    type string {
      length 0..16;
    }
  }
  typedef ddt-ReqRiPort_RiPort_preferredSfpProductNumber {
    type string {
      length 1..13;
    }
  }
  typedef ddt-MacAddressStr {
    description "MAC address string, controlled by a regular expression.
\n
\nAddress is to be specified in colon-separated hexadecimal notation as described in IEEE 802. 
\nMAC addresses must have 17 characters.
\nValid characters: 0123456789abcdefABCDEF
\nRegular expression: (^([0-9A-Fa-f]{2}:){5}[0-9A-Fa-f]{2}$)
\nExample: 00:12:34:56:78:9A";
    type string {
      length 17..17;
    }
  }
  typedef ddt-ReqRiPort_SfpProductData_productNumber {
    type string {
      length 0..13;
    }
  }
  typedef ddt-ReqRiPort_SfpProductData_serialNumber {
    type string {
      length 0..15;
    }
  }
  typedef ddt-ReqRiPort_SfpProductData_productionDate {
    type string {
      length 0..7;
    }
  }
  typedef ddt-ReqRiPort_SfpProductData_manufacturerRevision {
    type string {
      length 0..8;
    }
  }
  typedef ddt-ReqRiPort_SfpProductData_productRevision {
    type string {
      length 0..8;
    }
  }
  typedef ddt-ReqRiPort_SfpProductData_negotiatedBitRate {
    type string {
      length 0..8;
    }
  }
  grouping struct-SfpProductData {
    description "Information on the installed small form-factor pluggable (SFP) module on the Radio Interface (RI) link.";
    leaf productionDate {
      description "The production date of the SFP module.\n";
      type erienmnrmreqriport:ddt-ReqRiPort_SfpProductData_productionDate;
      mandatory true;
    }
    leaf serialNumber {
      description "The serial number of the SFP module.";
      type erienmnrmreqriport:ddt-ReqRiPort_SfpProductData_serialNumber;
      mandatory true;
    }
    leaf manufacturerRevision {
      description "The manufacturer revision of the SFP module. ";
      type erienmnrmreqriport:ddt-ReqRiPort_SfpProductData_manufacturerRevision;
      mandatory true;
    }
    leaf manufacturerId {
      description "The manufacturer ID of the SFP module. ";
      type erienmnrmreqriport:ddt-ReqRiPort_SfpProductData_manufacturerId;
      mandatory true;
    }
    leaf manufacturerDesignation {
      description "The manufacturer designation of the SFP module. ";
      type erienmnrmreqriport:ddt-ReqRiPort_SfpProductData_manufacturerDesignation;
      mandatory true;
    }
    leaf negotiatedBitRate {
      description "The maximum rate supported by the SFP module.";
      type erienmnrmreqriport:ddt-ReqRiPort_SfpProductData_negotiatedBitRate;
      mandatory true;
    }
    leaf productNumber {
      description "The product number of the SFP module.\n";
      type erienmnrmreqriport:ddt-ReqRiPort_SfpProductData_productNumber;
      mandatory true;
    }
    leaf productRevision {
      description "The product version of the SFP module. ";
      type erienmnrmreqriport:ddt-ReqRiPort_SfpProductData_productRevision;
      mandatory true;
    }
  } // end 'grouping struct-SfpProductData'
  grouping moc-RiPort-keys {
    description "Key(s) for MOC RiPort";
    leaf id {
      erienmyext:no-notification;
      description "The value component of the RDN.";
      mandatory true;
      yexte:ecim-name riPortId;
      type string;
    }
  } // end 'grouping moc-RiPort-keys'
  grouping moc-RiPort {
    description "Radio Interface (RI) Port.";
    leaf transmissionStandard {
      config false;
      description "Shows if the RiPort has come up as CPRI or Ethernet.";
      notife:notifiable-state-data true;
      type erienmnrmreqriport:enum-TransmissionStandard;
    }
    container sfpData {
      description "Information on the installed small form-factor pluggable (SFP) module on the Radio Interface (RI) link. A blank value indicates the data is currently unavailable. \n\nDeprecated since 16B.\nMoved to SfpProductData in SfpModule.";
      status deprecated {
        yexte:status-information "Since 16B";
      }
      erienmyext:enm-type STRUCT;
      uses erienmnrmreqriport:struct-SfpProductData;
    } // end 'container sfpData'
    leaf administrativeState {
      description "The administrative state. \nIf set to SHUTTINGDOWN, the state is immediately brought to LOCKED.\n";
      yexte:disturbances "Changing this attribute to LOCKED or SHUTTING_DOWN causes loss of traffic.";
      type erienmnrmreqriport:enum-AdmState;
      default UNLOCKED;
    }
    leaf sfpModuleRef {
      config false;
      description "Refers to one SfpModule on the unit to which the port is connected. ";
      notife:notifiable-state-data true;
      erienmyext:enm-type MOREF;
      type string;
    }
    leaf-list reservedBy {
      min-elements 0;
      erienmyext:no-notification;
      config false;
      description "Contains a list of MO instances that reserve this MO instance.";
      erienmyext:enm-type MOREF;
      type string;
    }
    leaf-list channelRef {
      min-elements 0;
      config false;
      description "Reference to MO SfpChannel instance connected to this port.";
      notife:notifiable-state-data true;
      erienmyext:enm-type MOREF;
      type string;
    }
    leaf-list availabilityStatus {
      min-elements 0;
      erienmyext:no-notification;
      config false;
      description "The availabilityStatus.\nIt contains details about operationalState.";
      type erienmnrmreqriport:enum-AvailStatus;
    }
    leaf operationalState {
      erienmyext:no-notification;
      config false;
      description "The operational state.";
      type erienmnrmreqriport:enum-OperState;
    }
    leaf preferredSfpProductNumber {
      description "Ericsson product number of the preferred SFP module for the RiPort.\nIf SFP with different product number detected, alarm \"SFP Product Number Mismatch\" is issued.\nThe default value, nil, means the SFP validation function is disabled.";
      type erienmnrmreqriport:ddt-ReqRiPort_RiPort_preferredSfpProductNumber;
    }
  } // end 'grouping moc-RiPort'
  grouping moc-RiEthernetPort-keys {
    description "Key(s) for MOC RiEthernetPort";
    leaf id {
      erienmyext:no-notification;
      description "The value component of the RDN.";
      mandatory true;
      yexte:ecim-name riEthernetPortId;
      type string;
    }
  } // end 'grouping moc-RiEthernetPort-keys'
  grouping moc-RiEthernetPort {
    description "Ethernet performance monitoring.\nRiEthernetPort MO is created automatically when the link starts in Ethernet mode.\n\nThe RDN of this MO is RiEthernetPort=1.";
    leaf macAddress {
      config false;
      description "MAC address for RiPort";
      notife:notifiable-state-data true;
      type erienmnrmreqriport:ddt-MacAddressStr;
    }
  } // end 'grouping moc-RiEthernetPort'
  augment /erienmnrmcomtop:ManagedElement/erienmnrmreqequipment:Equipment/erienmnrmreqfieldreplaceableunit:FieldReplaceableUnit {
    list RiPort {
      key id;
      description "Radio Interface (RI) Port.";
      erienmyext:enm-type MOC;
      uses moc-RiPort-keys;
      container attributes {
        description "Attributes for RiPort";
        uses moc-RiPort;
      } // end 'container attributes'
    } // end 'list RiPort'
  }
  augment /erienmnrmcomtop:ManagedElement/erienmnrmreqequipment:Equipment/erienmnrmreqfieldreplaceableunit:FieldReplaceableUnit/erienmnrmreqriport:RiPort {
    list RiEthernetPort {
      key id;
      max-elements 1;
      description "Ethernet performance monitoring.\nRiEthernetPort MO is created automatically when the link starts in Ethernet mode.\n\nThe RDN of this MO is RiEthernetPort=1.";
      erienmyext:enm-type MOC;
      uses moc-RiEthernetPort-keys;
      container attributes {
        description "Attributes for RiEthernetPort";
        uses moc-RiEthernetPort;
      } // end 'container attributes'
    } // end 'list RiEthernetPort'
  }
}
