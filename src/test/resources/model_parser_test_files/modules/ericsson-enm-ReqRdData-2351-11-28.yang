module ericsson-enm-ReqRdData {
  yang-version 1.1;
  namespace urn:rdns:com:ericsson:ericsson-enm-ReqRdData;
  prefix erienmnrmreqrddata;
  yexte:ecim-name ReqRdData;
  revision 2351-11-28 {
    yexte:version 1;
    yexte:release 2;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqTransceiver {
    prefix erienmnrmreqtransceiver;
  }
  import ericsson-enm-ReqFieldReplaceableUnit {
    prefix erienmnrmreqfieldreplaceableunit;
  }
  import ericsson-enm-ReqEquipment {
    prefix erienmnrmreqequipment;
  }
  typedef ddt-ReqRdData_RdData_requestedRelativeOutputPower {
    type uint32 {
      range 1..100;
    }
  }
  typedef ddt-ReqRdData_EutranCellArea_posCellBearing {
    type int32 {
      range -1..3599;
    }
  }
  typedef ddt-ReqRdData_RdData_actualRelativeOutputPower {
    type uint32 {
      range 1..100;
    }
  }
  typedef ddt-ReqRdData_EutranCellArea_posCellRadius {
    type int32 {
      range 0..100000;
    }
  }
  typedef ddt-ReqRdData_RdData_minimumRelativeOutputPower {
    type uint32 {
      range 1..100;
    }
  }
  typedef ddt-ReqRdData_EutranCellArea_posCellOpeningAngle {
    type int32 {
      range -1..3599;
    }
  }
  grouping struct-EutranCellArea {
    description "Models cell coverage area used for UE positioning. Cell coverage area is defined by cell bearing, cell opening angle and cell radius.";
    leaf posCellBearing {
      description "Cell bearing in decimal degrees clockwise from north. ";
      type erienmnrmreqrddata:ddt-ReqRdData_EutranCellArea_posCellBearing;
      default -1;
    }
    leaf posCellOpeningAngle {
      description "Opening angle of cell (3 dB beam width) in decimal degrees. \nValue 0 is used to define omnidirectional cell.";
      type erienmnrmreqrddata:ddt-ReqRdData_EutranCellArea_posCellOpeningAngle;
      default -1;
    }
    leaf posCellRadius {
      description "Cell radius in meters. ";
      type erienmnrmreqrddata:ddt-ReqRdData_EutranCellArea_posCellRadius;
      default 0;
    }
  } // end 'grouping struct-EutranCellArea'
  grouping moc-RdData-keys {
    description "Key(s) for MOC RdData";
    leaf id {
      erienmyext:no-notification;
      description "The value component of the RDN.";
      mandatory true;
      yexte:ecim-name rdDataId;
      type string;
    }
  } // end 'grouping moc-RdData-keys'
  grouping moc-RdData {
    description " This MO models Radio Dot Data (RdData).";
    leaf actualRelativeOutputPower {
      config false;
      description "Transceiver output power relative to output power set for SectorCarrier. It can differ from requested output power if another node requested it.";
      notife:notifiable-state-data true;
      type erienmnrmreqrddata:ddt-ReqRdData_RdData_actualRelativeOutputPower;
    }
    leaf minimumRelativeOutputPower {
      config false;
      description "Minimum requested relative output power that given transceiver is capable of. \n";
      notife:notifiable-state-data true;
      type erienmnrmreqrddata:ddt-ReqRdData_RdData_minimumRelativeOutputPower;
    }
    leaf requestedRelativeOutputPower {
      description "Requested transceiver output power relative to the output power set for SectorCarrier. Requested output power is rounded to closest possible value due to power setting granularity. If changes of requested relative output power are too small, they do not affect result of output power from transceiver.\n";
      yexte:disturbances "Changing this attribute can cause loss of traffic.";
      type erienmnrmreqrddata:ddt-ReqRdData_RdData_requestedRelativeOutputPower;
      default 100;
    }
    container radioDotCoverage {
      description "Coverage area used for UE positioning. Cell portion coverage is defined by bearing, opening angle and radius.\n\nThis attribute is used by Mobile Positioning System (MPS). Has no impact on traffic.";
      erienmyext:enm-type STRUCT;
      uses erienmnrmreqrddata:struct-EutranCellArea;
    } // end 'container radioDotCoverage'
  } // end 'grouping moc-RdData'
  augment /erienmnrmcomtop:ManagedElement/erienmnrmreqequipment:Equipment/erienmnrmreqfieldreplaceableunit:FieldReplaceableUnit/erienmnrmreqtransceiver:Transceiver {
    list RdData {
      key id;
      max-elements 1;
      description " This MO models Radio Dot Data (RdData).";
      erienmyext:enm-type MOC;
      uses moc-RdData-keys;
      container attributes {
        description "Attributes for RdData";
        uses moc-RdData;
      } // end 'container attributes'
    } // end 'list RdData'
  }
}
