module ericsson-enm-ComTop {
  yang-version 1.1;
  namespace urn:rdns:com:ericsson:ericsson-enm-ComTop;
  prefix erienmnrmcomtop;
  yexte:ecim-name ComTop;
  revision 2966-10-03 {
    yexte:version 10;
    yexte:release 22;
    yexte:correction 3;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  typedef enum-AdmState {
    description "The administrative state of a resource. ";
    type enumeration {
      enum LOCKED {
        description "The resource is administratively prohibited from performing services for its users.";
        value 0;
      }
      enum UNLOCKED {
        description "The resource is administratively permitted to perform services for its users.
\nThis is independent of its inherent operability.";
        value 1;
      }
      enum SHUTTINGDOWN {
        description "Use of the resource is administratively permitted to existing instances of use only.
\nWhile the system remains in the shutting down state the manager may at any time cause the managed object to revert to the locked state.";
        value 2;
      }
    }
  }
  typedef enum-OperState {
    description "The operational states of a resource.";
    type enumeration {
      enum DISABLED {
        description "  The resource is  totally inoperable.";
        value 0;
      }
      enum ENABLED {
        description "The resource partially or fully operable.";
        value 1;
      }
    }
  }
  typedef enum-BasicAdmState {
    description "The basic administrative states for a resource.";
    type enumeration {
      enum LOCKED {
        description "The resource is administratively prohibited from performing services for its users.";
        value 0;
      }
      enum UNLOCKED {
        description " The resource is administratively permitted to perform services for its users.
\nThis is independent of its inherent operability.";
        value 1;
      }
    }
  }
  typedef enum-SchemaFormat {
    description "The Schema formats of the supported data models. ";
    type enumeration {
      enum MP_DTD {
        description "The data model format is XML based on mp.dtd.";
        value 0;
      }
    }
  }
  typedef ddt-DifferenceFromUTC {
    description "Time zone difference between the local current time  and Coordinated Universal Time (UTC).\nThe format is as follows:\n[+/-]hh:mm\n\nIt is expressed as positive (that is, with the leading plus sign [+]) if the local time is ahead of or equal to UTC of day and as negative (that is, with the leading minus sign [-]) if it is behind the UTC of day.\nExample: +01:00";
    type string {
      length 6..6;
    }
  }
  typedef ddt-IpDNSAddress {
    description "The IpDNSAddress type represents an IP address or a DNS domain name.
\nA version 4 IP address is specified in dotted quad notation, for example 130.100.92.154. RFC 791 describes the syntax details.
\nA version 6 IP address is specified by 8 groups of 16 bit hexadecimal values separated by colons, for example 2001:0db8:85a3:0000:0000:8a2e:0370:7334. RFC 4291 describes the syntax details.
\nA DNS name is specified as a fully qualified domain name, for example myhost.ericsson.com. Internet domain are loosely specified but RFC 1034 recommends a syntax.";
    type string {
      length 1..253;
    }
  }
  typedef ddt-DateTimeWithoutOffset {
    description "Represents the international standard for the representation of local date and time (ISO 8601).\nThe following pattern describes the DateTimeWithoutOffset format:\nYYYY-MM-DDThh:mm:ss[.S+]\nWhere:\nYYYY    = Four digit year\nMM      = Two digit month (01=January, and so on)\nDD      = Two digit day of month (01 through 31)\nT       = Time designator (shows start of time component)\nhh      = Two digits of hour (00 through 23, AM/PM not allowed)\nmm      = Two digits of minute (00 through 59)\nss      = Two digits of second (00 through 59, leap second not allowed)\nS+      = One or more digits of decimal fraction of a second\n\nDateTimeWithoutOffset values are compliant with ISO 8601 \"Representation of dates and times\" but are restricted according to RFC 3339 \"Date and Time on the Internet: Timestamps\". The DateTimeWithoutOffset format is further restricted as follows:\n- T designator is upper case.\n- . (dot) is used to indicate start of fractions of seconds (ISO 8601 also allows comma)";
    type string {
      length 19..19;
    }
  }
  typedef ddt-DateTime {
    description "Represents the International Standard for the representation of date and time ( ISO 8601).
\nThe string format is \"YYYY-MM-DDThh:mm:ss.SSSZ\" (excluding quotes).
\nA DateTime string consists of a date part followed by a time part. When the time part represents local time, as opposed to UTC time indicated by Z as last character, an additional time offset part is added to the DateTime string.
\n
\nThe following pattern describes the DateTime format in detail:
\nYYYY-MM-DDThh:mm:ss[.S+][Z|+-hh:mm]
\nWhere:
\nYYYY = four digit year
\nMM = two digit month (01=January, etc.)
\nDD = two digit day of month (01 through 31)
\nT = time designator (shows start of time component)
\nhh = two digits of hour (00 through 23, AM/PM not allowed)
\nmm = two digits of minute (00 through 59)
\nss = two digits of second (00 through 59, leap second not allowed)
\nS+ = one or more digits of decimal fraction of a second
\nZ = time is Coordinated Universal Time (UTC)
\n+- = + or - character indicating positive or negative offset to UTC 
\n
\nDateTime values are compliant with ISO 8601 \"Representation of dates and times\" but are restricted according to RFC 3339 \"Date and Time on the Internet: Timestamps\". The DateTime format is further restricted:
\n- T and Z designators are upper case.
\n- . (dot) is used to indicate start of fractions of seconds (ISO 8601 also allows comma)";
    type string {
      length 20..31;
    }
  }
  grouping struct-ProductIdentity {
    description "Deprecated, Contains product information for a Managed Element and ManagedFunction(s).\nReplaced by ProductData.";
    leaf productDesignation {
      description "Common product name.";
      type string;
      mandatory true;
    }
    leaf productNumber {
      description "The product number in Ericsson ABC format.\nFor information, refer to Ericsson Corporate Basic Standards.";
      type string;
      mandatory true;
    }
    leaf productRevision {
      description "The product revision in the form R[1-9][A-Z].\nFor information, refer to Ericsson Corporate Basic Standards.";
      type string;
      mandatory true;
    }
  } // end 'grouping struct-ProductIdentity'
  grouping moc-Legacy-keys {
    description "Key(s) for MOC Legacy";
    leaf id {
      erienmyext:no-notification;
      description "The value component of the RDN.";
      mandatory true;
      yexte:ecim-name legacyId;
      type string;
    }
  } // end 'grouping moc-Legacy-keys'
  grouping moc-Legacy {
    description "Introduced to support deprecated types.";
    leaf dateTime {
      config false;
      description "Legacy  attribute deprecated in ECIM_Top and moved to ECIM_CommonLibrary.";
      notife:notifiable-state-data true;
      type erienmnrmcomtop:ddt-DateTime;
    }
    leaf operState {
      config false;
      description "Legacy  attribute deprecated in ECIM_Top and moved to ECIM_CommonLibrary.";
      notife:notifiable-state-data true;
      type erienmnrmcomtop:enum-OperState;
    }
    leaf ipDNSAddress {
      config false;
      description "Legacy  attribute deprecated in ECIM_Top and moved to ECIM_CommonLibrary.";
      notife:notifiable-state-data true;
      type erienmnrmcomtop:ddt-IpDNSAddress;
    }
    leaf basicAdmState {
      config false;
      description "Legacy  attribute deprecated in ECIM_Top and moved to ECIM_CommonLibrary.";
      notife:notifiable-state-data true;
      type erienmnrmcomtop:enum-BasicAdmState;
    }
    leaf schemaFormat {
      config false;
      description "Legacy  attribute deprecated in ECIM_Top and moved to ECIM_CommonLibrary.";
      notife:notifiable-state-data true;
      type erienmnrmcomtop:enum-SchemaFormat;
    }
    leaf admState {
      config false;
      description "Legacy  attribute deprecated in ECIM_Top and moved to ECIM_CommonLibrary.";
      notife:notifiable-state-data true;
      type erienmnrmcomtop:enum-AdmState;
    }
  } // end 'grouping moc-Legacy'
  grouping moc-ManagedElement-keys {
    description "Key(s) for MOC ManagedElement";
    leaf id {
      erienmyext:no-notification;
      description "Holds the name used when identifying the MO.";
      mandatory true;
      yexte:ecim-name managedElementId;
      type string;
    }
  } // end 'grouping moc-ManagedElement-keys'
  grouping moc-ManagedElement {
    description "The top-level class in the Common Information Model is Managed Element root Managed Object Class.
\nFrom this class, all model entities are contained.  The Managed Object Class (MOC) has attributes that provide information on the Managed Element Identity, primary location and the products it contains.  ";
    leaf localDateTime {
      status deprecated {
        yexte:status-information "Deprecated at version 2.3. Functionality replaced by TimeM model.";
      }
      config false;
      description "Deprecated. This is the local date and time for the Managed Element.
\nThe following format is used: YYYY-MM-DDThh:mm:ss
\n
\nThe meaning of each field is as follows:
\nYYYY = four digit year
\nMM = two digit month (01=January, etc.)
\nDD = two digit day of month (01 through 31)
\nT = time designator (shows start of time component)
\nhh = two digits of hour (00 through 23, AM/PM not allowed)
\nmm = two digits of minute (00 through 59)
\nss = two digits of second (00 through 59, leap second not allowed)
\nThe hyphen [-] and the colon [:] are used as separators within the date and time of day expressions, respectively.";
      notife:notifiable-state-data true;
      type erienmnrmcomtop:ddt-DateTimeWithoutOffset;
    }
    leaf dnPrefix {
      description "It provides naming context that allows the managed objects to be partitioned into logical domains.
\nA Distingushed Name (DN) is defined by 3GPP TS 32.300, which splits the DN into a DN Prefix and Local DN, for example DN format: dnPrefix=<DN Prefix>, localDn =<Local DN> Fault Management: dnPrefix does not impact Fault Management, since an NMS recognises a Managed Element by IP address Performance Management (PM): The dnPrefix is present in the PM Data file, Result Output Period (ROP) file, if the dnPrefix attribute is specified, that is, not an empty string. Example: DC=ericsson.se,g3SubNetwork=Sweden
\nExample: DC=ericsson.se,g3SubNetwork=Sweden
\n";
      type string;
    }
    leaf userLabel {
      description "A freetext string for additional information to assist Managed Element identification.";
      type string;
    }
    leaf locationName {
      config false;
      description "Provided for 3GPP alignment. The physical location (e.g. an address) of the Managed element.";
      notife:notifiable-state-data true;
      type string;
    }
    leaf swVersion {
      config false;
      description "Provided for 3GPP alignment. The software version of the ManagedElement.";
      notife:notifiable-state-data true;
      type string;
    }
    list productIdentity {
      min-elements 0;
      key auto-generated-struct-key;
      leaf auto-generated-struct-key {
        type uint16;
        description "This leaf has been injected to allow for struct instances in a sequence to be ordered.";
        mandatory true;
      }
      description "Contains product information for the Managed Element and its Managed Functions.
\nThis attribute is deprecated.";
      status deprecated;
      erienmyext:enm-type STRUCT;
      uses erienmnrmcomtop:struct-ProductIdentity;
    } // end 'list productIdentity'
    leaf managedElementType {
      config false;
      description "The type of product being managed.
\nFor example the type could be  RBS or CSCF.";
      notife:notifiable-state-data true;
      type string;
    }
    leaf userDefinedState {
      description "Provided for 3GPP alignment. It may hold an Operator-supplied state in free text form.";
      type string;
    }
    leaf release {
      config false;
      description "The release of the product type specified by the attribute managedElementType. 
\nIt commonly contains the Managed Element release, for example L12.0, 13A, R1A";
      notife:notifiable-state-data true;
      type string;
    }
    leaf timeZone {
      status deprecated {
        yexte:status-information "Deprecated at version 2.3. Functionality replaced by TimeM model.";
      }
      config false;
      description "DEPRECATED. This is the timeZone in which the Managed Element resides. 
\nThe possible values for this attribute are defined in the public-domain zoneinfo or Olson database. Locations are identified by a string indicating the continent or ocean and then the name of the location, typically the largest city within the region. See http://www.iana.org/time-zones for more information. Example: Europe/Stockholm.";
      notife:notifiable-state-data true;
      type string;
    }
    leaf logicalName {
      description "Optional identifier for the managed element.
\nUsed for legacy Ericsson model compatibility towards some third-party management systems.";
      type string;
    }
    leaf vendorName {
      config false;
      description "Provided for 3GPP alignment. If set, it shall contain 'Ericsson AB'.";
      notife:notifiable-state-data true;
      type string;
    }
    leaf dateTimeOffset {
      status deprecated {
        yexte:status-information "Deprecated at version 2.3. Functionality replaced by TimeM model.";
      }
      config false;
      description "Deprecated. Difference between the value of the localDateTime attribute and UTC.";
      notife:notifiable-state-data true;
      type erienmnrmcomtop:ddt-DifferenceFromUTC;
    }
    leaf networkManagedElementId {
      description "Replaces the value component of the RDN in the COM Northbound Interface.\nThis attribute shall, if used, be set to a simple string which adheres to 3GPP MO Naming Convention . The value should be unique within the network namespace.";
      type string;
    }
    leaf siteLocation {
      description "A freetext attribute describing the geographic location of a Managed Element.
\n";
      type string;
    }
    leaf-list managedElementTypeList {
      min-elements 0;
      config false;
      description "Provided for 3GPP alignment.\nIf set, it should describe a Managed element's functionality or a combination of functionalities.";
      notife:notifiable-state-data true;
      type string;
    }
  } // end 'grouping moc-ManagedElement'
  grouping moc-Transport-keys {
    description "Key(s) for MOC Transport";
    leaf id {
      erienmyext:no-notification;
      description "Holds the name used when identifying the MO.
\n";
      mandatory true;
      yexte:ecim-name transportId;
      type string;
    }
  } // end 'grouping moc-Transport-keys'
  grouping moc-Transport {
    description "This is a container for common transport functions used within the Managed Element. 
\n
\n";
  } // end 'grouping moc-Transport'
  grouping moc-SystemFunctions-keys {
    description "Key(s) for MOC SystemFunctions";
    leaf id {
      erienmyext:no-notification;
      description "Holds the name used when identifying the MO.
\n";
      mandatory true;
      yexte:ecim-name systemFunctionsId;
      type string;
    }
  } // end 'grouping moc-SystemFunctions-keys'
  grouping moc-SystemFunctions {
    description "This model has a purpose to group the management of the system functions of the Managed Element.";
  } // end 'grouping moc-SystemFunctions'
  augment /erienmnrmcomtop:ManagedElement {
    list Legacy {
      key id;
      max-elements 1;
      description "Introduced to support deprecated types.";
      erienmyext:enm-type MOC;
      uses moc-Legacy-keys;
      container attributes {
        description "Attributes for Legacy";
        uses moc-Legacy;
      } // end 'container attributes'
    } // end 'list Legacy'
  }
  list ManagedElement {
    key id;
    min-elements 1;
    max-elements 1;
    description "The top-level class in the Common Information Model is Managed Element root Managed Object Class.
\nFrom this class, all model entities are contained.  The Managed Object Class (MOC) has attributes that provide information on the Managed Element Identity, primary location and the products it contains.  ";
    yexte:is-system-created;
    erienmyext:enm-type MOC;
    uses moc-ManagedElement-keys;
    container attributes {
      description "Attributes for ManagedElement";
      uses moc-ManagedElement;
    } // end 'container attributes'
  } // end 'list ManagedElement'
  augment /erienmnrmcomtop:ManagedElement {
    list Transport {
      key id;
      max-elements 1;
      description "This is a container for common transport functions used within the Managed Element. 
\n
\n";
      yexte:is-system-created;
      erienmyext:enm-type MOC;
      uses moc-Transport-keys;
    } // end 'list Transport'
  }
  augment /erienmnrmcomtop:ManagedElement {
    list SystemFunctions {
      key id;
      max-elements 1;
      description "This model has a purpose to group the management of the system functions of the Managed Element.";
      yexte:is-system-created;
      erienmyext:enm-type MOC;
      uses moc-SystemFunctions-keys;
    } // end 'list SystemFunctions'
  }
}
