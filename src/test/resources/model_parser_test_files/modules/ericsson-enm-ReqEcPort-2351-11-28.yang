module ericsson-enm-ReqEcPort {
  yang-version 1.1;
  namespace urn:rdns:com:ericsson:ericsson-enm-ReqEcPort;
  prefix erienmnrmreqecport;
  yexte:ecim-name ReqEcPort;
  revision 2351-11-28 {
    yexte:version 4;
    yexte:release 1;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqExternalNode {
    prefix erienmnrmreqexternalnode;
  }
  import ericsson-enm-ReqFieldReplaceableUnit {
    prefix erienmnrmreqfieldreplaceableunit;
  }
  import ericsson-enm-ReqEquipment {
    prefix erienmnrmreqequipment;
  }
  typedef enum-OperState {
    description "Operational states of a resource.";
    type enumeration {
      enum DISABLED {
        description "The resource is  totally inoperable.";
        value 0;
      }
      enum ENABLED {
        description "The resource is partially or fully operable.";
        value 1;
      }
    }
  }
  typedef enum-AvailStatus {
    description "The availability status is used to qualify the operational state.
\n It indicates why the operational state has changed its value. ";
    type enumeration {
      enum IN_TEST {
        description "The resource is undergoing a test procedure. 
\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.
\nThe semantics are defined in CCITT Rec. X.735 | ISO/IEC 10164-6. ";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef ddt-ReqEcPort_EcPort_cascadingOrder {
    type int32 {
      range 0..7;
    }
  }
  typedef ddt-RegExprHubPosition {
    description "Valid values:
\n\t\t  [Ain, A1, A2, A3, A4, A5, A6, A7, A8, Bin, B1, B2, B3, B4, B5, B6, B7, B8, A, B, C, D, E, X, Y, SAU, NA, CLU, BPA]";
    type string {
      length 1..3;
    }
  }
  grouping moc-EcPort-keys {
    description "Key(s) for MOC EcPort";
    leaf id {
      erienmyext:no-notification;
      description "The value component of the RDN.";
      mandatory true;
      yexte:ecim-name ecPortId;
      type string;
    }
  } // end 'grouping moc-EcPort-keys'
  grouping moc-EcPort {
    description "This MO represents one port in a FieldReplaceableUnit MO.
\n 
\n";
    leaf ecBusRef {
      description "The EcBus to which the EcPort is connected. 
\n";
      erienmyext:enm-type MOREF;
      type string;
    }
    leaf hubPosition {
      description "The hub port that the external node or FRU is connected to.
\n
\n\tMust be set for FieldReplaceableUnit MOs of type DU or Baseband, TCU or Baseband T, BFU, PSU, PDU, EMU, SCU, SAU, CLU, SUP and BPA.
\n\tMust be set for ExternalNode MOs on the primary node.
\n\tSystem-updated attribute to reflect actual port.
\n
\n\tIn case attribute is updated by system, the system cannot detect what kind of hub is used.
\n\tThe system will reflect hub position as if the hub is an SHU.
\n\tSee actual hub-specific lookup table to get label found on SCU or SUP.
\n
\n\tValue:
\n\tBased on label for used port on hw.
\n
\n\tValid values:
\n\tAin, A0, A1, A2, A3, A4, A5, A6, A7, A8, Bin, B0, B1, B2, B3, B4, B5, B6, B7, B8, A, B, C, D, E, X, Y, SAU, NA, CLU, BPA
\n\tNA: Might be used in existing configurations for SCU and SUP.";
      type erienmnrmreqecport:ddt-RegExprHubPosition;
    }
    leaf-list availabilityStatus {
      min-elements 0;
      config false;
      description "The availability status. It contains details about operationalState.";
      notife:notifiable-state-data true;
      type erienmnrmreqecport:enum-AvailStatus;
    }
    leaf operationalState {
      config false;
      description "The operational state.";
      notife:notifiable-state-data true;
      type erienmnrmreqecport:enum-OperState;
      default ENABLED;
    }
    leaf cascadingOrder {
      description "The cascading order when there are multiple hubs or units connected in a cascade chain.
\nThe first unit in a cascade chain has value 1.
\nIf the EC-bus isn’t connected in cascade then the value shall be set to 0 (not applicable).";
      yexte:dependencies "If the EC-bus isn’t connected in cascade then the value shall be set to 0 (not applicable).";
      type erienmnrmreqecport:ddt-ReqEcPort_EcPort_cascadingOrder;
      default 0;
    }
  } // end 'grouping moc-EcPort'
  augment /erienmnrmcomtop:ManagedElement/erienmnrmreqequipment:Equipment/erienmnrmreqfieldreplaceableunit:FieldReplaceableUnit {
    list EcPort {
      key id;
      max-elements 1;
      description "This MO represents one port in a FieldReplaceableUnit MO.
\n 
\n";
      erienmyext:enm-type MOC;
      uses moc-EcPort-keys;
      container attributes {
        description "Attributes for EcPort";
        uses moc-EcPort;
      } // end 'container attributes'
    } // end 'list EcPort'
  }
  augment /erienmnrmcomtop:ManagedElement/erienmnrmreqequipment:Equipment/erienmnrmreqexternalnode:ExternalNode {
    list EcPort {
      key id;
      description "This MO represents one port in a FieldReplaceableUnit MO.
\n 
\n";
      erienmyext:enm-type MOC;
      uses moc-EcPort-keys;
      container attributes {
        description "Attributes for EcPort";
        uses moc-EcPort;
      } // end 'container attributes'
    } // end 'list EcPort'
  }
}
