module ericsson-enm-GNBDURelationsRn {
  yang-version 1.1;
  namespace urn:rdns:com:ericsson:ericsson-enm-GNBDURelationsRn;
  prefix erienmnrmgnbdurelationsrn;
  yexte:ecim-name GNBDURelationsRn;
  revision 2351-11-28 {
    yexte:version 1;
    yexte:release 6;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
}
