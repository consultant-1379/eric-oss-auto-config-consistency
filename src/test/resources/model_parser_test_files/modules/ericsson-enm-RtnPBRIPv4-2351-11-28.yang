module ericsson-enm-RtnPBRIPv4 {
  yang-version 1.1;
  namespace urn:rdns:com:ericsson:ericsson-enm-RtnPBRIPv4;
  prefix erienmnrmrtnpbripv4;
  yexte:ecim-name RtnPBRIPv4;
  revision 2351-11-28 {
    yexte:version 1;
    yexte:release 5;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RtnL3Router {
    prefix erienmnrmrtnl3router;
  }
  typedef enum-PBRNextHopState {
    description "The reachability of the next hop router and whether the NextHop is currently the active NextHop for the routing rule. ";
    type enumeration {
      enum UNREACHABLE {
        description "The NextHop is unreachable. ";
        value 0;
      }
      enum AVAILABLE {
        description "The NextHop is reachable.  
\n
\nThe route is not active. ";
        value 1;
      }
      enum ACTIVE {
        description "The NextHop is reachable.  
\n
\nThe route is active.";
        value 2;
      }
    }
  }
  typedef ddt-DistanceValueType {
    description "Distance Value Type.";
    type int16 {
      range 1..255;
    }
  }
  typedef ddt-RtnPBRIPv4_RoutingRuleIpv4_userLabel {
    type string {
      length 1..128;
    }
  }
  typedef ddt-Ipv4UnicastAddressStr {
    description "IPv4 address string, controlled by a regular expression.
\n
\nThe address is specified in dotted-quad decimal notation in accordance with RFC791, without leading zeros.\n
\nIPv4 addresses are within the range [1-126,128-223].[0-255].[0-255].[0-255], 7-15 characters. 
\nValid characters: 0123456789.
\n
\nExample: 1.1.1.1, 1.1.255.255";
    type string;
  }
  typedef ddt-RtnPBRIPv4_RoutingPolicyIpv4_userLabel {
    type string {
      length 1..128;
    }
  }
  typedef ddt-Priority {
    description "Priority of a policy rule.

\nPriority values shall be unique amongst policy rules under the same policy.
\nRule: valid values are 0 and positive integers.
\nNote: 0 is the highest priority, larger values give lower priority.
\n
\nMaximum possible range: 0..65535";
    type uint16;
  }
  typedef ddt-Ipv4RouteAddressAndPrefixLengthStr {
    description "'Unicast IPv4 address'/'prefix length' string.
\n
\nAddress should be specified in dotted-quad decimal notation in accordance with RFC791, without leading 0s.
\nIPv4 address within range [1-126,128-223].[0-255].[0-255].[0-255], 7-15 characters. Prefix is a number 0 to 32.
\n0.0.0.0/0 default route is allowed too.
\n
\nExample: 1.1.2.2/28";
    type string;
  }
  grouping moc-RoutingPolicyIpv4-keys {
    description "Key(s) for MOC RoutingPolicyIpv4";
    leaf id {
      erienmyext:no-notification;
      description "Value component of the RDN. ";
      mandatory true;
      yexte:ecim-name routingPolicyIpv4Id;
      type string;
    }
  } // end 'grouping moc-RoutingPolicyIpv4-keys'
  grouping moc-RoutingPolicyIpv4 {
    description "Represents IPv4 routing-policy used for PBR.\n\nReferring to routing-policy from IP interface, incoming packets on that IP interface are routed according to classification configured in routing-policy.\nReferring to routing-policy from Router MO, packets generated by Router MO are routed according to classification configured in routing-policy.\nRouting policy comprises list of each policy rules, which contains set of criterions and forwarding action.\n\nDependencies:\nMax number of RoutingPolicyIpv4 MOs are 16 for all Router MOs in node.";
    leaf userLabel {
      description "Label for free use. ";
      type erienmnrmrtnpbripv4:ddt-RtnPBRIPv4_RoutingPolicyIpv4_userLabel;
    }
    leaf-list reservedBy {
      min-elements 0;
      config false;
      description "Contains a list of MO instances that reserve this MO instance.";
      notife:notifiable-state-data true;
      erienmyext:enm-type MOREF;
      type string;
    }
  } // end 'grouping moc-RoutingPolicyIpv4'
  grouping moc-NextHop-keys {
    description "Key(s) for MOC NextHop";
    leaf id {
      erienmyext:no-notification;
      description "Value component of the RDN. ";
      mandatory true;
      yexte:ecim-name nextHopId;
      type string;
    }
  } // end 'grouping moc-NextHop-keys'
  grouping moc-NextHop {
    description "Represents information about route defined by this nexthop and its parent RoutingRuleIpv4 MO. ";
    leaf address {
      description "IP address of nexthop gateway of this route. ";
      mandatory true;
      yexte:dependencies "Must not coincide with address configured on InterfaceIPv4 MO on this router.\nMust be unique under same RoutingRuleIpv4 MO.\n";
      type erienmnrmrtnpbripv4:ddt-Ipv4UnicastAddressStr;
    }
    leaf bfdMonitoring {
      description "This attribute controls whether availability of this route depends on BFD session that monitors nexthop.\nIf true, availability of this route depends on session state if a BFD session monitors nexthop.\nIf false, availability of this route does not depend on session state, even when BFD session monitors nexthop.\nFor details on how to enable BFD monitoring of nexthop, see InterfaceIPv4::bfdStaticRoutes.";
      type boolean;
      default true;
    }
    leaf nextHopState {
      erienmyext:no-notification;
      config false;
      description "Reachability of next hop router and whether NextHop MO is currently active for routing rule. ";
      type erienmnrmrtnpbripv4:enum-PBRNextHopState;
    }
    leaf adminDistance {
      description "Defines priority of this nexthop relative to other nexthops under same RoutingRuleIpv4 MO.\nTwo nexthops under same RoutingRuleIpv4 MO cannot have same adminDistance value.";
      yexte:dependencies "adminDistance must be unique under the same RoutingRuleIpv4 MO.";
      type erienmnrmrtnpbripv4:ddt-DistanceValueType;
      default 1;
    }
  } // end 'grouping moc-NextHop'
  grouping moc-RoutingRuleIpv4-keys {
    description "Key(s) for MOC RoutingRuleIpv4";
    leaf id {
      erienmyext:no-notification;
      description "Value component of the RDN. ";
      mandatory true;
      yexte:ecim-name routingRuleIpv4Id;
      type string;
    }
  } // end 'grouping moc-RoutingRuleIpv4-keys'
  grouping moc-RoutingRuleIpv4 {
    description "IPv4 Routing Rule, which contains criterions and forwarding action attributes. ";
    leaf userLabel {
      description "Label for free use. ";
      type erienmnrmrtnpbripv4:ddt-RtnPBRIPv4_RoutingRuleIpv4_userLabel;
    }
    leaf addrDst {
      erienmyext:no-notification;
      description "IPv4 destination address criterion.
\n
\nThis criterion matches the IPv4 destination address field against the criterion’s configured destination subnet address.
\n
\nThe criterion format is a dotted value/prefix length [ddd.ddd.ddd.ddd/dd]. 
\n
\nIf the value list is empty, any IP address will match this rule. ";
      type erienmnrmrtnpbripv4:ddt-Ipv4RouteAddressAndPrefixLengthStr;
    }
    leaf addrSrc {
      erienmyext:no-notification;
      description "IPv4 source address criterion.
\n
\nThis criterion matches the IPv4 source address field against the criterion’s configured source subnet address.
\n
\nThe criterion format is a dotted value/prefix length [ddd.ddd.ddd.ddd/dd]. 
\n
\nIf the value list is empty, any IP address will match this rule. ";
      type erienmnrmrtnpbripv4:ddt-Ipv4RouteAddressAndPrefixLengthStr;
    }
    leaf priority {
      description "Rule priority. 
\n
\nThe rule priority orders the rules within a Routing Policy.  The ordering is from lesser numerical value towards greater numerical value.  The priorities must be unique among rules in a given Routing Policy.";
      mandatory true;
      yexte:dependencies "priority must be unique under the same RoutingPolicyIpv4 MO.";
      type erienmnrmrtnpbripv4:ddt-Priority;
    }
  } // end 'grouping moc-RoutingRuleIpv4'
  augment /erienmnrmcomtop:ManagedElement/erienmnrmcomtop:Transport/erienmnrmrtnl3router:Router {
    list RoutingPolicyIpv4 {
      key id;
      max-elements 16;
      description "Represents IPv4 routing-policy used for PBR.\n\nReferring to routing-policy from IP interface, incoming packets on that IP interface are routed according to classification configured in routing-policy.\nReferring to routing-policy from Router MO, packets generated by Router MO are routed according to classification configured in routing-policy.\nRouting policy comprises list of each policy rules, which contains set of criterions and forwarding action.\n\nDependencies:\nMax number of RoutingPolicyIpv4 MOs are 16 for all Router MOs in node.";
      erienmyext:enm-type MOC;
      uses moc-RoutingPolicyIpv4-keys;
      container attributes {
        description "Attributes for RoutingPolicyIpv4";
        uses moc-RoutingPolicyIpv4;
      } // end 'container attributes'
    } // end 'list RoutingPolicyIpv4'
  }
  augment /erienmnrmcomtop:ManagedElement/erienmnrmcomtop:Transport/erienmnrmrtnl3router:Router/erienmnrmrtnpbripv4:RoutingPolicyIpv4/erienmnrmrtnpbripv4:RoutingRuleIpv4 {
    list NextHop {
      key id;
      max-elements 2;
      description "Represents information about route defined by this nexthop and its parent RoutingRuleIpv4 MO. ";
      erienmyext:enm-type MOC;
      uses moc-NextHop-keys;
      container attributes {
        description "Attributes for NextHop";
        uses moc-NextHop;
      } // end 'container attributes'
    } // end 'list NextHop'
  }
  augment /erienmnrmcomtop:ManagedElement/erienmnrmcomtop:Transport/erienmnrmrtnl3router:Router/erienmnrmrtnpbripv4:RoutingPolicyIpv4 {
    list RoutingRuleIpv4 {
      key id;
      max-elements 8;
      description "IPv4 Routing Rule, which contains criterions and forwarding action attributes. ";
      erienmyext:enm-type MOC;
      uses moc-RoutingRuleIpv4-keys;
      container attributes {
        description "Attributes for RoutingRuleIpv4";
        uses moc-RoutingRuleIpv4;
      } // end 'container attributes'
    } // end 'list RoutingRuleIpv4'
  }
}
