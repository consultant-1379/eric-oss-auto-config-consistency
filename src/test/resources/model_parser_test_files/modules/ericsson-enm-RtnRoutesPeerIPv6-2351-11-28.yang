module ericsson-enm-RtnRoutesPeerIPv6 {
  yang-version 1.1;
  namespace urn:rdns:com:ericsson:ericsson-enm-RtnRoutesPeerIPv6;
  prefix erienmnrmrtnroutespeeripv6;
  yexte:ecim-name RtnRoutesPeerIPv6;
  revision 2351-11-28 {
    yexte:version 1;
    yexte:release 9;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RtnL3Router {
    prefix erienmnrmrtnl3router;
  }
  typedef enum-BfdStaticRoutesInterfaceType {
    description "State of bfdStaticRoutes.";
    type enumeration {
      enum DISABLED {
        value 0;
      }
      enum ENABLED {
        value 1;
      }
    }
  }
  typedef ddt-Ipv6FqdnAddressStr {
    description "IPv6 address or fully qualified domain name.\n\nIPv6 address is specified in colon separated hexadecimal notation in accordance with RFC4291 section 2.2 items 1-3, without leading zeros.\nIPv6 address must have length range of 3-39 characters.\nValid characters: 0123456789abcdefABCDEF:\n\nExample:\nFF01::101,\n2001:DB8:0:0:8:800:200C:417A\n\nValid fully qualified domain name:\n- has maximum length 253 characters.\n- is not case-sensitive.\n- consists of one or more labels separated by dots (\".\").\n\nMinimum length of each label is one character and the maximum length is 63 characters.\nValid characters for label are:\n- letters 'a' - 'z', 'A' - 'Z', digits '0' - '9', and character '-' (hyphen).\n- first and last character in each label cannot be '-' (hyphen).\n\nExample:\nmyhost.ericsson.com\n\nIf string is valid IPv6 address, it is interpreted as IPv6 address.\nIf string is not valid IPv6 address, it is interpreted as fully qualified domain name.";
    type string {
      length 1..253;
    }
  }
  grouping moc-PeerIPv6-keys {
    description "Key(s) for MOC PeerIPv6";
    leaf id {
      erienmyext:no-notification;
      description "The value component of the RDN.";
      mandatory true;
      yexte:ecim-name peerIPv6Id;
      type string;
    }
  } // end 'grouping moc-PeerIPv6-keys'
  grouping moc-PeerIPv6 {
    description "Provides IPv6 peer information.";
    leaf address {
      description "IPv6 address or fully qualified domain name of peer. ";
      mandatory true;
      yexte:disturbances "Changing this attribute causes traffic disturbances.";
      yexte:dependencies "Must not coincide with address configured on AddressIPv6 MO in this Router MO.\nMust be unique among all PeerIPv6 MO addresses within same Router MO.\nMust be IPv6 address, if this MO is referred by DhcpRelayIPv6 MO.\nDomain name is only possible for IPsec.\nNeeds to be in connected subnet in order for BFD session to be setup.\nNo BFD session is setup if domain name is used.\nIf domain name is used, DnsClient MO must be configured in same Router MO.\nIf domain name is resolved to multiple IPv6 addresses, detection of unreachable peer is delayed.";
      type erienmnrmrtnroutespeeripv6:ddt-Ipv6FqdnAddressStr;
    }
    leaf bfdProfile {
      description "A reference to BfdProfile MO containing BFD parameters used for BFD sessions towards this IP peer.";
      yexte:dependencies "The referred BfdProfile MO must belong to Transport MO or same Router MO.";
      erienmyext:enm-type MOREF;
      type string;
    }
    leaf bfdStaticRoutes {
      description "Enables/disables BFD monitoring of static routes with this peer as netxthop.\nIf this attribute is set to ENABLED, BFD monitoring is enabled for static routes where the address of the NextHop MO is equal to the address of this PeerIPv6 MO.\nIf bfdProfile is set on this MO, the BFD session uses parameters configured in the referred BfdProfile MO. \nIf bfdProfile is not set on this MO, the BFD session uses parameters configured in the BfdProfile MO referred from the InterfaceIPv6 MO bfdProfile attribute.\nIf bfdProfile is not set on this MO neither the InterfaceIPv6 MO, BFD monitoring is not enabled. \nIf this attribute is set to DISABLED, BFD monitoring is disabled for static routes where the address of the NextHop MO is equal to the address of this PeerIPv6 MO. This overrides the bfdStaticRoutes attribute on InterfaceIPv6 MO.\nIf this attribute is not set, BFD monitoring can still be enabled towards this peer by setting the bfdStaticRoutes attribute to ENABLED on InterfaceIPv6 MO. The bfdProfile on this PeerIPv6 MO is in this case not used.\nIf BFD monitoring is enabled, all static routes with this peer as nexthop are monitored, unless explicitly disabled per NextHop MO.";
      yexte:disturbances "Changing this attribute causes traffic disturbances.";
      type erienmnrmrtnroutespeeripv6:enum-BfdStaticRoutesInterfaceType;
    }
    leaf-list reservedBy {
      min-elements 0;
      config false;
      description "Contains a list of MO instances that reserve this MO instance.";
      notife:notifiable-state-data true;
      erienmyext:enm-type MOREF;
      type string;
    }
  } // end 'grouping moc-PeerIPv6'
  augment /erienmnrmcomtop:ManagedElement/erienmnrmcomtop:Transport/erienmnrmrtnl3router:Router {
    list PeerIPv6 {
      key id;
      description "Provides IPv6 peer information.";
      erienmyext:enm-type MOC;
      uses moc-PeerIPv6-keys;
      container attributes {
        description "Attributes for PeerIPv6";
        uses moc-PeerIPv6;
      } // end 'container attributes'
    } // end 'list PeerIPv6'
  }
}
