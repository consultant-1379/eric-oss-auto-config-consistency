module ericsson-enm-RtnPeerIpsecProfile {
  yang-version 1.1;
  namespace urn:rdns:com:ericsson:ericsson-enm-RtnPeerIpsecProfile;
  prefix erienmnrmrtnpeeripsecprofile;
  yexte:ecim-name RtnPeerIpsecProfile;
  revision 2351-11-28 {
    yexte:version 1;
    yexte:release 7;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RtnL3Router {
    prefix erienmnrmrtnl3router;
  }
  typedef ddt-RtnPeerIpsecProfile_PeerIpsecProfile_userLabel {
    type string {
      length 1..128;
    }
  }
  grouping moc-PeerIpsecProfile-keys {
    description "Key(s) for MOC PeerIpsecProfile";
    leaf id {
      erienmyext:no-notification;
      description "The value component of the RDN.";
      mandatory true;
      yexte:ecim-name peerIpsecProfileId;
      type string;
    }
  } // end 'grouping moc-PeerIpsecProfile-keys'
  grouping moc-PeerIpsecProfile {
    description "Enables node to automatically setup direct IPsec VPN connections to other RBS based on X2 or Xn neighbor information in node.\nInformation for IKE and Child SA negotiation for direct IPsec VPN connections by referring to Ikev2PolicyProfile MO and IpsecProposalProfile MO.\nPeerIpsecProfile MO must be configured in Router MO where AddressIPv4 MO or AddressIPv6 MO used for X2 or Xn is configured.";
    leaf userLabel {
      description "Label for free use.";
      type erienmnrmrtnpeeripsecprofile:ddt-RtnPeerIpsecProfile_PeerIpsecProfile_userLabel;
    }
    leaf antiReplayProtection {
      description "Enable or disable anti-replay protection.";
      yexte:disturbances "Changing this attribute causes traffic disturbances.";
      type boolean;
      default true;
    }
    leaf ipsecProposalProfile {
      description "Reference to IpsecProposalProfile MO.";
      mandatory true;
      yexte:disturbances "Changing this attribute causes traffic disturbances.";
      yexte:dependencies "Referenced IpsecProposalProfile MO must be configured with datalimit in childSaLifetime attribute set to nil, and attribute pfs must not be set to true.\nReferenced IpsecProposalProfile MO must not be configured with pfs attribute set to true.";
      erienmyext:enm-type MOREF;
      type string;
    }
    leaf ikev2PolicyProfile {
      description "Reference to Ikev2PolicyProfile MO.";
      mandatory true;
      yexte:disturbances "Changing this attribute causes traffic disturbances.";
      yexte:dependencies "Referenced Ikev2PolicyProfile MO must be configured for certificate based authentication with attributes credential and trustCategory set.";
      erienmyext:enm-type MOREF;
      type string;
    }
  } // end 'grouping moc-PeerIpsecProfile'
  augment /erienmnrmcomtop:ManagedElement/erienmnrmcomtop:Transport/erienmnrmrtnl3router:Router {
    list PeerIpsecProfile {
      key id;
      max-elements 1;
      description "Enables node to automatically setup direct IPsec VPN connections to other RBS based on X2 or Xn neighbor information in node.\nInformation for IKE and Child SA negotiation for direct IPsec VPN connections by referring to Ikev2PolicyProfile MO and IpsecProposalProfile MO.\nPeerIpsecProfile MO must be configured in Router MO where AddressIPv4 MO or AddressIPv6 MO used for X2 or Xn is configured.";
      erienmyext:enm-type MOC;
      uses moc-PeerIpsecProfile-keys;
      container attributes {
        description "Attributes for PeerIpsecProfile";
        uses moc-PeerIpsecProfile;
      } // end 'container attributes'
    } // end 'list PeerIpsecProfile'
  }
}
