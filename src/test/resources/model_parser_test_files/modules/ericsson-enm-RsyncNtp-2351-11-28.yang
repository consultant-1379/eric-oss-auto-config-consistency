module ericsson-enm-RsyncNtp {
  yang-version 1.1;
  namespace urn:rdns:com:ericsson:ericsson-enm-RsyncNtp;
  prefix erienmnrmrsyncntp;
  yexte:ecim-name RsyncNtp;
  revision 2351-11-28 {
    yexte:version 3;
    yexte:release 0;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef enum-OperState {
    description "The operational states of a resource.";
    type enumeration {
      enum DISABLED {
        description " The resource is  totally inoperable.";
        value 0;
      }
      enum ENABLED {
        description " The resource is partially or fully operable.";
        value 1;
      }
    }
  }
  typedef enum-AvailStatus {
    description "The availability status is used to qualify the operational state.
\n It indicates why the operational state has changed its value. ";
    type enumeration {
      enum IN_TEST {
        description "The resource is undergoing a test procedure. 
\nIf the administrative state is locked or  shutting down then normal users are precluded from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "This indicates a log full condition.";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef enum-NtpFrequencySyncStatus {
    description "NTP frequency synchronization status.";
    type enumeration {
      enum UNKNOWN {
        description "No status information available.";
        value 0;
      }
      enum NO_FAULT {
        description "No defect detected.";
        value 1;
      }
      enum PDV_PROBLEM {
        description "High Packet Delay Variation (PDV) detected.";
        value 2;
      }
      enum UNREACHABLE_REFERENCE {
        description "NTP server unreachable.";
        value 3;
      }
      enum HIGH_PACKET_DROP {
        description "NTP packet drop detected.";
        value 4;
      }
      enum LOW_STRATUM {
        description "NTP server indicates that its quality is unreliable.";
        value 5;
      }
      enum LI_ERROR {
        description "NTP server indicates that its quality is unreliable.";
        value 6;
      }
      enum QL_TOO_LOW {
        description "adminQL/minQL configuration gives too low QL for synchronization.";
        status deprecated;
        value 7;
      }
      enum UNRESOLVED_SERVER_ADDRESS {
        value 8;
      }
    }
  }
  typedef ddt-RsyncNtp_NtpFrequencySync_syncServerNtpIpAddress {
    type string;
  }
  typedef ddt-RsyncNtp_NtpFrequencySync_dscp {
    type uint8 {
      range 0..63;
    }
  }
  grouping moc-Ntp-keys {
    description "Key(s) for MOC Ntp";
    leaf id {
      erienmyext:no-notification;
      description "The value component of the RDN.";
      mandatory true;
      yexte:ecim-name ntpId;
      type string;
    }
  } // end 'grouping moc-Ntp-keys'
  grouping moc-Ntp {
    description "This MO class is the top class for NTP management.";
  } // end 'grouping moc-Ntp'
  grouping moc-NtpFrequencySync-keys {
    description "Key(s) for MOC NtpFrequencySync";
    leaf id {
      erienmyext:no-notification;
      description "The value component of the RDN.";
      mandatory true;
      yexte:ecim-name ntpFrequencySyncId;
      type string;
    }
  } // end 'grouping moc-NtpFrequencySync-keys'
  grouping moc-NtpFrequencySync {
    description "This MO class models a NTP frequency reference used for Network Synchronization.\nThe addressIPv4Reference attribute is the reference to the source IPv4 address to be used in NTP protocol exchange with NTP server.";
    leaf addressIPv4Reference {
      description "Specifies a reference to an AddressIPv4 MO.\nThe IP address of the referenced AddressIPv4 MO will be the source IPv4 address to be used in NTP protocol exchange with the NTP server.";
      mandatory true;
      erienmyext:enm-type MOREF;
      type string;
    }
    leaf-list ntpFrequencySyncStatus {
      min-elements 1;
      max-elements 6;
      erienmyext:no-notification;
      config false;
      description "Indicates the detailed fault status of the NTP frequency synchronization reference.";
      type erienmnrmrsyncntp:enum-NtpFrequencySyncStatus;
    }
    leaf dscp {
      description "The DSCP value used for SNTP/UDP/IP transmitted packets.";
      type erienmnrmrsyncntp:ddt-RsyncNtp_NtpFrequencySync_dscp;
      default 54;
    }
    leaf cachedIpAddress {
      erienmyext:no-notification;
      config false;
      description "The IPv4 address of the NTP  server obtained from a DNS.";
      type string;
    }
    leaf ingressUdpPort {
      erienmyext:no-notification;
      config false;
      description "The ingress UDP port number used by the NTP frequency synchronization reference.";
      type string;
    }
    leaf-list reservedBy {
      min-elements 0;
      config false;
      description "Contains a list of MO instances that reserve this MO instance.";
      notife:notifiable-state-data true;
      erienmyext:enm-type MOREF;
      type string;
    }
    leaf syncServerNtpIpAddress {
      description "The IPv4 address or domain name of the NTP server.";
      mandatory true;
      type erienmnrmrsyncntp:ddt-RsyncNtp_NtpFrequencySync_syncServerNtpIpAddress;
    }
    leaf-list availabilityStatus {
      min-elements 0;
      erienmyext:no-notification;
      config false;
      description "The availability status.\nIt contains details about operationalState.";
      type erienmnrmrsyncntp:enum-AvailStatus;
    }
    leaf operationalState {
      erienmyext:no-notification;
      config false;
      description "The operational state.";
      type erienmnrmrsyncntp:enum-OperState;
    }
  } // end 'grouping moc-NtpFrequencySync'
  augment /erienmnrmcomtop:ManagedElement/erienmnrmcomtop:Transport {
    list Ntp {
      key id;
      max-elements 1;
      description "This MO class is the top class for NTP management.";
      erienmyext:enm-type MOC;
      uses moc-Ntp-keys;
    } // end 'list Ntp'
  }
  augment /erienmnrmcomtop:ManagedElement/erienmnrmcomtop:Transport/erienmnrmrsyncntp:Ntp {
    list NtpFrequencySync {
      key id;
      max-elements 8;
      description "This MO class models a NTP frequency reference used for Network Synchronization.\nThe addressIPv4Reference attribute is the reference to the source IPv4 address to be used in NTP protocol exchange with NTP server.";
      erienmyext:enm-type MOC;
      uses moc-NtpFrequencySync-keys;
      container attributes {
        description "Attributes for NtpFrequencySync";
        uses moc-NtpFrequencySync;
      } // end 'container attributes'
    } // end 'list NtpFrequencySync'
  }
}
