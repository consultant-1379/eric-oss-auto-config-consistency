module ericsson-enm-GNBCUCP {
  yang-version 1.1;
  namespace urn:rdns:com:ericsson:ericsson-enm-GNBCUCP;
  prefix erienmnrmgnbcucp;
  yexte:ecim-name GNBCUCP;
  revision 2351-11-28 {
    yexte:version 18;
    yexte:release 2;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef enum-InitialUplinkConf {
    description "Initial uplink configurations enum.";
    type enumeration {
      enum MCG {
        description "PDCP uplink data PDU to the configured RLC entity in MCG at initial state.";
        value 0;
      }
      enum SCG {
        description "PDCP uplink data PDU to the configured RLC entity in SCG at initial state.";
        value 1;
      }
    }
  }
  typedef enum-NRCellState {
    description "Cell states.";
    type enumeration {
      enum IDLE {
        description "The resource is not currently in use.";
        value 0;
      }
      enum INACTIVE {
        description "The cell is known by both the gNodeB-DU and the gNodeB-CU-CP.\n\nThe cell shall not serve UEs.";
        value 1;
      }
      enum ACTIVE {
        description "The cell is known by both the gNodeB-DU and the gNodeB-CU-CP.\n\nThe cell should try to provide service to the UEs.";
        value 2;
      }
    }
  }
  typedef enum-AdmState {
    description "Administrative state of a resource.";
    type enumeration {
      enum LOCKED {
        description "The resource is administratively prohibited from performing services for its users.";
        value 0;
      }
      enum UNLOCKED {
        description "The resource is administratively permitted to perform services for its users.\nThis is independent of its inherent operability.";
        value 1;
      }
      enum SHUTTINGDOWN {
        description "Use of the resource is administratively permitted to existing instances of use only.\nWhile the system remains in the shutting down state the manager may at any time cause the managed object to revert to the locked state.";
        value 2;
      }
    }
  }
  typedef enum-OperState {
    description "Operational states of a resource.";
    type enumeration {
      enum DISABLED {
        description "The resource is  totally inoperable.";
        value 0;
      }
      enum ENABLED {
        description "The resource is partially or fully operable.";
        value 1;
      }
    }
  }
  typedef enum-PmUeReportType {
    description "Report type selected for PM purpose.";
    type enumeration {
      enum PERIODICAL {
        description "Periodical measurement report.";
        value 0;
      }
      enum EVENT_A2 {
        description "Event A2 measurement report.";
        value 1;
      }
      enum EVENT_A3 {
        description "Event A3 measurement report.";
        value 2;
      }
    }
  }
  typedef enum-NRCellServiceState {
    description "Cell service state.";
    type enumeration {
      enum OUT_OF_SERVICE {
        description "Cell is not operational and cannot serve UE instances.\n\nThe gNodeB Distributed Unit (gNodeB-DU) is trying to make cell operational.";
        value 0;
      }
      enum IN_SERVICE {
        description "Cell is operational and can serve UE instances.";
        value 1;
      }
    }
  }
  typedef enum-EpsFbOperationTypeEm {
    description "EPS fallback operation for emergency calls.";
    type enumeration {
      enum ACTIVE {
        description "Use Release with Redirection EPS fallback without measurement for emergency call.\n\nApplied for UE and RAN not supporting emergency call over NR.";
        value 0;
      }
      enum FORCED {
        description "Use Release with Redirection EPS fallback without measurement for emergency call.";
        value 1;
      }
      enum ACTIVE_MEAS_RWR {
        description "Use measurement-based Release with Redirection EPS fallback for emergency call.\n\nApplied for UE and RAN not supporting emergency call over NR.";
        value 2;
      }
      enum ACTIVE_MEAS_IRAT_HO {
        description "Use measurement-based Inter-RAT handover EPS fallback for emergency call.\n\nApplied for UE and RAN not supporting emergency call over NR.";
        value 3;
      }
      enum FORCED_MEAS_RWR {
        description "Use measurement-based Release with Redirection EPS fallback for emergency call.";
        value 4;
      }
      enum FORCED_MEAS_IRAT_HO {
        description "Use Measurement-based Inter-RAT handover EPS fallback for emergency call.";
        value 5;
      }
    }
  }
  typedef enum-CaStatus {
    description "Service Status of carrier aggregation.";
    type enumeration {
      enum DISABLED {
        description "The resource is totally inoperable.";
        status obsolete {
          yexte:status-information "Since 20.Q3. Planned to be removed.";
        }
        value 0;
      }
      enum ENABLED {
        description "The resource is partially or fully operable.";
        status obsolete {
          yexte:status-information "Since 20.Q3. Planned to be removed.";
        }
        value 1;
      }
    }
  }
  typedef enum-CreatedByGutran {
    description "Identifies MO creation.";
    type enumeration {
      enum ANR {
        description "Created by ANR.";
        value 0;
      }
      enum X2 {
        description "Created by X2.";
        value 1;
      }
      enum OPERATOR {
        description "Created by operator.";
        value 2;
      }
    }
  }
  typedef enum-ServiceType {
    description "Service type.";
    type enumeration {
      enum UNDEFINED {
        description "No service defined.";
        status current {
          yexte:preliminary;
        }
        value 0;
      }
      enum VOIP {
        description "Service type is VOIP.";
        status current {
          yexte:preliminary;
        }
        value 1;
      }
      enum IMS_SIGNALING {
        description "Service type is IMS signaling.";
        status current {
          yexte:preliminary;
        }
        value 2;
      }
      enum PTT {
        description "Mission-Critical and non-Mission-Critical Push-to-Talk.";
        status current {
          yexte:preliminary;
        }
        value 3;
      }
      enum MC_SIGNALING {
        description "Mission-Critical delay-sensitive signaling.";
        status current {
          yexte:preliminary;
        }
        value 4;
      }
    }
  }
  typedef enum-ReportInterval {
    description "Interval between periodical reports.";
    type enumeration {
      enum MS_120 {
        description "120 ms interval.";
        value 0;
      }
      enum MS_240 {
        description "240 ms interval.";
        value 1;
      }
      enum MS_480 {
        description "480 ms interval.";
        value 2;
      }
      enum MS_640 {
        description "640 ms interval.";
        value 3;
      }
      enum MS_1024 {
        description "1024 ms interval.";
        value 4;
      }
      enum MS_2048 {
        description "2048 ms interval.";
        value 5;
      }
      enum MS_5120 {
        description "5120 ms interval.";
        value 6;
      }
      enum MS_10240 {
        description "10240 ms interval.";
        value 7;
      }
      enum MS_20480 {
        description "20480 ms interval.";
        value 8;
      }
      enum MS_40960 {
        description "40960 ms interval.";
        value 9;
      }
      enum MIN_1 {
        description "1 minute.";
        value 10;
      }
      enum MIN_6 {
        description "6 minutes.";
        value 11;
      }
      enum MIN_12 {
        description "12 minutes.";
        value 12;
      }
      enum MIN_30 {
        description "30 minutes.";
        value 13;
      }
    }
  }
  typedef enum-NRCellServiceStatus {
    description "Cell service status.";
    type enumeration {
      enum OUT_OF_SERVICE {
        description "The cell is not operational, and it is not able to serve UEs.\n\nThe gNodeB-DU is trying to make the cell operational.";
        status deprecated {
          yexte:status-information "Since 20.Q1. Planned to be removed.";
        }
        value 0;
      }
      enum IN_SERVICE {
        description "The cell is operational and able to serve UEs.";
        status deprecated {
          yexte:status-information "Since 20.Q1. Planned to be removed.";
        }
        value 1;
      }
    }
  }
  typedef enum-InterfaceName {
    description "RAN interfaces.";
    type enumeration {
      enum C5 {
        description "C5 for user plane.";
        value 0;
      }
      enum E1 {
        description "E1 for control and user plane.";
        value 1;
      }
      enum E6 {
        description "E6 for control plane.";
        value 2;
      }
      enum F1 {
        description "F1 for control and user plane.";
        value 3;
      }
      enum NG {
        description "NG for control and user plane.";
        value 4;
      }
      enum S1 {
        description "S1 for user plane.";
        value 5;
      }
      enum XN {
        description "Xn for control and user plane.";
        value 6;
      }
      enum X2 {
        description "X2 for control and user plane.";
        value 7;
      }
    }
  }
  typedef enum-EndcMobilityAction {
    description "Intra-frequency handover evaluation fails to select a target NR cell or SN change procedure fails.";
    type enumeration {
      enum RELEASE {
        description "SN initiated SN Release is triggered.";
        value 0;
      }
      enum IGNORE {
        description "No action is taken.";
        value 1;
      }
    }
  }
  typedef enum-PWSRestartHandling {
    description "Whether PWS restart handling is supported.";
    type enumeration {
      enum DISABLED {
        description "PWS restart and failure messages cannot be sent to AMF.";
        value 0;
      }
      enum ENABLED {
        description "PWS restart and failure messages can be sent to AMF.";
        value 1;
      }
    }
  }
  typedef enum-EpsFallbackOperationType {
    description "EPS fallback operation.";
    type enumeration {
      enum INACTIVE {
        description "Always use Voice over NR (VoNR).";
        value 0;
      }
      enum ACTIVE {
        description "Use Release with Redirection EPS fallback without measurement.\n\nApplied for UE not supporting Voice over NR (VoNR).";
        value 1;
      }
      enum FORCED {
        description "Use EPS fallback with Release with Redirection without measurement.";
        value 2;
      }
      enum ACTIVE_MEAS_RWR {
        description "Use measurement-based Release with Redirection EPS fallback.\n\nApplied for UE not supporting Voice over NR (VoNR).";
        value 3;
      }
      enum ACTIVE_MEAS_IRAT_HO {
        description "Use measurement-based Inter-RAT handover EPS fallback.\n\nApplied for UE not supporting Voice over NR (VoNR).";
        value 4;
      }
      enum FORCED_MEAS_RWR {
        description "Use measurement-based Release with Redirection EPS fallback.";
        value 5;
      }
      enum FORCED_MEAS_IRAT_HO {
        description "Use Measurement-based Inter-RAT handover EPS fallback.";
        value 6;
      }
    }
  }
  typedef enum-CipheringAlgorithmID {
    description "Ciphering algorithms enum.";
    type enumeration {
      enum NEA0 {
        description "No ciphering is applied.";
        value 0;
      }
      enum NEA1 {
        description "128-NEA1 (based on SNOW 3G).";
        value 1;
      }
      enum NEA2 {
        description "128-NEA2 (based on AES).";
        value 2;
      }
      enum NEA3 {
        description "128-NEA3 (based on ZUC).";
        value 3;
      }
    }
  }
  typedef enum-AvailStatus {
    description "The availability status is used to qualify the operational state.\nIt indicates why the operational state has changed its value.";
    type enumeration {
      enum IN_TEST {
        description "The resource is undergoing a test procedure.\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.\nThis routine operation is to place the resource online and make it available for use. The operation may be manual or automatic, or both.\nThe operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.\nThe semantics are defined in CCITT Rec. X.735 | ISO/IEC 10164-6.";
        value 8;
      }
      enum DEPENDENCY_LOCKED {
        description "The administrative state of a resource that this resource depends on is locked.\nAlternatively, the availability status of the other resource is dependency locked.";
        value 9;
      }
      enum DEPENDENCY_FAILED {
        description "The availability status of a resource that this resource depends on is failed or dependency failed.";
        value 10;
      }
      enum DEPENDENCY_SHUTTINGDOWN {
        description "The administrative state of a resource that this resource depends on is shutting down.\nAlternatively, the availability status of the other resource is dependency shutting down.";
        value 11;
      }
      enum DEPENDENCY_RECOVERY {
        description "Resource that this resource depends on is undergoing a recovery procedure.";
        value 12;
      }
      enum DEPENDENCY_HOLDING {
        description "Resource cannot operate because some other resource on which it depends is currently unavailable.\nThe situation is expected to be resolved. Actions to facilitate dependency resolution may be ongoing.";
        value 13;
      }
    }
  }
  typedef enum-ResourceType {
    description "Resource type of the Quality of Service indicator (5QI).";
    type enumeration {
      enum NON_GBR {
        description "5QI resource type is Non-GBR.";
        status current {
          yexte:preliminary;
        }
        value 0;
      }
      enum GBR {
        description "5QI resource type is GBR.";
        status current {
          yexte:preliminary;
        }
        value 1;
      }
      enum DC_GBR {
        description "5QI resource type is Delay-Critical GBR.";
        status current {
          yexte:preliminary;
        }
        value 2;
      }
    }
  }
  typedef enum-SCellCandidate {
    description "SCell candidate status.";
    type enumeration {
      enum NOT_ALLOWED {
        description "Not allowed as SCell candidate.";
        value 0;
      }
      enum ALLOWED {
        description "Allowed as SCell candidate.";
        value 1;
      }
    }
  }
  typedef enum-CaStatusCause {
    description "Additional status information when caStatusActive is false.";
    type enumeration {
      enum E5_TUNNEL_CAP {
        description "E5 tunnel capacity is reached.";
        value 0;
      }
      enum E5_TUNNEL_CAP_REMOTE {
        description "E5 tunnel capacity is reached on remote host.";
        value 1;
      }
      enum E5_CELL_ALLOC_CAP {
        description "E5 cell allocation capacity is reached.";
        value 2;
      }
      enum E5_CELL_ALLOC_CAP_REMOTE {
        description "E5 cell allocation capacity is reached on remote host.";
        value 3;
      }
    }
  }
  typedef enum-ReportAmount {
    description "Number of periodical or event-triggered measurement reports.";
    type enumeration {
      enum R1 {
        description "One report.";
        value 0;
      }
      enum R2 {
        description "Two reports.";
        value 1;
      }
      enum R4 {
        description "Four reports.";
        value 2;
      }
      enum R8 {
        description "Eight reports.";
        value 3;
      }
      enum R16 {
        description "16 reports.";
        value 4;
      }
      enum R32 {
        description "32 reports.";
        value 5;
      }
      enum R64 {
        description "64 reports.";
        value 6;
      }
      enum INFINITY {
        description "Infinite number of reports.";
        value 7;
      }
    }
  }
  typedef enum-CreatedByNR {
    description "Identifies MO creation.";
    type enumeration {
      enum XN {
        description "Created by Xn.";
        value 0;
      }
      enum OPERATOR {
        description "Created by operator.";
        value 1;
      }
    }
  }
  typedef enum-RlcMode {
    description "RLC mode.";
    type enumeration {
      enum AM {
        description "RLC mode is AM.";
        status current {
          yexte:preliminary;
        }
        value 0;
      }
      enum UM {
        description "RLC mode is UM Bidirectional.";
        status current {
          yexte:preliminary;
        }
        value 1;
      }
    }
  }
  typedef enum-McpcQuantity {
    description "Measurement quantity applicable for MCPC function.";
    type enumeration {
      enum RSRP {
        description "Reference signal received power.";
        value 0;
      }
    }
  }
  typedef enum-IntegrityAlgorithmID {
    description "Integrity algorithms enum.";
    type enumeration {
      enum NIA1 {
        description "128-NIA1 SNOW 3G based algorithm.";
        value 1;
      }
      enum NIA2 {
        description "128-NIA2 AES based algorithm.";
        value 2;
      }
      enum NIA3 {
        description "128-NIA3 ZUC based algorithm.";
        value 3;
      }
    }
  }
  typedef enum-TriggerQuantity {
    description "The measurement quantity that triggers a measurement event.";
    type enumeration {
      enum RSRP {
        description "RSRP (Reference Signal Received Power) is used.";
        value 0;
      }
      enum RSRQ {
        description "RSRQ (Reference Signal Received Quality) is used.";
        value 1;
      }
    }
  }
  typedef enum-MsgRedOptions {
    description "Measurement configuration options in single RRCReconfiguration messages in NR SA deployment.";
    type enumeration {
      enum NO_MSG_RED {
        description "No message size reduction.\n\nSCells and measurement configuration are included in one single RRCReconfiguration message.";
        status current {
          yexte:preliminary;
        }
        value 0;
      }
      enum HO_ESS_MSG_RED_LEVEL1 {
        description "SCells and measurement configuration are sent in subsequent RRCReconfiguration message.\n\nApplies to handover at poor coverage and initial context setup in ESS cell.";
        status current {
          yexte:preliminary;
        }
        value 1;
      }
    }
  }
  typedef enum-SupportedCoverage {
    description "Coverage relation.";
    type enumeration {
      enum NONE {
        description "No coverage relation between cells.";
        value 0;
      }
      enum COVERS {
        description "Related cell covers current cell.";
        value 1;
      }
      enum OVERLAP {
        description "Related cell and current cell has approximately the same coverage area.";
        value 2;
      }
      enum CONTAINED_IN {
        description "Related cell is contained in current cell.";
        value 3;
      }
    }
  }
  typedef enum-IntraFreqMCCellProfileUsage {
    description "IntraFreqMCCellProfile MO class usage in relation to the deprecated MO class ReportConfigA3.";
    type enumeration {
      enum LIMITED_USAGE {
        description "Limited usage of IntraFreqMCCellProfile MO class.\n\nFollowing attributes are not used:\n- rsrpBetterSpCell\n- rsrqBetterSpCell\n- betterSpCellTriggerQuantity\n- endcActionEvalFail\nInstead attributes from deprecated MO class ReportConfigA3 are used.";
        value 0;
      }
      enum COMPLETE_USAGE {
        description "Complete usage of IntraFreqMCCellProfile MO class.\n\nDeprecated MO class ReportConfigA3 is not used.";
        value 1;
      }
    }
  }
  typedef ddt-GNBCUCP_UeMCCellProfile_filterCoefficientNrRsrpLow {
    type int32 {
      range "0..9 | 11..11 | 13..13 | 15..15 | 17..17 | 19..19";
    }
  }
  typedef ddt-GNBCUCP_LwNeighborRelInfo_nRPCI {
    type int32 {
      range 0..1007;
    }
  }
  typedef ddt-GNBCUCP_ReportConfigA6Rsrp_hysteresis {
    type int32 {
      range 0..150;
    }
  }
  typedef ddt-GNBCUCP_UeGroupSelectionProfile_ueGroupId {
    type int32 {
      range 1..255;
    }
  }
  typedef ddt-GNBCUCP_EUtranFrequency_freqBandList {
    type int32 {
      range 1..256;
    }
  }
  typedef ddt-GNBCUCP_ExternalENodeBFunction_eNodeBId {
    type int32 {
      range 0..1048575;
    }
  }
  typedef ddt-GNBCUCP_ReportConfigA5Rsrp_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_EUtranFreqRelation_pMaxEUtra {
    type int32 {
      range -30..33;
    }
  }
  typedef ddt-GNBCUCP_NRCellCU_pwsEmergencyAreaIdList {
    type int32 {
      range 0..16777215;
    }
  }
  typedef ddt-GNBCUCP_NRCellCU_sNonIntraSearchP {
    type int32 {
      range 0..62;
    }
  }
  typedef ddt-GNBCUCP_NRCellCU_sNonIntraSearchQ {
    type int32 {
      range 0..31;
    }
  }
  typedef ddt-GNBCUCP_ReportConfigB2RsrpOffsets_threshold1Offset {
    type int32 {
      range -100..100;
    }
  }
  typedef ddt-GNBCUCP_QciProfileEndcConfigExt_tReorderingUlDiscardPdcp {
    type int32 {
      range "10..10 | 20..20 | 30..30 | 40..40 | 50..50 | 60..60 | 75..75 | 100..100 | 150..150 | 200..200 | 250..250 | 300..300 | 500..500 | 750..750 | 1500..1500";
    }
  }
  typedef ddt-GNBCUCP_ReportConfigA1A2Rsrp_timeToTriggerA1 {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_ReportConfigA5RsrpOffsets_threshold2Offset {
    type int32 {
      range -100..100;
    }
  }
  typedef ddt-GNBCUCP_ExternalNRCellCU_nRTAC {
    type uint32 {
      range 0..16777215;
    }
  }
  typedef ddt-GNBCUCP_NRFreqRelation_threshXLowQ {
    type int32 {
      range 0..31;
    }
  }
  typedef ddt-GNBCUCP_NRFreqRelation_threshXLowP {
    type int32 {
      range 0..62;
    }
  }
  typedef ddt-GNBCUCP_NRCellCU_cellLocalId {
    type int32 {
      range 0..16383;
    }
  }
  typedef ddt-GNBCUCP_QciProfileEndcConfigExt_ulDataSplitThreshold {
    type int32 {
      range "-1..-1 | 0..0 | 100..100 | 200..200 | 400..400 | 800..800 | 1600..1600 | 3200..3200 | 6400..6400 | 12800..12800 | 25600..25600 | 51200..51200 | 102400..102400 | 204800..204800 | 409600..409600 | 819200..819200 | 1228800..1228800 | 1638400..1638400 | 2457600..2457600 | 3276800..3276800 | 4096000..4096000 | 4915200..4915200 | 5734400..5734400 | 6553600..6553600";
    }
  }
  typedef ddt-GNBCUCP_NRFreqRelation_sIntraSearchQ {
    type int32 {
      range 0..31;
    }
  }
  typedef ddt-GNBCUCP_TermPointToGNodeB_ipsecEpAddress {
    type string {
      length 2..39;
    }
  }
  typedef ddt-GNBCUCP_GNBCUCPFunction_gNBCUName {
    type string {
      length 1..150;
    }
  }
  typedef ddt-GNBCUCP_LwNeighborRelInfo_mnc {
    type string {
      length 2..3;
    }
  }
  typedef ddt-NratCommonLibrary_SliceSelectionAssistInfo_sd {
    type int32 {
      range 0..16777215;
    }
  }
  typedef ddt-GNBCUCP_ExternalEUtranCell_localCellId {
    type int32 {
      range 0..255;
    }
  }
  typedef ddt-NratCommonLibrary_SliceSelectionAssistInfo_sst {
    type int32 {
      range 0..255;
    }
  }
  typedef ddt-GNBCUCP_ExternalBroadcastPLMNInfo_nRTAC {
    type int32 {
      range 0..16777215;
    }
  }
  typedef ddt-GNBCUCP_NRFreqRelation_sIntraSearchP {
    type int32 {
      range 0..62;
    }
  }
  typedef ddt-GNBCUCP_NRFreqRelation_tReselectionNR {
    type int32 {
      range 0..7;
    }
  }
  typedef ddt-GNBCUCP_ReportConfigA6Rsrp_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_TermPointToAmf_relativeCapacity {
    type int32 {
      range 0..255;
    }
  }
  typedef ddt-GNBCUCP_AnrFunction_removeNrelTime {
    type int32 {
      range 1..1000;
    }
  }
  typedef ddt-GNBCUCP_ReportConfigA3_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_UeGroupSelectionProfile_ueGroupPriority {
    type int32 {
      range 1..65535;
    }
  }
  typedef ddt-GNBCUCP_ReportConfigA3Rsrp_hysteresis {
    type int32 {
      range 0..150;
    }
  }
  typedef ddt-GNBCUCP_NRFreqRelation_qQualMin {
    type int32 {
      range -43..-12;
    }
  }
  typedef ddt-GNBCUCP_CUCP5qi_profile5qi {
    type int32 {
      range 0..255;
    }
  }
  typedef ddt-GNBCUCP_TermPointToGNBDU_gNBDUId {
    type int64 {
      range 0..68719476735;
    }
  }
  typedef ddt-GNBCUCP_NRFrequency_bandList {
    type int32 {
      range 1..1024;
    }
  }
  typedef ddt-GNBCUCP_GNBCUCPFunction_maxCommonProcTime {
    type int32 {
      range 1..60;
    }
  }
  typedef ddt-GNBCUCP_ReportConfigB2Rsrp_threshold1 {
    type int32 {
      range -156..-29;
    }
  }
  typedef ddt-GNBCUCP_EUtranFreqRelation_cellReselectionPriority {
    type int32 {
      range 0..7;
    }
  }
  typedef ddt-GNBCUCP_ReportConfigA2_thresholdRsrp {
    type int32 {
      range -156..-29;
    }
  }
  typedef ddt-GNBCUCP_PrefUeGroupSelectionProfile_prefUeGroupId {
    type int32 {
      range 1..255;
    }
  }
  typedef ddt-GNBCUCP_ReportConfigA2_thresholdRsrq {
    type int32 {
      range -435..200;
    }
  }
  typedef ddt-GNBCUCP_ExternalNRCellCU_cellLocalId {
    type int32 {
      range 0..16383;
    }
  }
  typedef ddt-GNBCUCP_AnrFunctionNR_gNBIdLength {
    type int32 {
      range 22..32;
    }
  }
  typedef ddt-NratCommonLibrary_GlobalUniqueAmfId_amfRegionId {
    type int32 {
      range 0..255;
    }
  }
  typedef ddt-GNBCUCP_NRCellCU_nCI {
    type int64 {
      range 0..68719476735;
    }
  }
  typedef ddt-GNBCUCP_ReportConfigA5Rsrp_threshold1 {
    type int32 {
      range -156..-29;
    }
  }
  typedef ddt-NratCommonLibrary_AbsFrameStartOffset_absTimeOffset {
    type int32 {
      range 0..999999;
    }
  }
  typedef ddt-GNBCUCP_TermPointToAmf_ipv6Address2 {
    type string {
      length 2..39;
    }
  }
  typedef ddt-GNBCUCP_ExternalNRCellCU_nCI {
    type int64 {
      range 0..68719476735;
    }
  }
  typedef ddt-GNBCUCP_GNBCUCPFunction_gNBId {
    type int64 {
      range 0..4294967295;
    }
  }
  typedef ddt-GNBCUCP_QciProfileEndcConfigExt_tReorderingDlPdcp {
    type int32 {
      range "0..0 | 20..20 | 40..40 | 60..60 | 80..80 | 100..100 | 120..120 | 140..140 | 160..160 | 180..180 | 200..200 | 220..220 | 240..240 | 260..260 | 280..280 | 300..300 | 500..500 | 750..750";
    }
  }
  typedef ddt-GNBCUCP_TermPointToGNodeB_ipv6Address {
    type string {
      length 2..39;
    }
  }
  typedef ddt-GNBCUCP_ReportConfigA5Rsrp_threshold2 {
    type int32 {
      range -156..-29;
    }
  }
  typedef ddt-GNBCUCP_NRFrequency_smtcPeriodicity {
    type int32 {
      range "5..5 | 10..10 | 20..20 | 40..40 | 80..80 | 160..160";
    }
  }
  typedef ddt-GNBCUCP_TermPointToAmf_ipv6Address1 {
    type string {
      length 2..39;
    }
  }
  typedef ddt-GNBCUCP_UeMCCellProfile_sMeasure {
    type int32 {
      range -156..-29;
    }
  }
  typedef ddt-GNBCUCP_ReportConfigB2RsrpOffsets_threshold2EUtraOffset {
    type int32 {
      range -100..100;
    }
  }
  typedef ddt-UserLabel {
    description "User-defined label, maximum 128 characters including spaces.";
    type string {
      length 1..128;
    }
  }
  typedef ddt-GNBCUCP_LwNeighborRelInfo_gNBIdLength {
    type int32 {
      range 22..32;
    }
  }
  typedef ddt-GNBCUCP_UeMCCellProfile_filterCoefficientNrRsrqHigh {
    type int32 {
      range "0..9 | 11..11 | 13..13 | 15..15 | 17..17 | 19..19";
    }
  }
  typedef ddt-GNBCUCP_EUtranFreqRelation_eUtranFallbackPrioEc {
    type int32 {
      range 0..7;
    }
  }
  typedef ddt-GNBCUCP_ReportConfigA5Rsrp_hysteresis {
    type int32 {
      range 0..150;
    }
  }
  typedef ddt-GNBCUCP_ExternalNRCellCU_timeOfCreation {
    type string {
      length 0..19;
    }
  }
  typedef ddt-NratCommonLibrary_GlobalUniqueAmfId_mcc {
    type string {
      length 3..3;
    }
  }
  typedef ddt-GNBCUCP_EUtranCellRelation_cellIndividualOffset {
    type int32 {
      range "-24..-24 | -22..-22 | -20..-20 | -18..-18 | -16..-16 | -14..-14 | -12..-12 | -10..-10 | -8..-8 | -6..6 | 8..8 | 10..10 | 12..12 | 14..14 | 16..16 | 18..18 | 20..20 | 22..22 | 24..24";
    }
  }
  typedef ddt-GNBCUCP_UeMCCellProfile_filterCoefficientNrRsrqLow {
    type int32 {
      range "0..9 | 11..11 | 13..13 | 15..15 | 17..17 | 19..19";
    }
  }
  typedef ddt-GNBCUCP_EssCellScPair_essScPairId {
    type int64 {
      range 0..9223372036854775807;
    }
  }
  typedef ddt-GNBCUCP_NRFrequency_smtcDuration {
    type int32 {
      range 1..5;
    }
  }
  typedef ddt-GNBCUCP_ReportConfigA5RsrpOffsets_threshold1Offset {
    type int32 {
      range -100..100;
    }
  }
  typedef ddt-GNBCUCP_ResourcePartition_resourcePartitionName {
    type string {
      length 1..255;
    }
  }
  typedef ddt-NratCommonLibrary_GlobalUniqueAmfId_amfSetId {
    type int32 {
      range 0..1023;
    }
  }
  typedef ddt-NratCommonLibrary_PLMNId_mcc {
    type string {
      length 3..3;
    }
  }
  typedef ddt-GNBCUCP_ExternalGNBCUCPFunction_gNBId {
    type int64 {
      range 0..4294967295;
    }
  }
  typedef ddt-GNBCUCP_ReportConfigA1A2Rsrq_timeToTriggerA1 {
    type int32 {
      range "-1..-1 | 0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_LwNeighborRelInfo_gNBId {
    type int64 {
      range 0..4294967295;
    }
  }
  typedef ddt-GNBCUCP_LwNeighborRelInfo_cellLocalId {
    type int32 {
      range 0..16383;
    }
  }
  typedef ddt-GNBCUCP_UeGroupSelectionProfile_selectionCriteria {
    type string {
      length 1..1000;
    }
  }
  typedef ddt-GNBCUCP_ExternalGNBCUCPFunction_timeOfCreation {
    type string {
      length 0..19;
    }
  }
  typedef ddt-NratCommonLibrary_GlobalUniqueAmfId_amfPointer {
    type int32 {
      range 0..63;
    }
  }
  typedef ddt-GNBCUCP_ReportConfigA1A2Rsrp_threshold {
    type int32 {
      range -156..-29;
    }
  }
  typedef ddt-GNBCUCP_ReportConfigB1Rsrq_threshold {
    type int32 {
      range -195..-30;
    }
  }
  typedef ddt-GNBCUCP_ExternalEUtranCell_dlChannelBandwidth {
    type int32 {
      range "1400..1400 | 3000..3000 | 5000..5000 | 10000..10000 | 15000..15000 | 20000..20000";
    }
  }
  typedef ddt-GNBCUCP_QciProfileEndcConfigExt_rlcModeQciUM {
    type int32 {
      range 0..255;
    }
  }
  typedef ddt-GNBCUCP_EUtranFreqRelation_connectedModeMobilityPrio {
    type int32 {
      range 0..7;
    }
  }
  typedef ddt-GNBCUCP_EUtranFreqRelation_threshXHighP {
    type int32 {
      range 0..62;
    }
  }
  typedef ddt-GNBCUCP_EUtranFreqRelation_threshXHighQ {
    type int32 {
      range 0..31;
    }
  }
  typedef ddt-GNBCUCP_ReportConfigA1A2Rsrq_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_GNBCUCPFunction_gNBIdLength {
    type int32 {
      range 22..32;
    }
  }
  typedef ddt-GNBCUCP_ReportConfigB1Rsrp_hysteresis {
    type int32 {
      range 0..150;
    }
  }
  typedef ddt-NratCommonLibrary_AbsFrameStartOffset_absSubFrameOffset {
    type int32 {
      range -5..4;
    }
  }
  typedef ddt-GNBCUCP_ReportConfigA3_offset {
    type int32 {
      range -150..150;
    }
  }
  typedef ddt-GNBCUCP_EUtranFrequency_excludeAdditionalFreqBandList {
    type int32 {
      range 1..256;
    }
  }
  typedef ddt-GNBCUCP_CUCP5qi_pdcpSnSize {
    type int32 {
      range "12..12 | 18..18";
    }
  }
  typedef ddt-GNBCUCP_McpcPCellProfile_rsrpSearchTimeRestriction {
    type int32 {
      range "-1..-1 | 10..12000";
    }
  }
  typedef ddt-GNBCUCP_NRFreqRelation_pMax {
    type int32 {
      range -30..26;
    }
  }
  typedef ddt-GNBCUCP_ExternalEUtranCell_tac {
    type int32 {
      range 0..65535;
    }
  }
  typedef ddt-GNBCUCP_ReportConfigB2Rsrp_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_TermPointToAmf_domainName {
    type string {
      length 1..255;
    }
  }
  typedef ddt-GNBCUCP_PrefUeGroupSelectionProfile_prefUeGroupPriority {
    type int32 {
      range 1..65535;
    }
  }
  typedef ddt-GNBCUCP_ReportConfigB1Rsrq_hysteresis {
    type int32 {
      range 0..150;
    }
  }
  typedef ddt-GNBCUCP_UeMeasControl_filterCoefficientNrRsrq {
    type int32 {
      range "0..0 | 1..1 | 2..2 | 3..3 | 4..4 | 5..5 | 6..6 | 7..7 | 8..8 | 9..9 | 11..11 | 13..13 | 15..15 | 17..17 | 19..19";
    }
  }
  typedef ddt-GNBCUCP_CUCP5qi_tPdcpDiscard {
    type int32 {
      range "10..10 | 20..20 | 30..30 | 40..40 | 50..50 | 60..60 | 75..75 | 100..100 | 150..150 | 200..200 | 250..250 | 300..300 | 500..500 | 750..750 | 1500..2147483646";
    }
  }
  typedef ddt-GNBCUCP_ReportConfigA1A2Rsrp_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_EUtranCellRelation_essMbsfnSubframeConfig {
    type uint32 {
      range "9440512..9440512 | 9441024..9441024 | 12584960..12584960";
    }
  }
  typedef ddt-GNBCUCP_NRCellRelation_timeOfCreation {
    type string {
      length 0..19;
    }
  }
  typedef ddt-GNBCUCP_ReportConfigB1Rsrp_threshold {
    type int32 {
      range -140..-44;
    }
  }
  typedef ddt-GNBCUCP_EssCellScPair_gNBessLocalScId {
    type int32 {
      range 0..99999;
    }
  }
  typedef ddt-GNBCUCP_ReportConfigA6Rsrp_offset {
    type int32 {
      range -150..150;
    }
  }
  typedef ddt-GNBCUCP_ReportConfigB2Rsrp_threshold2EUtra {
    type int32 {
      range -140..-44;
    }
  }
  typedef ddt-GNBCUCP_GNBCUCPFunction_maxNgRetryTime {
    type int32 {
      range 1..3600;
    }
  }
  typedef ddt-GNBCUCP_NRCellCU_qHyst {
    type int32 {
      range "0..0 | 1..1 | 2..2 | 3..3 | 4..4 | 5..5 | 6..6 | 8..8 | 10..10 | 12..12 | 14..14 | 16..16 | 18..18 | 20..20 | 22..22 | 24..24";
    }
  }
  typedef ddt-GNBCUCP_ReportConfigA3Rsrp_offset {
    type int32 {
      range -150..150;
    }
  }
  typedef ddt-GNBCUCP_EmCall_arpEmCallList {
    type int32 {
      range 1..15;
    }
  }
  typedef ddt-GNBCUCP_NRFreqRelation_threshXHighQ {
    type int32 {
      range 0..31;
    }
  }
  typedef ddt-GNBCUCP_NRFreqRelation_threshXHighP {
    type int32 {
      range 0..62;
    }
  }
  typedef ddt-GNBCUCP_TermPointToGNodeB_upIpAddress {
    type string {
      length 2..39;
    }
  }
  typedef ddt-GNBCUCP_EUtranFreqRelation_threshXLowQ {
    type int32 {
      range 0..31;
    }
  }
  typedef ddt-GNBCUCP_GNBCUCPFunction_nasInactivityTime {
    type int32 {
      range 1..60;
    }
  }
  typedef ddt-GNBCUCP_EUtranFreqRelation_threshXLowP {
    type int32 {
      range 0..62;
    }
  }
  typedef ddt-GNBCUCP_NRFreqRelation_qOffsetFreq {
    type int32 {
      range "-24..-24 | -22..-22 | -20..-20 | -18..-18 | -16..-16 | -14..-14 | -12..-12 | -10..-10 | -8..-8 | -6..-6 | -5..-5 | -4..-4 | -3..-3 | -2..-2 | -1..-1 | 0..0 | 1..1 | 2..2 | 3..3 | 4..4 | 5..5 | 6..6 | 8..8 | 10..10 | 12..12 | 14..14 | 16..16 | 18..18 | 20..20 | 22..22 | 24..24";
    }
  }
  typedef ddt-GNBCUCP_EUtranFreqRelation_allowedMeasBandwidth {
    type int32 {
      range "6..6 | 15..15 | 25..25 | 50..50 | 75..75 | 100..100";
    }
  }
  typedef ddt-GNBCUCP_ExternalEUtranCell_earfcnul {
    type int32 {
      range "0..0 | 18000..35999 | 46590..262143";
    }
  }
  typedef ddt-GNBCUCP_PmUeIntraFreqCellProfile_ueSelectionRatio {
    type int32 {
      range 0..1000;
    }
  }
  typedef ddt-GNBCUCP_ReportConfigA1A2Rsrp_hysteresis {
    type int32 {
      range 0..150;
    }
  }
  typedef ddt-GNBCUCP_PrefUeGroupSelectionProfile_selectionCriteria {
    type string {
      length 1..1000;
    }
  }
  typedef ddt-GNBCUCP_UeMCCellProfile_filterCoefficientNrRsrpHigh {
    type int32 {
      range "0..9 | 11..11 | 13..13 | 15..15 | 17..17 | 19..19";
    }
  }
  typedef ddt-GNBCUCP_UeMeasControl_filterCoefficientNrRsrp {
    type int32 {
      range "0..0 | 1..1 | 2..2 | 3..3 | 4..4 | 5..5 | 6..6 | 7..7 | 8..8 | 9..9 | 11..11 | 13..13 | 15..15 | 17..17 | 19..19";
    }
  }
  typedef ddt-GNBCUCP_TermPointToENodeB_upIpAddress {
    type string {
      length 2..39;
    }
  }
  typedef ddt-NratCommonLibrary_GlobalUniqueAmfId_mnc {
    type string {
      length 2..3;
    }
  }
  typedef ddt-GNBCUCP_ExternalENodeBFunction_eNBPlmnId {
    type string {
      length 6..7;
    }
  }
  typedef ddt-GNBCUCP_TermPointToAmf_usedIpAddress {
    type string {
      length 2..39;
    }
  }
  typedef ddt-GNBCUCP_TermPointToGNBDU_gNBDUName {
    type string {
      length 1..150;
    }
  }
  typedef ddt-GNBCUCP_ExternalEUtranCell_ulChannelBandwidth {
    type int32 {
      range "1400..1400 | 3000..3000 | 5000..5000 | 10000..10000 | 15000..15000 | 20000..20000";
    }
  }
  typedef ddt-GNBCUCP_UeMeasControl_sMeasure {
    type int32 {
      range -156..-29;
    }
  }
  typedef ddt-GNBCUCP_NRFrequency_smtcScs {
    type int32 {
      range "15..15 | 30..30 | 120..120 | 240..240";
    }
  }
  typedef ddt-GNBCUCP_TermPointToAmf_ipv4Address2 {
    type string {
      length 7..15;
    }
  }
  typedef ddt-GNBCUCP_McfbCellProfile_epsFbTargetSearchTimer {
    type int32 {
      range 1..12000;
    }
  }
  typedef ddt-GNBCUCP_ReportConfigA2_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_TermPointToAmf_ipv4Address1 {
    type string {
      length 7..15;
    }
  }
  typedef ddt-GNBCUCP_NRFrequency_arfcnValueNRDl {
    type int32 {
      range 0..3279165;
    }
  }
  typedef ddt-GNBCUCP_ReportConfigA3Rsrq_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_ReportConfigA1A2Rsrq_threshold {
    type int32 {
      range -435..200;
    }
  }
  typedef ddt-NratCommonLibrary_PLMNId_mnc {
    type string {
      length 2..3;
    }
  }
  typedef ddt-GNBCUCP_QciProfileEndcConfigExt_tReorderingUlPdcp {
    type int32 {
      range "0..0 | 1..1 | 4..4 | 5..5 | 8..8 | 10..10 | 15..15 | 20..20 | 30..30 | 40..40 | 50..50 | 60..60 | 80..80 | 100..100 | 120..120 | 140..140 | 160..160 | 180..180 | 200..200 | 220..220 | 240..240 | 260..260 | 280..280 | 300..300 | 500..500 | 750..750 | 1000..1000 | 1250..1250 | 1500..1500 | 1750..1750 | 2000..2000 | 2250..2250 | 2500..2500 | 2750..2750 | 3000..3000";
    }
  }
  typedef ddt-GNBCUCP_GNBCUCPFunction_ngcDedProcTime {
    type int32 {
      range 1..60;
    }
  }
  typedef ddt-GNBCUCP_ReportConfigA3Rsrq_hysteresis {
    type int32 {
      range 0..150;
    }
  }
  typedef ddt-GNBCUCP_TermPointToGNodeB_ipv4Address {
    type string {
      length 7..15;
    }
  }
  typedef ddt-GNBCUCP_CUCP5qi_packetErrorRateScalar {
    type int32 {
      range 0..9;
    }
  }
  typedef ddt-GNBCUCP_NRCellCU_threshServingLowQ {
    type int32 {
      range 0..31;
    }
  }
  typedef ddt-GNBCUCP_NRCellCU_threshServingLowP {
    type int32 {
      range 0..62;
    }
  }
  typedef ddt-GNBCUCP_UeGroupSelectionProfile_selectionProbability {
    type int32 {
      range 0..100;
    }
  }
  typedef ddt-GNBCUCP_EUtranFreqRelation_voicePrio {
    type int32 {
      range 0..7;
    }
  }
  typedef ddt-GNBCUCP_ReportConfigB1Rsrq_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_ReportConfigA1A2Rsrq_hysteresis {
    type int32 {
      range 0..150;
    }
  }
  typedef ddt-GNBCUCP_ExternalEUtranCell_physicalLayerCellId {
    type int32 {
      range 0..503;
    }
  }
  typedef ddt-GNBCUCP_EUtranFreqRelation_qRxLevMin {
    type int32 {
      range -140..-44;
    }
  }
  typedef ddt-GNBCUCP_UeMCCellProfile_filterCoefficientEUtraRsrq {
    type int32 {
      range "0..0 | 1..1 | 2..2 | 3..3 | 4..4 | 5..5 | 6..6 | 7..7 | 8..8 | 9..9 | 11..11 | 13..13 | 15..15 | 17..17 | 19..19";
    }
  }
  typedef ddt-GNBCUCP_ExternalNRCellCU_nRPCI {
    type int32 {
      range 0..1007;
    }
  }
  typedef ddt-GNBCUCP_UeMCCellProfile_filterCoefficientEUtraRsrp {
    type int32 {
      range "0..0 | 1..1 | 2..2 | 3..3 | 4..4 | 5..5 | 6..6 | 7..7 | 8..8 | 9..9 | 11..11 | 13..13 | 15..15 | 17..17 | 19..19";
    }
  }
  typedef ddt-GNBCUCP_TermPointToENodeB_ipsecEpAddress {
    type string {
      length 2..39;
    }
  }
  typedef ddt-GNBCUCP_ExternalEUtranCell_earfcndl {
    type int32 {
      range "1..17999 | 46590..262143";
    }
  }
  typedef ddt-GNBCUCP_ReportConfigA3Rsrp_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_EssCellScPair_eNBessLocalScId {
    type int32 {
      range 0..99999;
    }
  }
  typedef ddt-GNBCUCP_NRFreqRelation_qRxLevMin {
    type int32 {
      range -140..-44;
    }
  }
  typedef ddt-GNBCUCP_EUtranFreqRelation_tReselectionEUtra {
    type int32 {
      range 0..7;
    }
  }
  typedef ddt-GNBCUCP_LwNeighborRelInfo_mcc {
    type string {
      length 3..3;
    }
  }
  typedef ddt-GNBCUCP_CUCP5qi_packetErrorRateExp {
    type int32 {
      range 0..9;
    }
  }
  typedef ddt-GNBCUCP_EUtranFreqRelation_qQualMin {
    type int32 {
      range -43..-12;
    }
  }
  typedef ddt-GNBCUCP_ReportConfigA3Rsrq_offset {
    type int32 {
      range -150..150;
    }
  }
  typedef ddt-GNBCUCP_CUCP5qi_tReorderingUl {
    type int32 {
      range "0..0 | 1..1 | 2..2 | 4..4 | 5..5 | 8..8 | 10..10 | 15..15 | 20..20 | 30..30 | 40..40 | 50..50 | 60..60 | 80..80 | 100..100 | 120..120 | 140..140 | 160..160 | 180..180 | 200..200 | 220..220 | 240..240 | 260..260 | 280..280 | 300..300 | 500..500 | 750..750 | 1000..1000 | 1250..1250 | 1500..1500 | 1750..1750 | 2000..2000 | 2250..2250 | 2500..2500 | 2750..2750 | 3000..3000";
    }
  }
  typedef ddt-GNBCUCP_ReportConfigB2Rsrp_hysteresis {
    type int32 {
      range 0..150;
    }
  }
  typedef ddt-GNBCUCP_ReportConfigA2_hysteresis {
    type int32 {
      range 0..150;
    }
  }
  typedef ddt-GNBCUCP_NRFrequency_smtcOffset {
    type int32 {
      range 0..159;
    }
  }
  typedef ddt-GNBCUCP_NRCellRelation_cellIndividualOffsetNR {
    type int32 {
      range "-24..-24 | -22..-22 | -20..-20 | -18..-18 | -16..-16 | -14..-14 | -12..-12 | -10..-10 | -8..-8 | -6..6 | 8..8 | 10..10 | 12..12 | 14..14 | 16..16 | 18..18 | 20..20 | 22..22 | 24..24";
    }
  }
  typedef ddt-GNBCUCP_NRFrequency_bandListManual {
    type int32 {
      range "1..5 | 7..7 | 8..8 | 12..12 | 14..14 | 18..18 | 20..20 | 25..25 | 26..26 | 28..28 | 29..29 | 30..30 | 34..34 | 38..41 | 48..48 | 50..50 | 51..51 | 65..65 | 66..66 | 70..70 | 71..71 | 74..84 | 86..86 | 89..95 | 257..257 | 258..258 | 260..260 | 261..261";
    }
  }
  typedef ddt-GNBCUCP_ReportConfigA3_hysteresis {
    type int32 {
      range 0..150;
    }
  }
  typedef ddt-GNBCUCP_ExternalEUtranCell_cellLocalId {
    type int32 {
      range 0..255;
    }
  }
  typedef ddt-GNBCUCP_ExternalGNBCUCPFunction_gNBIdLength {
    type int32 {
      range 22..32;
    }
  }
  typedef ddt-GNBCUCP_CUCP5qi_tReorderingDl {
    type int32 {
      range "0..0 | 1..1 | 2..2 | 4..4 | 5..5 | 8..8 | 10..10 | 15..15 | 20..20 | 30..30 | 40..40 | 50..50 | 60..60 | 80..80 | 100..100 | 120..120 | 140..140 | 160..160 | 180..180 | 200..200 | 220..220 | 240..240 | 260..260 | 280..280 | 300..300 | 500..500 | 750..750 | 1000..1000 | 1250..1250 | 1500..1500 | 1750..1750 | 2000..2000 | 2250..2250 | 2500..2500 | 2750..2750 | 3000..3000";
    }
  }
  typedef ddt-GNBCUCP_NRFreqRelation_cellReselectionPriority {
    type int32 {
      range 0..7;
    }
  }
  typedef ddt-GNBCUCP_EUtranFrequency_arfcnValueEUtranDl {
    type int32 {
      range "0..17999 | 36000..262143";
    }
  }
  typedef ddt-GNBCUCP_ReportConfigB1Rsrp_timeToTrigger {
    type int32 {
      range "0..0 | 40..40 | 64..64 | 80..80 | 100..100 | 128..128 | 160..160 | 256..256 | 320..320 | 480..480 | 512..512 | 640..640 | 1024..1024 | 1280..1280 | 2560..2560 | 5120..5120";
    }
  }
  typedef ddt-GNBCUCP_GNBCUCPFunction_tInactivityTimer {
    type int32 {
      range 1..7200;
    }
  }
  typedef ddt-GNBCUCP_GNBCUCPFunction_tDcOverall {
    type int32 {
      range 1..20;
    }
  }
  typedef ddt-GNBCUCP_UeMCCellProfile_freqClassificationThreshold {
    type int32 {
      range 0..3279164;
    }
  }
  typedef ddt-GNBCUCP_PmUeIntraFreqCellProfile_maxReportCells {
    type int32 {
      range 1..8;
    }
  }
  grouping struct-AbsFrameStartOffset {
    description "Absolute frame start offset for cell.";
    leaf absTimeOffset {
      status current {
        yexte:preliminary;
      }
      description "Absolute frame synchronization offset within a subframe.";
      type erienmnrmgnbcucp:ddt-NratCommonLibrary_AbsFrameStartOffset_absTimeOffset;
      default 0;
    }
    leaf absSubFrameOffset {
      status current {
        yexte:preliminary;
      }
      description "Absolute frame synchronization offset.";
      type erienmnrmgnbcucp:ddt-NratCommonLibrary_AbsFrameStartOffset_absSubFrameOffset;
      default 0;
    }
  } // end 'grouping struct-AbsFrameStartOffset'
  grouping struct-ReportConfigB1Rsrq {
    description "Report configuration settings for E-UTRA B1 measurement event when trigger quantity is RSRQ.";
    leaf timeToTrigger {
      description "Time-to-trigger value for eventB1 measurement.";
      type erienmnrmgnbcucp:ddt-GNBCUCP_ReportConfigB1Rsrq_timeToTrigger;
      default 40;
    }
    leaf threshold {
      description "RSRQ threshold value for eventB1.";
      type erienmnrmgnbcucp:ddt-GNBCUCP_ReportConfigB1Rsrq_threshold;
      default -195;
    }
    leaf hysteresis {
      description "Hysteresis value for eventB1.";
      type erienmnrmgnbcucp:ddt-GNBCUCP_ReportConfigB1Rsrq_hysteresis;
      default 10;
    }
  } // end 'grouping struct-ReportConfigB1Rsrq'
  grouping struct-ReportConfigA5Rsrp {
    description "Report configuration settings for A5 measurement event when trigger quantity is RSRP.";
    leaf timeToTrigger {
      description "Time-to-trigger value for eventA5.";
      type erienmnrmgnbcucp:ddt-GNBCUCP_ReportConfigA5Rsrp_timeToTrigger;
      default 640;
    }
    leaf threshold1 {
      description "RSRP threshold1 value for eventA5.\nValue -29 defines threshold1 to infinity.";
      type erienmnrmgnbcucp:ddt-GNBCUCP_ReportConfigA5Rsrp_threshold1;
      default -156;
    }
    leaf threshold2 {
      description "RSRP threshold2 value for eventA5.\nValue -29 defines threshold2 to infinity.";
      type erienmnrmgnbcucp:ddt-GNBCUCP_ReportConfigA5Rsrp_threshold2;
      default -156;
    }
    leaf hysteresis {
      description "Hysteresis value for eventA5.";
      type erienmnrmgnbcucp:ddt-GNBCUCP_ReportConfigA5Rsrp_hysteresis;
      default 10;
    }
  } // end 'grouping struct-ReportConfigA5Rsrp'
  grouping struct-ReportConfigB1Rsrp {
    description "Report configuration settings for E-UTRA B1 measurement event when trigger quantity is RSRP.";
    leaf timeToTrigger {
      description "Time-to-trigger value for eventB1 measurement.";
      type erienmnrmgnbcucp:ddt-GNBCUCP_ReportConfigB1Rsrp_timeToTrigger;
      default 40;
    }
    leaf threshold {
      description "RSRP threshold value for eventB1.";
      type erienmnrmgnbcucp:ddt-GNBCUCP_ReportConfigB1Rsrp_threshold;
      default -140;
    }
    leaf hysteresis {
      description "Hysteresis value for eventB1.";
      type erienmnrmgnbcucp:ddt-GNBCUCP_ReportConfigB1Rsrp_hysteresis;
      default 10;
    }
  } // end 'grouping struct-ReportConfigB1Rsrp'
  grouping struct-ReportConfigA1A2Rsrp {
    description "Report configuration settings for UE DL A1, A2, or both measurements with trigger quantity RSRP.";
    leaf timeToTrigger {
      description "Time-to-trigger value for RSRP in UE DL event A1, A2, or both measurements.";
      type erienmnrmgnbcucp:ddt-GNBCUCP_ReportConfigA1A2Rsrp_timeToTrigger;
      default 160;
    }
    leaf threshold {
      description "RSRP threshold value for UE DL event A1, A2, or both measurements.";
      type erienmnrmgnbcucp:ddt-GNBCUCP_ReportConfigA1A2Rsrp_threshold;
      default -156;
    }
    leaf timeToTriggerA1 {
      description "Time-to-trigger value for event A1.\nIf set to -1, time-to-trigger value from struct member timeToTrigger is used.";
      type erienmnrmgnbcucp:ddt-GNBCUCP_ReportConfigA1A2Rsrp_timeToTriggerA1;
      default -1;
    }
    leaf hysteresis {
      description "Hysteresis value for RSRP in UE DL event A1, A2, or both measurements.";
      type erienmnrmgnbcucp:ddt-GNBCUCP_ReportConfigA1A2Rsrp_hysteresis;
      default 10;
    }
  } // end 'grouping struct-ReportConfigA1A2Rsrp'
  grouping struct-ReportConfigA1A2Rsrq {
    description "Report configuration settings for A1 and A2 measurements when trigger quantity is RSRQ.";
    leaf timeToTrigger {
      description "Time-to-trigger value for RSRQ in event A1 and A2 measurements.";
      type erienmnrmgnbcucp:ddt-GNBCUCP_ReportConfigA1A2Rsrq_timeToTrigger;
      default 160;
    }
    leaf threshold {
      description "RSRQ threshold value for event A1 and A2 measurements.";
      type erienmnrmgnbcucp:ddt-GNBCUCP_ReportConfigA1A2Rsrq_threshold;
      default -435;
    }
    leaf timeToTriggerA1 {
      description "The time-to-trigger value for eventA1.\nIf set to -1, time-to-trigger value from struct member timeToTrigger is used.";
      type erienmnrmgnbcucp:ddt-GNBCUCP_ReportConfigA1A2Rsrq_timeToTriggerA1;
      default -1;
    }
    leaf hysteresis {
      description "Hysteresis value for RSRQ in event A1 and A2 measurements.";
      type erienmnrmgnbcucp:ddt-GNBCUCP_ReportConfigA1A2Rsrq_hysteresis;
      default 10;
    }
  } // end 'grouping struct-ReportConfigA1A2Rsrq'
  grouping struct-ReportConfigA3Rsrq {
    description "Report configuration settings for A3 measurement events when trigger quantity is RSRQ.";
    leaf offset {
      description "Offset value for eventA3.";
      type erienmnrmgnbcucp:ddt-GNBCUCP_ReportConfigA3Rsrq_offset;
      default 30;
    }
    leaf timeToTrigger {
      description "Time-to-trigger value for eventA3.";
      type erienmnrmgnbcucp:ddt-GNBCUCP_ReportConfigA3Rsrq_timeToTrigger;
      default 640;
    }
    leaf hysteresis {
      description "Hysteresis value for eventA3.";
      type erienmnrmgnbcucp:ddt-GNBCUCP_ReportConfigA3Rsrq_hysteresis;
      default 10;
    }
  } // end 'grouping struct-ReportConfigA3Rsrq'
  grouping struct-ReportConfigA3Rsrp {
    description "Report configuration settings for A3 measurement events when trigger quantity is RSRP.";
    leaf offset {
      description "Offset value for eventA3.";
      type erienmnrmgnbcucp:ddt-GNBCUCP_ReportConfigA3Rsrp_offset;
      default 30;
    }
    leaf timeToTrigger {
      description "Time-to-trigger value for eventA3.";
      type erienmnrmgnbcucp:ddt-GNBCUCP_ReportConfigA3Rsrp_timeToTrigger;
      default 640;
    }
    leaf hysteresis {
      description "Hysteresis value for eventA3.";
      type erienmnrmgnbcucp:ddt-GNBCUCP_ReportConfigA3Rsrp_hysteresis;
      default 10;
    }
  } // end 'grouping struct-ReportConfigA3Rsrp'
  grouping struct-ReportConfigA5RsrpOffsets {
    description "Threshold offsets for report configuration setting for A5 measurement event.\n\nApplied when trigger quantity is RSRP.";
    leaf threshold1Offset {
      description "RSRP threshold1 offset value for eventA5.";
      type erienmnrmgnbcucp:ddt-GNBCUCP_ReportConfigA5RsrpOffsets_threshold1Offset;
      default 0;
    }
    leaf threshold2Offset {
      description "RSRP threshold2 offset value for eventA5.";
      type erienmnrmgnbcucp:ddt-GNBCUCP_ReportConfigA5RsrpOffsets_threshold2Offset;
      default 0;
    }
  } // end 'grouping struct-ReportConfigA5RsrpOffsets'
  grouping struct-PLMNId {
    description "PLMN Identity consisting of Mobile Country Code (MCC) and Mobile Network Code (MNC).";
    leaf mnc {
      description "The Mobile Network Code (MNC) identifies home PLMN of mobile subscription.\nMNC consists of two or three decimal digits. For example, MNC of 001 is not same as MNC of 01.\nAs default value, use 01.\nAllowed values: [0-9][0-9][0-9]|[0-9][0-9]";
      type erienmnrmgnbcucp:ddt-NratCommonLibrary_PLMNId_mnc;
      mandatory true;
    }
    leaf mcc {
      description "The Mobile Country Code (MCC) identifies uniquely domicile country of mobile subscriber.\nMCC consists of three decimal digits. The first digit of MCC identifies geographic region. (Values 1 and 8 in the first digit are not allowed.)\nAs default value, use 001.\nAllowed values: [02345679][0-9][0-9]";
      type erienmnrmgnbcucp:ddt-NratCommonLibrary_PLMNId_mcc;
      mandatory true;
    }
  } // end 'grouping struct-PLMNId'
  grouping struct-ReportConfigB2Rsrp {
    description "Report configuration settings for B2 measurement event when trigger quantity is RSRP.";
    leaf threshold2EUtra {
      description "RSRP threshold2 value for event B2.";
      type erienmnrmgnbcucp:ddt-GNBCUCP_ReportConfigB2Rsrp_threshold2EUtra;
      default -140;
    }
    leaf timeToTrigger {
      description "Time-to-trigger value for event B2.";
      type erienmnrmgnbcucp:ddt-GNBCUCP_ReportConfigB2Rsrp_timeToTrigger;
      default 640;
    }
    leaf threshold1 {
      description "RSRP threshold1 value for event B2.\nValue -29 defines threshold1 to infinity.";
      type erienmnrmgnbcucp:ddt-GNBCUCP_ReportConfigB2Rsrp_threshold1;
      default -156;
    }
    leaf hysteresis {
      description "Hysteresis value for event B2.";
      type erienmnrmgnbcucp:ddt-GNBCUCP_ReportConfigB2Rsrp_hysteresis;
      default 10;
    }
  } // end 'grouping struct-ReportConfigB2Rsrp'
  grouping struct-ReportConfigB2RsrpOffsets {
    description "Threshold offsets for report configuration setting for B2 measurement event.\n\nApplied when trigger quantity is RSRP.";
    leaf threshold2EUtraOffset {
      description "RSRP threshold2 offset value for Event B2.";
      type erienmnrmgnbcucp:ddt-GNBCUCP_ReportConfigB2RsrpOffsets_threshold2EUtraOffset;
      default 0;
    }
    leaf threshold1Offset {
      description "RSRP threshold1 offset value for Event B2.";
      type erienmnrmgnbcucp:ddt-GNBCUCP_ReportConfigB2RsrpOffsets_threshold1Offset;
      default 0;
    }
  } // end 'grouping struct-ReportConfigB2RsrpOffsets'
  grouping struct-ReportConfigA6Rsrp {
    description "Report configuration settings for A6 measurements when trigger quantity is RSRP.";
    leaf offset {
      description "RSRP offset value for event A6 measurements.";
      type erienmnrmgnbcucp:ddt-GNBCUCP_ReportConfigA6Rsrp_offset;
      default 30;
    }
    leaf timeToTrigger {
      description "Time-to-trigger value for RSRP in event A6 measurements.";
      type erienmnrmgnbcucp:ddt-GNBCUCP_ReportConfigA6Rsrp_timeToTrigger;
      default 160;
    }
    leaf hysteresis {
      description "Hysteresis value for RSRP in event A6 measurements.";
      type erienmnrmgnbcucp:ddt-GNBCUCP_ReportConfigA6Rsrp_hysteresis;
      default 10;
    }
  } // end 'grouping struct-ReportConfigA6Rsrp'
  grouping struct-GlobalUniqueAmfId {
    description "Globally Unique AMF Identifier (GUAMI).";
    leaf mnc {
      description "MNC identifies home PLMN of mobile subscription.\nMNC consists of two or three decimal digits. For example, MNC of 001 is not same as MNC of 01.";
      type erienmnrmgnbcucp:ddt-NratCommonLibrary_GlobalUniqueAmfId_mnc;
      default 01;
    }
    leaf amfPointer {
      description "Indicates one or more AMFs within the AMF set.";
      type erienmnrmgnbcucp:ddt-NratCommonLibrary_GlobalUniqueAmfId_amfPointer;
      default 0;
    }
    leaf amfSetId {
      description "Indicates AMF set within the AMF region.";
      type erienmnrmgnbcucp:ddt-NratCommonLibrary_GlobalUniqueAmfId_amfSetId;
      default 0;
    }
    leaf amfRegionId {
      description "Indicates AMF region.";
      type erienmnrmgnbcucp:ddt-NratCommonLibrary_GlobalUniqueAmfId_amfRegionId;
      default 0;
    }
    leaf mcc {
      description "MCC identifies uniquely domicile country of mobile subscriber.\nMCC consists of three decimal digits. The first digit of MCC identifies geographic region. (Values 1 and 8 in the first digit are not allowed.)";
      type erienmnrmgnbcucp:ddt-NratCommonLibrary_GlobalUniqueAmfId_mcc;
      default 001;
    }
  } // end 'grouping struct-GlobalUniqueAmfId'
  grouping struct-LwNeighborRelInfo {
    description "Lightweight representation of an NR neighbor relation.";
    leaf mnc {
      description "MNC identifies home PLMN of mobile subscription.\nMNC consists of two or three decimal digits. For example, MNC of 001 is not same as MNC of 01.";
      type erienmnrmgnbcucp:ddt-GNBCUCP_LwNeighborRelInfo_mnc;
      mandatory true;
    }
    leaf nRPCI {
      description "Physical cell ID of external NR cell.";
      type erienmnrmgnbcucp:ddt-GNBCUCP_LwNeighborRelInfo_nRPCI;
      mandatory true;
    }
    leaf cellLocalId {
      description "Together with gNodeB identifier, identifies an NR cell within PLMN.";
      type erienmnrmgnbcucp:ddt-GNBCUCP_LwNeighborRelInfo_cellLocalId;
      mandatory true;
    }
    leaf gNBId {
      description "Identifies a gNodeB within PLMN.";
      type erienmnrmgnbcucp:ddt-GNBCUCP_LwNeighborRelInfo_gNBId;
      mandatory true;
    }
    leaf mcc {
      description "Mobile Country Code identifies home country of mobile subscriber.\nMCC consists of three decimal digits. The first digit of MCC identifies geographic region. (Values 1 and 8 in the first digit are not allowed.)";
      type erienmnrmgnbcucp:ddt-GNBCUCP_LwNeighborRelInfo_mcc;
      mandatory true;
    }
    leaf gNBIdLength {
      description "Number of bits for encoding gNodeB ID.";
      type erienmnrmgnbcucp:ddt-GNBCUCP_LwNeighborRelInfo_gNBIdLength;
      mandatory true;
    }
  } // end 'grouping struct-LwNeighborRelInfo'
  grouping struct-SliceSelectionAssistInfo {
    description "Single Network Slice Selection Assistance Information (S-NSSAI).";
    leaf sd {
      description "Slice Differentiator (SD).\nIf it is not associated with SST, SD value can be set to 16777215.";
      type erienmnrmgnbcucp:ddt-NratCommonLibrary_SliceSelectionAssistInfo_sd;
      mandatory true;
    }
    leaf sst {
      description "Slice/Service Type (SST).\nValues 0 to 127 belong to standardized SST range and are defined in 3GPP TS 23.501. Values 128 to 255 belong to operator-specific range.";
      type erienmnrmgnbcucp:ddt-NratCommonLibrary_SliceSelectionAssistInfo_sst;
      mandatory true;
    }
  } // end 'grouping struct-SliceSelectionAssistInfo'
  grouping struct-EssCellScPair {
    description "The eNodeB-gNodeB Sector Carrier pair used for ESS operation.";
    leaf gNBessLocalScId {
      description "The gNodeB Local SectorCarrier ID.";
      type erienmnrmgnbcucp:ddt-GNBCUCP_EssCellScPair_gNBessLocalScId;
      default 0;
    }
    leaf essScPairId {
      description "ESS SectorCarrier Pair ID.";
      type erienmnrmgnbcucp:ddt-GNBCUCP_EssCellScPair_essScPairId;
      default 0;
    }
    leaf eNBessLocalScId {
      description "The eNodeB Local SectorCarrier ID.";
      type erienmnrmgnbcucp:ddt-GNBCUCP_EssCellScPair_eNBessLocalScId;
      default 0;
    }
  } // end 'grouping struct-EssCellScPair'
  grouping struct-ReportQuantityCell {
    description "Cell measurement quantities to be included in measurement report.";
    leaf rsrq {
      description "Whether RSRQ quantity is included in measurement report.";
      type boolean;
      default true;
    }
    leaf rsrp {
      description "Whether RSRP quantity is included in measurement report.";
      type boolean;
      default true;
    }
    leaf sinr {
      description "Whether SINR quantity is included in measurement report.";
      type boolean;
      default false;
    }
  } // end 'grouping struct-ReportQuantityCell'
  grouping moc-NRFrequency-keys {
    description "Key(s) for MOC NRFrequency";
    leaf id {
      erienmyext:no-notification;
      description "The value component of the RDN.";
      mandatory true;
      yexte:ecim-name nRFrequencyId;
      type string;
    }
  } // end 'grouping moc-NRFrequency-keys'
  grouping moc-NRFrequency {
    description "NRFrequency and related measurement parameters.\n\nNRFrequencies on the Global Synchronization Channel Raster present a value in attribute gscn.\n\nThe RDN of this MO is NRFrequency=arfcnValueNRDl-smtcScs-smtcPeriodicity-smtcOffset-smtcDuration.\nExample: \"NRFrequency=630000-30-20-0-1\".";
    leaf smtcOffset {
      yexte:restricted;
      description "Offset of the measurement window in which to receive SSBs, given in number of subframes.\nThis attribute is broadcast in SIB2 and SIB4.\n1 subframe = 1 ms.";
      mandatory true;
      yexte:dependencies "smtcOffset < smtcPeriodicity\nMust match nRFrequencyId.";
      type erienmnrmgnbcucp:ddt-GNBCUCP_NRFrequency_smtcOffset;
    }
    leaf gscn {
      config false;
      description "GSCN.\nIf empty SSB is not placed on synchronization raster.";
      notife:notifiable-state-data true;
      type int32;
    }
    leaf smtcDuration {
      yexte:restricted;
      description "Duration of the measurement window in which to receive SSBs, given in number of subframes.\nThis attribute is broadcast in SIB2 and SIB4.\n1 subframe = 1 ms.";
      mandatory true;
      yexte:dependencies "Must match nRFrequencyId.";
      type erienmnrmgnbcucp:ddt-GNBCUCP_NRFrequency_smtcDuration;
    }
    leaf smtcScs {
      yexte:restricted;
      description "Subcarrier Spacing for the SSBs.\nThis attribute is broadcast in SIB4.";
      mandatory true;
      yexte:dependencies "Must match nRFrequencyId.\nIf arfcnValueNRDl is less than 2016667 (FR1), valid smtcScs values are 15 and 30 kHz.\nIf arfcnValueNRDl is greater or equal than 2016667 (FR2), valid smtcScs values are 120 and 240 kHz.";
      type erienmnrmgnbcucp:ddt-GNBCUCP_NRFrequency_smtcScs;
    }
    leaf arfcnValueNRDl {
      yexte:restricted;
      description "Absolute frequency applicable for a downlink NR carrier frequency associated with the SSB.\nThis attribute is broadcast in SIB4.";
      mandatory true;
      yexte:dependencies "Must match nRFrequencyId.";
      type erienmnrmgnbcucp:ddt-GNBCUCP_NRFrequency_arfcnValueNRDl;
    }
    leaf-list reservedBy {
      min-elements 0;
      config false;
      description "Contains a list of MO instances that reserve this MO instance.";
      notife:notifiable-state-data true;
      erienmyext:enm-type MOREF;
      type string;
    }
    leaf-list bandList {
      min-elements 0;
      max-elements 32;
      config false;
      description "List of all NR bands the NRFrequency belongs to.\nCalculated by the system based on arfcnValueNRDl and smtcScs.\nIf configured, bandListManual is used instead of bandList.";
      notife:notifiable-state-data true;
      type erienmnrmgnbcucp:ddt-GNBCUCP_NRFrequency_bandList;
    }
    leaf-list bandListManual {
      min-elements 0;
      max-elements 32;
      description "Configured list of bands to be used by NRFrequency.\nIf present, this list will be used instead of bandList.\nBands specified in bandListManual must be an intersection of possible bands for given NRFrequency configuration.\nPossible bands are displayed in bandList.\nFor example, if bandList contains bands 77 and 78, bandListManual contains either 77, 78, or both 77 and 78.";
      yexte:takes-effect "New connection";
      type erienmnrmgnbcucp:ddt-GNBCUCP_NRFrequency_bandListManual;
    }
    leaf smtcPeriodicity {
      yexte:restricted;
      description "Periodicity of the measurement window in which to receive SSBs, given in number of subframes.\nThis attribute is broadcast in SIB2 and SIB4.\n1 subframe = 1 ms.";
      mandatory true;
      yexte:dependencies "smtcPeriodicity > smtcOffset\nMust match nRFrequencyId.";
      type erienmnrmgnbcucp:ddt-GNBCUCP_NRFrequency_smtcPeriodicity;
    }
  } // end 'grouping moc-NRFrequency'
  grouping moc-UeMeasControl-keys {
    description "Key(s) for MOC UeMeasControl";
    leaf id {
      status deprecated {
        yexte:status-information "Since 20.Q4. Planned to be removed.";
      }
      erienmyext:no-notification;
      description "The value component of the RDN.";
      mandatory true;
      yexte:ecim-name ueMeasControlId;
      type string;
    }
  } // end 'grouping moc-UeMeasControl-keys'
  grouping moc-UeMeasControl {
    description "Manageable characteristics of a cell for UE measurements.\n\nThe RDN of this MO is UeMeasControl=1.";
    leaf sMeasure {
      status deprecated {
        yexte:status-information "Since 20.Q4. Planned to be removed.";
      }
      description "RSRP measurement threshold when UE is required to perform measurements on non-serving cells.\nCorresponds to the RRC parameter s-MeasureConfig.\nIf set to empty, the threshold is not used.\nValue -29 corresponds to special value of SS-RSRP = infinity.";
      yexte:takes-effect "New connection";
      type erienmnrmgnbcucp:ddt-GNBCUCP_UeMeasControl_sMeasure;
    }
    leaf filterCoefficientNrRsrq {
      status deprecated {
        yexte:status-information "Since 20.Q4. Planned to be removed.";
      }
      description "Reference Signal Received Quality (RSRQ) filtering coefficient for NR.\nThe coefficient filters measurements before event evaluation.";
      yexte:takes-effect "New connection";
      type erienmnrmgnbcucp:ddt-GNBCUCP_UeMeasControl_filterCoefficientNrRsrq;
      default 11;
    }
    leaf filterCoefficientNrRsrp {
      status deprecated {
        yexte:status-information "Since 20.Q4. Planned to be removed.";
      }
      description "Reference Signal Received Power (RSRP) filtering coefficient for NR.\nThe coefficient filters measurements before event evaluation.";
      yexte:takes-effect "New connection";
      type erienmnrmgnbcucp:ddt-GNBCUCP_UeMeasControl_filterCoefficientNrRsrp;
      default 4;
    }
  } // end 'grouping moc-UeMeasControl'
  grouping moc-NRFreqRelation-keys {
    description "Key(s) for MOC NRFreqRelation";
    leaf id {
      erienmyext:no-notification;
      description "The value component of the RDN.";
      mandatory true;
      yexte:ecim-name nRFreqRelationId;
      type string;
    }
  } // end 'grouping moc-NRFreqRelation-keys'
  grouping moc-NRFreqRelation {
    description "Mobility relation between NR cell and an NR frequency.\n\nMust use an NRFrequency on the Global Synchronization Channel Raster (indicated in NRFrequency::gscn) for Standalone operation.\nFrequency relation not on the GSCN are not included in SIB4, nor used for PCell mobility.";
    leaf pMax {
      description "Parameter used to calculate Pcompensation at cell reselection.\nCorresponds to parameter PEMAX in 3GPP TS 38.101.\nThis attribute is broadcast in SIB2 or SIB4, depending on whether the related frequency is intra-frequency or inter-frequency.\nThis attribute should be chosen less or equal to 23 dBm.\nIf the attribute is set to empty, value is not broadcast in SIB2 and SIB4 and the UE applies the maximum power according to 3GPP TS 38.101.";
      yexte:takes-effect "Next cell unlock";
      type erienmnrmgnbcucp:ddt-GNBCUCP_NRFreqRelation_pMax;
      default 23;
    }
    leaf plmnRestriction {
      description "Whether PLMN restriction is defined for frequency relation.\nPLMN restriction is defined by attribute plmnIdList.";
      yexte:disturbances "Changing this attribute can cause loss of traffic.";
      yexte:takes-effect "New connection";
      type boolean;
      default false;
    }
    leaf nRFrequencyRef {
      yexte:restricted;
      description "Reference to MO NRFrequency.\nMust be unique among NRFreqRelations under an NRCellCU.";
      mandatory true;
      erienmyext:enm-type MOREF;
      type string;
    }
    leaf tReselectionNR {
      description "Time interval that evaluates the criteria before the reselection can be done.\nThis attribute is broadcast in SIB2 or SIB4, depending on whether the related frequency is intra-frequency or inter-frequency.";
      yexte:takes-effect "Next cell unlock";
      type erienmnrmgnbcucp:ddt-GNBCUCP_NRFreqRelation_tReselectionNR;
      default 2;
    }
    leaf threshXHighQ {
      description "RSRQ threshold level for reselection to higher priority.\nThreshold used by UE when reselecting towards a higher priority frequency X from the actual serving frequency.\nEach frequency of NR can have a specific threshold.\nIf set to empty, value is not broadcast in SIB4.";
      yexte:takes-effect "Next cell unlock";
      yexte:dependencies "Must be empty if NRCellCU::threshServingLowQ is empty or set if NRCellCU::threshServingLowQ is set.";
      type erienmnrmgnbcucp:ddt-GNBCUCP_NRFreqRelation_threshXHighQ;
    }
    leaf threshXHighP {
      description "RSRP threshold level for reselection to higher priority.\nEach frequency of NR can have a specific threshold.";
      yexte:takes-effect "Next cell unlock";
      type erienmnrmgnbcucp:ddt-GNBCUCP_NRFreqRelation_threshXHighP;
      default 4;
    }
    leaf threshXLowP {
      description "RSRP threshold level for reselection to lower priority.\nEach frequency of NR can have a specific threshold.";
      yexte:takes-effect "Next cell unlock";
      type erienmnrmgnbcucp:ddt-GNBCUCP_NRFreqRelation_threshXLowP;
      default 0;
    }
    leaf threshXLowQ {
      description "RSRQ threshold level for reselection to lower priority.\nThe threshold used by the UE when reselecting towards a lower priority frequency X from the current serving frequency.\nEach frequency of NR can have a specific threshold.\nIf the attribute is set to empty the value is not broadcast in SIB.";
      yexte:takes-effect "Next cell unlock";
      yexte:dependencies "Must be empty if NRCellCU::threshServingLowQ is empty or set if NRCellCU::threshServingLowQ is set.";
      type erienmnrmgnbcucp:ddt-GNBCUCP_NRFreqRelation_threshXLowQ;
    }
    list plmnIdList {
      min-elements 0;
      max-elements 15;
      key auto-generated-struct-key;
      leaf auto-generated-struct-key {
        type uint16;
        description "This leaf has been injected to allow for struct instances in a sequence to be ordered.";
        mandatory true;
      }
      description "List of all PLMN IDs allowed for this frequency relation.\n\nOnly applied if attribute plmnRestriction is set to true.\n\nUE that does not support any of the PLMN(s) according to UE Mobility Restriction List is not allowed to use this frequency.\nEmpty list means that no PLMN is allowed to use the frequency.\n\nPLMN ID consists of the following:\n- Mobile Country Code, 3 digits.\n- Mobile Network Code, 2 or 3 digits.";
      erienmyext:enm-type STRUCT;
      uses erienmnrmgnbcucp:struct-PLMNId;
    } // end 'list plmnIdList'
    leaf-list reservedBy {
      min-elements 0;
      config false;
      description "Contains a list of MO instances that reserve this MO instance.";
      notife:notifiable-state-data true;
      erienmyext:enm-type MOREF;
      type string;
    }
    leaf sIntraSearchQ {
      description "Squal threshold indicating when intra-frequency measurements are required.\nIf set to empty, the value is not broadcast in SIB2.";
      yexte:takes-effect "Next cell unlock";
      type erienmnrmgnbcucp:ddt-GNBCUCP_NRFreqRelation_sIntraSearchQ;
    }
    leaf mcpcPCellNrFreqRelProfileRef {
      description "Reference to McpcPCellNrFreqRelProfile MO instance.\nIf reference is non-empty, attributes from referred MO instance are used.\nIf reference is empty, attribute default values according to MO class definition are used.\nReferenced McpcPCellNrFreqRelProfile must be under Mcpc MO under same GNBCUCPFunction as NRCellCU.";
      yexte:takes-effect "Next usage.";
      erienmyext:enm-type MOREF;
      type string;
    }
    leaf qRxLevMin {
      description "Minimum received RSRP level in cell reselection.\nThis attribute is broadcast in SIB2 or SIB4, depending on whether the related frequency is intra-frequency or inter-frequency.\nCorresponds to parameter Qrxlevmin in 3GPP TS 38.304.";
      yexte:takes-effect "New connection";
      type erienmnrmgnbcucp:ddt-GNBCUCP_NRFreqRelation_qRxLevMin;
      default -140;
    }
    leaf sIntraSearchP {
      description "Srxlev threshold indicating when intra-frequency measurements are required.";
      yexte:takes-effect "Next cell unlock";
      type erienmnrmgnbcucp:ddt-GNBCUCP_NRFreqRelation_sIntraSearchP;
      default 62;
    }
    leaf cellReselectionPriority {
      description "Absolute priority of the carrier frequency used by the cell reselection procedure.\nThis attribute is broadcast in SIB2 or SIB4, depending on whether the related frequency is intra-frequency or inter-frequency.\nValue 0 means lowest priority.\nThe value must be unique between RATs. This means that equal priorities between RATs are not supported.";
      yexte:takes-effect "Next cell unlock";
      yexte:dependencies "The cellReselectionPriority must be unique between NRFreqRelations and EUtranFreqRelations under the same NRCellCU.";
      type erienmnrmgnbcucp:ddt-GNBCUCP_NRFreqRelation_cellReselectionPriority;
      default 7;
    }
    leaf qOffsetFreq {
      description "Offset applied when evaluating candidates for cell reselection.";
      yexte:takes-effect "Next cell unlock";
      type erienmnrmgnbcucp:ddt-GNBCUCP_NRFreqRelation_qOffsetFreq;
      default 0;
    }
    leaf qQualMin {
      description "Minimum required quality level RSRQ in the cell.\nThis attribute is broadcast in SIB2 or SIB4, depending on whether the related frequency is intra-frequency or inter-frequency.\nIf the attribute is set to empty, the value is not broadcast in SIB2 or SIB4, and the UE applies the default value of negative infinity for Qqualmin in 3GPP TS 38.304.";
      yexte:takes-effect "Next cell unlock";
      type erienmnrmgnbcucp:ddt-GNBCUCP_NRFreqRelation_qQualMin;
    }
  } // end 'grouping moc-NRFreqRelation'
  grouping moc-PrefUeGroupSelectionProfile-keys {
    description "Key(s) for MOC PrefUeGroupSelectionProfile";
    leaf id {
      status current {
        yexte:preliminary;
      }
      erienmyext:no-notification;
      description "The value component of the RDN.";
      mandatory true;
      yexte:ecim-name prefUeGroupSelectionProfileId;
      type string;
    }
  } // end 'grouping moc-PrefUeGroupSelectionProfile-keys'
  grouping moc-PrefUeGroupSelectionProfile {
    description "A set of preference UE group selection criteria used to define a subset of all UEs.";
    leaf userLabel {
      status current {
        yexte:preliminary;
      }
      description "Label for free use.";
      type erienmnrmgnbcucp:ddt-UserLabel;
    }
    leaf selectionCriteria {
      status current {
        yexte:preliminary;
      }
      description "UE group selection criteria.\nBackus-Naur form defines criteria to decide if a UE belongs to the preference UE group.\nAn empty (\"\") preference UE group selection criteria matches all UEs.\nSyntax:\n<Statement> ::= <ExpressionList> | \"\"\n<ExpressionList> ::= <ExpressionList> <AndOr> <ExpressionList> | \"!\"? \"(\" <ExpressionList> \")\" | \"!\"? <VariableExpression>\n<VariableExpression> ::= <Variable> <RelationalOperator> <Value> | <Variable> \"==\" \"{\" <ValueList> \"}\"\n<ValueList> ::= <Value> \",\" <ValueList> | <Value>\n<Variable> ::= \"5qi\" | \"arp\" | \"cgrole\" | \"imeisv\" | \"plmn\" | \"qci\" | \"rfsp\" | \"snssai\" | \"spid\"\n<AndOr> ::= \"&&\" | \"||\"\n<RelationalOperator> ::= \"==\" | \"!=\" | \"<\" | \"<=\" | \">=\" | \">\"\nA list of possible values can be specified in the form <Variable> == {<value1>, <value2>, ... , <valueN>}. This statement is equivalent to writing (<Variable> == <value1> || <Variable> == <value2> || ... || <Variable> == <valueN>).\nA <Statement> set to the empty string (\"\") always evaluates to true.\nWhitespaces are allowed between every token in the syntax above.\nQuestion mark (?) means zero or one occurrence. For example, \"!\"? makes ! optional.\nAllowed <Value> and <RelationalOperator> depend on <Variable> with limitations given below.\nVariable Definitions\n5qi:\nOperator: one of ==, !=, <=, >=, <, >\nValue: Integer in range 0..255 given in decimal.\narp:\nOpearator: one of ==, !=, <=, >=, <, >\nValue: Integer in range 1..16 given in decimal.\ncgrole:\nOperator: one of ==, !=\nValue: One of mcg or scg.\nimeisv:\nOperator: one of ==, !=\nValue: A string matched by the regular expression [0-9]{16} (16 decimal digits).\nExampleValues: 1234567890123456,0000000000000000, 0123456789012345\nplmn:\nOperator: one of ==, !=\nValue: A string matched by the regular expression [02-79][0-9][0-9]-[0-9][0-9][0-9]?.\nExampleValues: 070-007, 070-07, 234-56\nqci:\nOperator: one of ==, !=, <=, >=, <, >\nValue: Integer in range 0..255 given in decimal.\nrfsp:\nOperator: one of ==, !=, <=, >=, <, >\nValue: Integer in range 1..256 given in decimal.\nsnssai:\nOperator: one of ==, !=, <=, >=, <, >\nValue: Integer in range 0x0..0xffffffff given in hexadecimal.\nspid:\nOperator: one of ==, !=, <=, >=, <, >\nValue: Integer in range 1..256 given in decimal.\n\nOperators\nPrecedence Operator Description\n---------------------------------------------\n1 < Less than\n<= Less than or equal\n> Greater than\n>= Greater than or equal\n== Equal\n!= Not equal\n---------------------------------------------\n2 ! Not\n---------------------------------------------\n3 && And\n---------------------------------------------\n4 || Or\n---------------------------------------------\n\nThe not operator ! negates either the following <VariableExpression> or an <ExpressionList> encapsulated in parenthesis.\nTherefore, the expression !a==b && c==d is equivalent to ((!(a==b)) && (c==d)) and different from !(a==b && c==d).\nExpression !a==b and !(a==b) are equivalent.\nSince operator && operator has higher precedence than ||, a<b || a<c && c<d is equivalent to (a<b || (a<c && c<d)). To change the order of operations, surround the expression with parentheses (...) as (a<b || a<c) && c<d to force || to be evaluated first.\n\nExamples\nSimple one valued expressions:\nplmnid == 234-56\nspid == 1\ncgrole == mcg\narp > 3\nsnssai == 0xfedcba98\nValue list expressions:\nspid == {8,9,10,1,155}\n!plmnid == {234-56, 434-567}\nEquivalent expressions using ||:\n(spid == 8 || spid == 9 || spid == 10 || spid == 1 || spid == 155)\n!(plmnid == 234-56 || plmnid == 434-567)\nMixed examples:\nspid == 1 && cgrole == mcg\n!(spid != 1 || cgrole != mcg)\n(spid == 8 || spid == 9 || spid == 10 || spid == 1 || spid == 155) && (plmnid == 234-56 || plmnid == 434-567)";
      yexte:disturbances "Changing this attribute can cause loss of traffic.";
      yexte:takes-effect "New connection";
      type erienmnrmgnbcucp:ddt-GNBCUCP_PrefUeGroupSelectionProfile_selectionCriteria;
    }
    leaf prefUeGroupId {
      status current {
        yexte:preliminary;
      }
      description "Preference UE group identifier.\nMust be unique among PrefUeGroupSelectionProfile MO instances.";
      mandatory true;
      yexte:disturbances "Changing this attribute can cause loss of traffic.";
      yexte:takes-effect "New connection";
      type erienmnrmgnbcucp:ddt-GNBCUCP_PrefUeGroupSelectionProfile_prefUeGroupId;
    }
    leaf prefUeGroupPriority {
      status current {
        yexte:preliminary;
      }
      description "Relative priority among preference UE groups.\nMust be unique among PrefUeGroupSelectionProfile MO instances.\nIf UE fulfills more than one prefUeGroupSelectionProfile, prefUeGroupSelectionProfile with the highest relative prefUeGroupPriority is applied. Higher value of prefUeGroupPriority gives higher priority.";
      mandatory true;
      yexte:disturbances "Changing this attribute can cause loss of traffic.";
      yexte:takes-effect "New connection";
      type erienmnrmgnbcucp:ddt-GNBCUCP_PrefUeGroupSelectionProfile_prefUeGroupPriority;
    }
  } // end 'grouping moc-PrefUeGroupSelectionProfile'
  grouping moc-Mcpc-keys {
    description "Key(s) for MOC Mcpc";
    leaf id {
      erienmyext:no-notification;
      description "The value component of the RDN.";
      mandatory true;
      yexte:ecim-name mcpcId;
      type string;
    }
  } // end 'grouping moc-Mcpc-keys'
  grouping moc-Mcpc {
    description "Configuration of Mobility Control at Poor Coverage (MCPC) and container for MCPC profiles.\n\nThe RDN of this MO must always be Mcpc=1.";
  } // end 'grouping moc-Mcpc'
  grouping moc-NRCellRelation-keys {
    description "Key(s) for MOC NRCellRelation";
    leaf id {
      erienmyext:no-notification;
      description "The value component of the RDN.";
      mandatory true;
      yexte:ecim-name nRCellRelationId;
      type string;
    }
  } // end 'grouping moc-NRCellRelation-keys'
  grouping moc-NRCellRelation {
    description "Handover relationship between NR cell and a neighboring NR cell.";
    leaf isHoAllowed {
      description "Specifies if handover between the cells in this relation is allowed.";
      type boolean;
      default true;
    }
    leaf ribtmStatusActive {
      config false;
      description "Status of Radio Interface Based Time Monitoring for this NRCellRelation.\nIf empty, status is false.";
      notife:notifiable-state-data true;
      type boolean;
    }
    leaf timeOfCreation {
      erienmyext:no-notification;
      config false;
      description "Time and date of MO creation.\nFormat: YYYY-MM-DD HH:MM:SS.";
      type erienmnrmgnbcucp:ddt-GNBCUCP_NRCellRelation_timeOfCreation;
    }
    leaf nRCellRef {
      yexte:restricted;
      description "Reference to an instance of NRCellCU or ExternalNRCellCU MO.";
      mandatory true;
      erienmyext:enm-type MOREF;
      type string;
    }
    leaf ribtmEnabled {
      description "Whether Radio Interface Based Time Monitoring for this NRCellRelation is enabled.\nOnly takes effect when Radio Interface Based Time Monitoring feature is enabled.";
      yexte:takes-effect "Immediately if MO existed at last parent cell unlock, otherwise at next parent cell unlock.";
      type boolean;
      default false;
    }
    leaf includeInSIB {
      description "Whether cell is included in System Information.\nValue false means cell is not included in intra-frequency neighboring or black cell list in SIB3 or SIB4.";
      yexte:takes-effect "Next cell unlock";
      type boolean;
      default true;
    }
    leaf caStatusInfo {
      config false;
      description "Additional status information when caStatusActive is false.\nEmpty when caStatusActive is true or additional status information is unavailable.";
      notife:notifiable-state-data true;
      type erienmnrmgnbcucp:enum-CaStatusCause;
    }
    leaf caStatusActive {
      config false;
      description "Active status of carrier aggregation for this NRCellRelation.";
      notife:notifiable-state-data true;
      type boolean;
    }
    leaf caStatus {
      status obsolete {
        yexte:status-information "Since 20.Q3. Planned to be removed.";
      }
      config false;
      description "Whether neighbor cell can serve as Scell for carrier aggregation.";
      notife:notifiable-state-data true;
      type erienmnrmgnbcucp:enum-CaStatus;
    }
    leaf sCellCandidate {
      description "SCell candidate status.\nWhether cell referenced by nRCellRef can be SCell for carrier aggregation.";
      type erienmnrmgnbcucp:enum-SCellCandidate;
      default NOT_ALLOWED;
    }
    leaf nRFreqRelationRef {
      yexte:restricted;
      description "Reference to NRFreqRelation MO under the same parent NRCellCU.";
      mandatory true;
      erienmyext:enm-type MOREF;
      type string;
    }
    leaf createdBy {
      config false;
      description "Whether MO is created by the ANR function or operator.";
      notife:notifiable-state-data true;
      type erienmnrmgnbcucp:enum-CreatedByGutran;
    }
    leaf isRemoveAllowed {
      description "Whether ANR function is allowed to remove this object.\nThe setting does not restrict operator removal of the object. Objects created by ANR have this parameter set to true initially.";
      type boolean;
      default false;
    }
    leaf cellIndividualOffsetNR {
      description "Offset value for neighbor cell.\nUsed when UE is in connected mode.";
      yexte:takes-effect "New connection";
      type erienmnrmgnbcucp:ddt-GNBCUCP_NRCellRelation_cellIndividualOffsetNR;
      default 0;
    }
    leaf coverageIndicator {
      description "Coverage indication.\nRelation between coverage area of cell referenced by nRCellRef and current cell. Can be:\n- overlap\n- referenced cell contains current cell\n- current cell contains reference cell";
      type erienmnrmgnbcucp:enum-SupportedCoverage;
      default NONE;
    }
  } // end 'grouping moc-NRCellRelation'
  grouping moc-UeGroupSelectionProfile-keys {
    description "Key(s) for MOC UeGroupSelectionProfile";
    leaf id {
      status current {
        yexte:preliminary;
      }
      erienmyext:no-notification;
      description "The value component of the RDN.";
      mandatory true;
      yexte:ecim-name ueGroupSelectionProfileId;
      type string;
    }
  } // end 'grouping moc-UeGroupSelectionProfile-keys'
  grouping moc-UeGroupSelectionProfile {
    description "A set of UE group selection criteria used to define a subset of all UEs.";
    leaf userLabel {
      status current {
        yexte:preliminary;
      }
      description "Label for free use.";
      type erienmnrmgnbcucp:ddt-UserLabel;
    }
    leaf selectionCriteria {
      status current {
        yexte:preliminary;
      }
      description "UE group selection criteria.\nBackus-Naur form defines criteria to decide if a UE belongs to the UE group.\nAn empty (\"\") UE group selection criteria matches all UEs.\nSyntax:\n<Statement> ::= <ExpressionList> | \"\"\n<ExpressionList> ::= <ExpressionList> <AndOr> <ExpressionList> | \"!\"? \"(\" <ExpressionList> \")\" | \"!\"? <VariableExpression>\n<VariableExpression> ::= <Variable> <RelationalOperator> <Value> | <Variable> \"==\" \"{\" <ValueList> \"}\"\n<ValueList> ::= <Value> \",\" <ValueList> | <Value>\n<Variable> ::= \"5qi\" | \"arp\" | \"cgrole\" | \"imeisv\" | \"plmn\" | \"qci\" | \"rfsp\" | \"snssai\" | \"spid\"\n<AndOr> ::= \"&&\" | \"||\"\n<RelationalOperator> ::= \"==\" | \"!=\" | \"<\" | \"<=\" | \">=\" | \">\"\nA list of possible values can be specified in the form <Variable> == {<value1>, <value2>, ... , <valueN>}. This statement is equivalent to writing (<Variable> == <value1> || <Variable> == <value2> || ... || <Variable> == <valueN>).\nA <Statement> set to the empty string (\"\") always evaluates to true.\nWhitespaces are allowed between every token in the syntax above.\nQuestion mark (?) means zero or one occurrence. For example, \"!\"? makes ! optional.\nAllowed <Value> and <RelationalOperator> depend on <Variable> with limitations given below.\nVariable Definitions\n5qi:\nOperator: one of ==, !=, <=, >=, <, >\nValue: Integer in range 0..255 given in decimal.\narp:\nOpearator: one of ==, !=, <=, >=, <, >\nValue: Integer in range 1..16 given in decimal.\ncgrole:\nOperator: one of ==, !=\nValue: One of mcg or scg.\nimeisv:\nOperator: one of ==, !=\nValue: A string matched by the regular expression [0-9]{16} (16 decimal digits).\nExampleValues: 1234567890123456,0000000000000000, 0123456789012345\nplmn:\nOperator: one of ==, !=\nValue: A string matched by the regular expression [02-79][0-9][0-9]-[0-9][0-9][0-9]?.\nExampleValues: 070-007, 070-07, 234-56\nqci:\nOperator: one of ==, !=, <=, >=, <, >\nValue: Integer in range 0..255 given in decimal.\nrfsp:\nOperator: one of ==, !=, <=, >=, <, >\nValue: Integer in range 1..256 given in decimal.\nsnssai:\nOperator: one of ==, !=, <=, >=, <, >\nValue: Integer in range 0x0..0xffffffff given in hexadecimal.\nspid:\nOperator: one of ==, !=, <=, >=, <, >\nValue: Integer in range 1..256 given in decimal.\n\nOperators\nPrecedence Operator Description\n---------------------------------------------\n1 < Less than\n<= Less than or equal\n> Greater than\n>= Greater than or equal\n== Equal\n!= Not equal\n---------------------------------------------\n2 ! Not\n---------------------------------------------\n3 && And\n---------------------------------------------\n4 || Or\n---------------------------------------------\n\nThe not operator ! negates either the following <VariableExpression> or an <ExpressionList> encapsulated in parenthesis.\nTherefore, the expression !a==b && c==d is equivalent to ((!(a==b)) && (c==d)) and different from !(a==b && c==d).\nExpression !a==b and !(a==b) are equivalent.\nSince operator && operator has higher precedence than ||, a<b || a<c && c<d is equivalent to (a<b || (a<c && c<d)). To change the order of operations, surround the expression with parentheses (...) as (a<b || a<c) && c<d to force || to be evaluated first.\n\nExamples\nSimple one valued expressions:\nplmnid == 234-56\nspid == 1\ncgrole == mcg\narp > 3\nsnssai == 0xfedcba98\nValue list expressions:\nspid == {8,9,10,1,155}\n!plmnid == {234-56, 434-567}\nEquivalent expressions using ||:\n(spid == 8 || spid == 9 || spid == 10 || spid == 1 || spid == 155)\n!(plmnid == 234-56 || plmnid == 434-567)\nMixed examples:\nspid == 1 && cgrole == mcg\n!(spid != 1 || cgrole != mcg)\n(spid == 8 || spid == 9 || spid == 10 || spid == 1 || spid == 155) && (plmnid == 234-56 || plmnid == 434-567)";
      yexte:disturbances "Changing this attribute can cause loss of traffic.";
      yexte:takes-effect "New connection";
      type erienmnrmgnbcucp:ddt-GNBCUCP_UeGroupSelectionProfile_selectionCriteria;
    }
    leaf selectionProbability {
      status current {
        yexte:preliminary;
      }
      description "Selection probability for AB testing.\nProbability for UE to be selected into this UeGroup after fulfilling all selection conditions according to the configured selectionCriteria.";
      yexte:takes-effect "New connection";
      type erienmnrmgnbcucp:ddt-GNBCUCP_UeGroupSelectionProfile_selectionProbability;
      default 100;
    }
    leaf ueGroupId {
      status current {
        yexte:preliminary;
      }
      description "UE group identifier.\nMust be unique among UeGroupSelectionProfile MO instances.";
      mandatory true;
      yexte:disturbances "Changing this attribute can cause loss of traffic.";
      yexte:takes-effect "New connection";
      type erienmnrmgnbcucp:ddt-GNBCUCP_UeGroupSelectionProfile_ueGroupId;
    }
    leaf ueGroupPriority {
      status current {
        yexte:preliminary;
      }
      description "Relative priority among UE groups.\nMust be unique among UeGroupSelectionProfile MO instances.\nIf UE fulfills more than one ueGroupSelectionProfile, ueGroupSelectionProfile with the highest relative ueGroupPriority is applied. Higher value of ueGroupPriority gives higher priority.";
      mandatory true;
      yexte:disturbances "Changing this attribute can cause loss of traffic.";
      yexte:takes-effect "New connection";
      type erienmnrmgnbcucp:ddt-GNBCUCP_UeGroupSelectionProfile_ueGroupPriority;
    }
  } // end 'grouping moc-UeGroupSelectionProfile'
  grouping moc-AdditionalPLMNInfo-keys {
    description "Key(s) for MOC AdditionalPLMNInfo";
    leaf id {
      erienmyext:no-notification;
      description "The value component of the RDN.";
      mandatory true;
      yexte:ecim-name additionalPLMNInfoId;
      type string;
    }
  } // end 'grouping moc-AdditionalPLMNInfo-keys'
  grouping moc-AdditionalPLMNInfo {
    description "PLMN-related Information that can be additionally served by NR cell.\n\nCreated by system when F1 interface is set up or configuration is updated by GNBDUFunction.\nDeleted by system when configuration is updated by GNBDUFunction.\n\nThe RDNs of these MOs are AdditionalPLMNInfo=1 to AdditionalPLMNInfo=11.";
    leaf nRTAC {
      config false;
      description "NR Tracking Area Code (TAC).";
      notife:notifiable-state-data true;
      type int32;
    }
    list pLMNIdList {
      min-elements 1;
      max-elements 12;
      key auto-generated-struct-key;
      leaf auto-generated-struct-key {
        type uint16;
        description "This leaf has been injected to allow for struct instances in a sequence to be ordered.";
        mandatory true;
      }
      description "List of supported PLMNs.";
      erienmyext:enm-type STRUCT;
      uses erienmnrmgnbcucp:struct-PLMNId;
    } // end 'list pLMNIdList'
  } // end 'grouping moc-AdditionalPLMNInfo'
  grouping moc-EmCall-keys {
    description "Key(s) for MOC EmCall";
    leaf id {
      erienmyext:no-notification;
      description "The value component of the RDN.";
      mandatory true;
      yexte:ecim-name emCallId;
      type string;
    }
  } // end 'grouping moc-EmCall-keys'
  grouping moc-EmCall {
    description "Emergency call configuration for NRCellCU MOs.";
    leaf userLabel {
      description "Label for free use.";
      type erienmnrmgnbcucp:ddt-UserLabel;
    }
    leaf-list arpEmCallList {
      min-elements 0;
      max-elements 15;
      description "Allocation and Retention Priority (ARP) priority level values used for emergency calls.\nIf empty, no ARP priority level is interpreted as emergency call.";
      type erienmnrmgnbcucp:ddt-GNBCUCP_EmCall_arpEmCallList;
    }
    list pLMNIdList {
      min-elements 0;
      max-elements 12;
      key auto-generated-struct-key;
      leaf auto-generated-struct-key {
        type uint16;
        description "This leaf has been injected to allow for struct instances in a sequence to be ordered.";
        mandatory true;
      }
      description "PLMNs for which parameters are valid.\n\nIf empty, parameters are valid for all PLMNs.";
      erienmyext:enm-type STRUCT;
      uses erienmnrmgnbcucp:struct-PLMNId;
    } // end 'list pLMNIdList'
  } // end 'grouping moc-EmCall'
  grouping moc-ResourcePartition-keys {
    description "Key(s) for MOC ResourcePartition";
    leaf id {
      erienmyext:no-notification;
      description "The value component of the RDN.";
      mandatory true;
      yexte:ecim-name resourcePartitionId;
      type string;
    }
  } // end 'grouping moc-ResourcePartition-keys'
  grouping moc-ResourcePartition {
    description "Combination of attributes specifying in which resource partition a UE is included.";
    leaf-list reservedBy {
      min-elements 0;
      config false;
      description "Contains a list of MO instances that reserve this MO instance.\nCurrently not used.";
      notife:notifiable-state-data true;
      erienmyext:enm-type MOREF;
      type string;
    }
    leaf related5qiTableRef {
      description "Reference to CUCP5qiTable MO instance.";
      yexte:takes-effect "New connection";
      yexte:dependencies "If non-empty, ResourcePartitionMember::endpointResourceRef must be empty.";
      erienmyext:enm-type MOREF;
      type string;
    }
    leaf resourcePartitionName {
      description "Name of a resource partition.";
      type erienmnrmgnbcucp:ddt-GNBCUCP_ResourcePartition_resourcePartitionName;
    }
  } // end 'grouping moc-ResourcePartition'
  grouping moc-EndpointResource-keys {
    description "Key(s) for MOC EndpointResource";
    leaf id {
      erienmyext:no-notification;
      description "The value component of the RDN.";
      mandatory true;
      yexte:ecim-name endpointResourceId;
      type string;
    }
  } // end 'grouping moc-EndpointResource-keys'
  grouping moc-EndpointResource {
    description "Transport network endpoints for RAN interfaces.\n\nConfiguration is valid for an entity that refers to an instance of this MO.";
    leaf userLabel {
      description "Label for free use.";
      type erienmnrmgnbcucp:ddt-UserLabel;
    }
    leaf-list reservedBy {
      min-elements 0;
      config false;
      description "Contains a list of MO instances that reserve this MO instance.";
      notife:notifiable-state-data true;
      erienmyext:enm-type MOREF;
      type string;
    }
  } // end 'grouping moc-EndpointResource'
  grouping moc-TermPointToAmf-keys {
    description "Key(s) for MOC TermPointToAmf";
    leaf id {
      erienmyext:no-notification;
      description "The value component of the RDN.";
      mandatory true;
      yexte:ecim-name termPointToAmfId;
      type string;
    }
  } // end 'grouping moc-TermPointToAmf-keys'
  grouping moc-TermPointToAmf {
    description "Models an NG link AMF termination point.";
    leaf usedIpAddress {
      config false;
      description "The destination address used for initialization of the underlying SCTP association.\nContains the address of the latest successful NGAP Setup.\nThe IP address can be an IPv4 or an IPv6 address.";
      notife:notifiable-state-data true;
      type erienmnrmgnbcucp:ddt-GNBCUCP_TermPointToAmf_usedIpAddress;
    }
    leaf ipv4Address2 {
      description "Secondary IPv4 address of AMF for NG-C interface.\nThe input format is four fields of digits, separated by dots. Each field consists of three digits. The value of each field must be in the range 0-255.";
      yexte:takes-effect "Next MO unlock";
      yexte:precondition "Value can only be changed if administrativeState is LOCKED.";
      type erienmnrmgnbcucp:ddt-GNBCUCP_TermPointToAmf_ipv4Address2;
      default 0.0.0.0;
    }
    leaf ipv4Address1 {
      description "Primary IPv4 address of AMF for NG-C interface.\nThe input format is four fields of digits, separated by dots. Each field consists of three digits. The value of each field must be in the range 0-255.";
      yexte:takes-effect "Next MO unlock";
      yexte:precondition "Value can only be changed if administrativeState is LOCKED.";
      type erienmnrmgnbcucp:ddt-GNBCUCP_TermPointToAmf_ipv4Address1;
      default 0.0.0.0;
    }
    leaf pwsRestartHandling {
      description "Whether the NG-C link is used to send restart and failure messages related to PWS.\nNote: If set to ENABLED but no connection exists between AMF and CBC function, the PWS restart and failure messages are lost.";
      yexte:disturbances "Changing this attribute can prevent sending PWS restart and failure messages to an AMF.";
      yexte:takes-effect "Next PWS restart or failure message to be transmitted on the NG-C interface. Does not affect ongoing PWS broadcast.";
      type erienmnrmgnbcucp:enum-PWSRestartHandling;
      default DISABLED;
    }
    leaf defaultAmf {
      description "Whether the TermPointToAmf instance is a default AMF or not.";
      yexte:takes-effect "Next MO unlock";
      yexte:precondition "Value can only be changed if administrativeState is LOCKED.";
      type boolean;
      default true;
    }
    leaf ipv6Address1 {
      description "Primary IPv6 address of AMF for NG-C interface.\nThe input format is eight fields, separated by colons.\nEach field consists of four hexadecimal characters. The value of each field must be in the range 0-FFFF.\nLeading zeroes can be omitted in a field, and multiple groups of 16 bits of zeroes can be compressed to ::. The :: can be used only once in an address.";
      yexte:takes-effect "Next MO unlock";
      yexte:precondition "Value can only be changed if administrativeState is LOCKED.";
      type erienmnrmgnbcucp:ddt-GNBCUCP_TermPointToAmf_ipv6Address1;
      default ::;
    }
    leaf ipv6Address2 {
      description "Secondary IPv6 address of AMF for NG-C interface.\nThe input format is eight fields, separated by colons.\nEach field consists of four hexadecimal characters. The value of each field must be in the range 0-FFFF.\nLeading zeroes can be omitted in a field, and multiple groups of 16 bits of zeroes can be compressed to ::. The :: can be used only once in an address.";
      yexte:takes-effect "Next MO unlock";
      yexte:precondition "Value can only be changed if administrativeState is LOCKED.";
      type erienmnrmgnbcucp:ddt-GNBCUCP_TermPointToAmf_ipv6Address2;
      default ::;
    }
    list sNSSAIList {
      min-elements 0;
      max-elements 1024;
      key auto-generated-struct-key;
      leaf auto-generated-struct-key {
        type uint16;
        description "This leaf has been injected to allow for struct instances in a sequence to be ordered.";
        mandatory true;
      }
      description "List of supported network slices.";
      erienmyext:enm-type STRUCT;
      uses erienmnrmgnbcucp:struct-SliceSelectionAssistInfo;
    } // end 'list sNSSAIList'
    leaf administrativeState {
      description "The administrative state.\nIf set to SHUTTINGDOWN, the state is immediately brought to LOCKED.";
      type erienmnrmgnbcucp:enum-AdmState;
      default LOCKED;
    }
    leaf domainName {
      description "Fully qualified domain name of AMF.\nConsists of one or more labels, separated by dots (.).\nValid characters for labels are limited to letters a - z, A - Z, digits 0 - 9, and character - (dash). Character case is preserved. Length of labels cannot exceed 255 characters.\nNOTE: First and last character in domain name cannot be the character - (dash).\nFor more information, see RFC 952, 1101 and 1123.";
      yexte:takes-effect "Next MO unlock";
      yexte:precondition "Value can only be changed if administrativeState is LOCKED.";
      type erienmnrmgnbcucp:ddt-GNBCUCP_TermPointToAmf_domainName;
    }
    leaf pwsCapable {
      status obsolete {
        yexte:status-information "Since 20.Q3. Planned to be removed.";
      }
      description "Whether the NG-C link is capable of receiving and sending messages related to PWS.";
      yexte:disturbances "Changing this attribute can prevent handling of PWS messages.";
      yexte:takes-effect "Next PWS related message received or transmitted on the NG-C interface. Does not affect ongoing PWS broadcast.";
      type boolean;
      default false;
    }
    leaf relativeCapacity {
      config false;
      description "Relative processing capacity of an AMF to other AMFs in pool.\nCapacity is used to balance the load between AMFs in a pool.";
      notife:notifiable-state-data true;
      type erienmnrmgnbcucp:ddt-GNBCUCP_TermPointToAmf_relativeCapacity;
    }
    leaf amfName {
      config false;
      description "Used by ENM to identify an AMF.\nSet by RBS at NG-SETUP.";
      notife:notifiable-state-data true;
      type string;
    }
    leaf-list availabilityStatus {
      min-elements 0;
      config false;
      description "The availability status.\nIt contains details about operationalState.";
      notife:notifiable-state-data true;
      type erienmnrmgnbcucp:enum-AvailStatus;
    }
    leaf operationalState {
      config false;
      description "The operational state.";
      notife:notifiable-state-data true;
      type erienmnrmgnbcucp:enum-OperState;
    }
    list servedGuamiList {
      min-elements 0;
      max-elements 256;
      key auto-generated-struct-key;
      leaf auto-generated-struct-key {
        type uint16;
        description "This leaf has been injected to allow for struct instances in a sequence to be ordered.";
        mandatory true;
      }
      description "List of Globally Unique AMF IDs (GUAMIs) served by this AMF.";
      erienmyext:enm-type STRUCT;
      uses erienmnrmgnbcucp:struct-GlobalUniqueAmfId;
    } // end 'list servedGuamiList'
    container operatorPLMNId {
      description "PLMN identifier used as a part of Global RAN Node ID.\n\nIf set to empty, pLMNId on GNBCUCPFunction MO will be used.";
      erienmyext:enm-type STRUCT;
      uses erienmnrmgnbcucp:struct-PLMNId;
    } // end 'container operatorPLMNId'
    list pLMNIdList {
      min-elements 0;
      max-elements 12;
      key auto-generated-struct-key;
      leaf auto-generated-struct-key {
        type uint16;
        description "This leaf has been injected to allow for struct instances in a sequence to be ordered.";
        mandatory true;
      }
      description "PLMNs that can be served by this AMF.";
      erienmyext:enm-type STRUCT;
      uses erienmnrmgnbcucp:struct-PLMNId;
    } // end 'list pLMNIdList'
  } // end 'grouping moc-TermPointToAmf'
  grouping moc-TermPointToGNodeB-keys {
    description "Key(s) for MOC TermPointToGNodeB";
    leaf id {
      erienmyext:no-notification;
      description "The value component of the RDN.";
      mandatory true;
      yexte:ecim-name termPointToGNodeBId;
      type string;
    }
  } // end 'grouping moc-TermPointToGNodeB-keys'
  grouping moc-TermPointToGNodeB {
    description "Local gNodeB termination point of Xn link between gNodeB and neighbor gNodeB.\n\nWhen created by the system, the RDN of this MO is TermPointToGNodeB=auto1.";
    leaf ipsecEpAddress {
      description "Outer IP address of X2 or Xn neighbor.\nDefined if direct IPsec VPN connection is to be established with X2 or Xn neighbor.\nIPv4 or IPv6 address.\nFor IPv4, input format is four fields of digits separated by dots. Each field consists of up to three digits. Values range from 0 to 255.\nFor IPv6, input format is eight fields separated by colons. Each field consists of up to four hexadecimal characters. Values range from 0 to FFFF.\nLeading zeroes can be omitted in a field.\nMultiple groups of 16 bits of zeroes can be indicated with the :: compression. This can appear once in address.\nThis attribute is for future use.";
      yexte:disturbances "Changing this attribute can cause loss of traffic.";
      yexte:takes-effect "Next MO unlock";
      yexte:precondition "To set this attribute, administrativeState must be LOCKED.";
      type erienmnrmgnbcucp:ddt-GNBCUCP_TermPointToGNodeB_ipsecEpAddress;
    }
    leaf usedIpAddress {
      config false;
      description "Destination address used in underlying SCTP association.";
      notife:notifiable-state-data true;
      type string;
    }
    leaf ipv6Address {
      description "IPv6 address of the peer gNodeB.\nEight fields, separated by colons.\nEach field consists of up to four hexadecimal characters. Value of each field is in range 0-FFFF.\nLeading zeroes can be omitted in a field, and multiple groups of 16 bits of zeroes can be compressed to ::\nThe :: can appear only once in an address.";
      yexte:takes-effect "Next MO unlock";
      yexte:precondition "Value can only be changed if administrativeState is LOCKED.";
      type erienmnrmgnbcucp:ddt-GNBCUCP_TermPointToGNodeB_ipv6Address;
      default ::;
    }
    leaf administrativeState {
      description "The administrative state.";
      yexte:disturbances "Changing this attribute to LOCKED causes loss of traffic.";
      type erienmnrmgnbcucp:enum-AdmState;
      default LOCKED;
    }
    leaf ipv4Address {
      description "IPv4 address of the peer gNodeB.\nFour fields, separated by dots.\nEach field consists of up to three digits. The value of each field is in the range 0-255.";
      yexte:takes-effect "Next MO unlock";
      yexte:precondition "Value can only be changed if administrativeState is LOCKED.";
      type erienmnrmgnbcucp:ddt-GNBCUCP_TermPointToGNodeB_ipv4Address;
      default 0.0.0.0;
    }
    leaf-list availabilityStatus {
      min-elements 0;
      config false;
      description "The availability status.\nIt contains details about operationalState.";
      notife:notifiable-state-data true;
      type erienmnrmgnbcucp:enum-AvailStatus;
    }
    leaf operationalState {
      config false;
      description "The operational state.";
      notife:notifiable-state-data true;
      type erienmnrmgnbcucp:enum-OperState;
    }
    leaf upIpAddress {
      description "User plane address of X2 or Xn neighbor.\nRequired if direct IPsec VPN connection is to be established with X2 or Xn neighbor and different IP addresses for user plane and control plane.\nIPv4 or IPv6 address.\nFor IPv4, input format is four fields of digits separated by dots. Each field consists of up to three digits. Values range from 0 to 255.\nFor IPv6, input format is eight fields separated by colons. Each field consists of up to four hexadecimal characters. Values range from 0 to FFFF.\nLeading zeroes can be omitted in a field.\nMultiple groups of 16 bits of zeroes can be indicated with the :: compression. This can appear once in address.\nThis attribute is for future use.";
      yexte:disturbances "Changing this attribute can cause loss of traffic.";
      yexte:takes-effect "Next MO unlock";
      yexte:precondition "To set this attribute, administrativeState must be LOCKED.";
      type erienmnrmgnbcucp:ddt-GNBCUCP_TermPointToGNodeB_upIpAddress;
    }
  } // end 'grouping moc-TermPointToGNodeB'
  grouping moc-CUCPResourcePartitions-keys {
    description "Key(s) for MOC CUCPResourcePartitions";
    leaf id {
      status obsolete {
        yexte:status-information "Since 20.Q2. Deprecated: Since 19.Q4. Planned to be removed.";
      }
      erienmyext:no-notification;
      description "The value component of the RDN.";
      mandatory true;
      yexte:ecim-name cUCPResourcePartitionsId;
      type string;
    }
  } // end 'grouping moc-CUCPResourcePartitions-keys'
  grouping moc-CUCPResourcePartitions {
    description "Set of resource partitions.";
  } // end 'grouping moc-CUCPResourcePartitions'
  grouping moc-McpcPSCellProfile-keys {
    description "Key(s) for MOC McpcPSCellProfile";
    leaf id {
      erienmyext:no-notification;
      description "The value component of the RDN.";
      mandatory true;
      yexte:ecim-name mcpcPSCellProfileId;
      type string;
    }
  } // end 'grouping moc-McpcPSCellProfile-keys'
  grouping moc-McpcPSCellProfile {
    description "Mobility Control at Poor Coverage (MCPC) for PSCell.\n\nApplies to UEs which use the cell as PSCell. Attributes are used on cell level.\n\nMCPC for PSCell is enabled per NRCellCU MO by setting NRCellCU::mcpcPSCellEnabled attribute.\nIf NRCellCU::mcpcPSCellProfileRef is non-empty, attributes from referred MO instance are used.\nIf NRCellCU::mcpcPSCellProfileRef is empty, attribute default values according to MO class definition are used.\n\nThe option to create McpcPSCellProfile MO under NRCellCU is obsolete since 20.Q4 and that option will be removed.";
    leaf rsrpCriticalEnabled {
      description "Whether RSRP measurements for detecting critical coverage is enabled.\nRSRP measurement criteria for detecting critical coverage is defined by attribute rpspCritical.";
      yexte:disturbances "Changing this attribute to true can trigger release of NR resources if UE measurement event condition defined by rsrpCritical attribute is been fulfilled.";
      yexte:takes-effect "Next usage.";
      type boolean;
      default false;
    }
    leaf-list reservedBy {
      min-elements 0;
      config false;
      description "Contains a list of MO instances that reserve this MO instance.";
      notife:notifiable-state-data true;
      erienmyext:enm-type MOREF;
      type string;
    }
    container rsrpCritical {
      description "RSRP measurement report criteria for detecting critical coverage.\n\nOnly applied if attribute rsrpCriticalEnabled is set to true.";
      erienmyext:enm-type STRUCT;
      uses erienmnrmgnbcucp:struct-ReportConfigA1A2Rsrp;
    } // end 'container rsrpCritical'
  } // end 'grouping moc-McpcPSCellProfile'
  grouping moc-QciProfileEndcConfigExt-keys {
    description "Key(s) for MOC QciProfileEndcConfigExt";
    leaf id {
      erienmyext:no-notification;
      description "The value component of the RDN.";
      mandatory true;
      yexte:ecim-name qciProfileEndcConfigExtId;
      type string;
    }
  } // end 'grouping moc-QciProfileEndcConfigExt-keys'
  grouping moc-QciProfileEndcConfigExt {
    description "Managing QoS-related parameters for Data Radio Bearers in EN-DC.\n\nExtension of the configuration in MO class QciProfileEndcConfig.\n\nThe RDN of this MO is QciProfileEndcConfigExt=1.";
    leaf-list rlcModeQciUM {
      min-elements 0;
      max-elements 10;
      status deprecated {
        yexte:status-information "Since 20.Q3. Replaced by CUCP5qi::rlcMode. Planned to be removed.";
      }
      description "List of QCIs that use RLC UM.\nQCIs not listed use RLC AM.";
      yexte:takes-effect "New connection";
      type erienmnrmgnbcucp:ddt-GNBCUCP_QciProfileEndcConfigExt_rlcModeQciUM;
    }
    leaf tReorderingUlPdcp {
      status deprecated {
        yexte:status-information "Since 20.Q3. Replaced by CUCP5qi::tReorderingUl. Planned to be removed.";
      }
      description "Short timer that detects loss of PDCP uplink data units.\nUsed by receiving end of AM or UM PDCP entity. When timer expires, received packets are delivered to higher layers.\nDifferent values are set based on purpose of optimization and bearer type.\nBased on purpose of optimization and the bearer type, different values are set.";
      yexte:takes-effect "New connection";
      type erienmnrmgnbcucp:ddt-GNBCUCP_QciProfileEndcConfigExt_tReorderingUlPdcp;
      default 200;
    }
    leaf initialUplinkConf {
      description "Initial uplink configuration for EN-DC.\nWhether to use MCG or SCG leg for UL at initial state. Set when dual connectivity is configured.";
      yexte:takes-effect "New connection";
      type erienmnrmgnbcucp:enum-InitialUplinkConf;
      default MCG;
    }
    leaf ulDataSplitThreshold {
      description "Buffer threshold for uplink PDCP split for capable UE instances.\nSpecifies buffer level where capable UE instances can split data on both main and secondary leg.\nA capable UE is a UE with dual connectivity supporting split DRB with uplink on both MCG and SCG. This UE can submit uplink PDCP PDUs to both primary RLC entity and secondary RLC entity if total amount of PDCP and RLC data volume for initial transmission in the two associated RLC entities is equal or larger than the used threshold.\nIf set to 0, uplink PDCP split is always active for capable UE instances.\nIf set to -1, used threshold is infinity meaning that PDCP split is not allowed even for capable UE instances.\nIf set to empty, used threshold will be automatically controlled.\nWithout license for LTE-NR Uplink Aggregation a value of infinity is used.";
      yexte:disturbances "Changing this attribute can cause loss of traffic.";
      yexte:takes-effect "New connection";
      type erienmnrmgnbcucp:ddt-GNBCUCP_QciProfileEndcConfigExt_ulDataSplitThreshold;
    }
    leaf tReorderingUlDiscardPdcp {
      status obsolete {
        yexte:status-information "Since 20.Q3. Planned to be removed.";
      }
      description "Long timer that receives missing packets when tReorderingUlPdcp is expired.\nWhen timer expires, PDCP reception window is moved forward and remaining arriving packets are discarded. Hence, packets arriving between expiration of tReorderingUlPdcp and tReorderingUlDiscardPdcp can also be delivered to network.\nDifferent values are set based on purpose of optimization and bearer type.\nIf empty, system handles timer value as infinity.";
      yexte:takes-effect "New connection";
      type erienmnrmgnbcucp:ddt-GNBCUCP_QciProfileEndcConfigExt_tReorderingUlDiscardPdcp;
      default 200;
    }
    leaf tReorderingDlPdcp {
      status deprecated {
        yexte:status-information "Since 20.Q3. Replaced by CUCP5qi::tReorderingDl. Planned to be removed.";
      }
      description "Reordering downlink timer for PDCP.\nTimer used by receiving end of AM or UM PDCP entity in UE. When timer expires, missing packets are considered lost, but packets received with earlier sequence number are sent upwards.";
      yexte:takes-effect "New connection";
      type erienmnrmgnbcucp:ddt-GNBCUCP_QciProfileEndcConfigExt_tReorderingDlPdcp;
      default 200;
    }
  } // end 'grouping moc-QciProfileEndcConfigExt'
  grouping moc-PmUeIntraFreqCellProfile-keys {
    description "Key(s) for MOC PmUeIntraFreqCellProfile";
    leaf id {
      erienmyext:no-notification;
      description "The value component of the RDN.";
      mandatory true;
      yexte:ecim-name pmUeIntraFreqCellProfileId;
      type string;
    }
  } // end 'grouping moc-PmUeIntraFreqCellProfile-keys'
  grouping moc-PmUeIntraFreqCellProfile {
    description "Profile for PM intra-frequency UE measurements.\n\nIf NRCellCU::pmUeIntraFreqCellProfileRef is non-empty, attributes from referred MO instance are used.\nIf NRCellCU::pmUeIntraFreqCellProfileRef is empty, attribute default values according to MO class definition are used.";
    leaf userLabel {
      description "Label for free use.";
      type erienmnrmgnbcucp:ddt-UserLabel;
    }
    container reportConfigA3Rsrq {
      description "Event A3 measurement reporting criteria.\n\nApplied if reportType is EVENT_A3 and trigger quantity is RSRQ.";
      erienmyext:enm-type STRUCT;
      uses erienmnrmgnbcucp:struct-ReportConfigA3Rsrq;
    } // end 'container reportConfigA3Rsrq'
    leaf pmUeReportType {
      description "Report type used in PM UE measurement.";
      yexte:takes-effect "New connection";
      type erienmnrmgnbcucp:enum-PmUeReportType;
      default PERIODICAL;
    }
    leaf triggerQuantity {
      description "Measurement quantity that triggers event A2 or A3 measurements.\nApplied when reportType is EVENT_A2 or EVENT_A3.";
      yexte:takes-effect "New connection";
      type erienmnrmgnbcucp:enum-TriggerQuantity;
      default RSRP;
    }
    leaf maxReportCells {
      description "Maximum number of non-serving cells included in measurement report.";
      yexte:takes-effect "New connection";
      type erienmnrmgnbcucp:ddt-GNBCUCP_PmUeIntraFreqCellProfile_maxReportCells;
      default 4;
    }
    container reportConfigA3Rsrp {
      description "Event A3 measurement reporting criteria.\n\nApplied if reportType is EVENT_A3 and trigger quantity is RSRP.";
      erienmyext:enm-type STRUCT;
      uses erienmnrmgnbcucp:struct-ReportConfigA3Rsrp;
    } // end 'container reportConfigA3Rsrp'
    leaf ueSelectionRatio {
      description "UE selection ratio for PM UE measurements configuration.";
      yexte:disturbances "Large report interval setting can cause high measurement report load.";
      yexte:takes-effect "New connection";
      type erienmnrmgnbcucp:ddt-GNBCUCP_PmUeIntraFreqCellProfile_ueSelectionRatio;
      default 100;
    }
    leaf reportInterval {
      description "Interval for periodical or event-triggered measurement reports.";
      yexte:disturbances "A short report interval setting can cause high measurement report load.";
      yexte:takes-effect "New connection";
      type erienmnrmgnbcucp:enum-ReportInterval;
      default MIN_1;
    }
    leaf reportAmount {
      description "Number of periodical or event-triggered measurement reports.";
      yexte:disturbances "Large report interval setting can cause high measurement report load.";
      yexte:takes-effect "New connection";
      type erienmnrmgnbcucp:enum-ReportAmount;
      default R2;
    }
    leaf-list reservedBy {
      min-elements 0;
      config false;
      description "Contains a list of MO instances that reserve this MO instance.";
      notife:notifiable-state-data true;
      erienmyext:enm-type MOREF;
      type string;
    }
    container reportConfigA2Rsrp {
      description "Event A2 measurement reporting criteria.\n\nApplied if reportType is EVENT_A2 and trigger quantity is RSRP.";
      erienmyext:enm-type STRUCT;
      uses erienmnrmgnbcucp:struct-ReportConfigA1A2Rsrp;
    } // end 'container reportConfigA2Rsrp'
    container reportConfigA2Rsrq {
      description "Event A2 measurement reporting criteria.\n\nApplied if reportType is EVENT_A2 and trigger quantity is RSRQ.";
      erienmyext:enm-type STRUCT;
      uses erienmnrmgnbcucp:struct-ReportConfigA1A2Rsrq;
    } // end 'container reportConfigA2Rsrq'
    container reportQuantityCell {
      description "Cell measurement quantities to be included in measurement report.";
      erienmyext:enm-type STRUCT;
      uses erienmnrmgnbcucp:struct-ReportQuantityCell;
    } // end 'container reportQuantityCell'
  } // end 'grouping moc-PmUeIntraFreqCellProfile'
  grouping moc-McpcPCellNrFreqRelProfile-keys {
    description "Key(s) for MOC McpcPCellNrFreqRelProfile";
    leaf id {
      erienmyext:no-notification;
      description "The value component of the RDN.";
      mandatory true;
      yexte:ecim-name mcpcPCellNrFreqRelProfileId;
      type string;
    }
  } // end 'grouping moc-McpcPCellNrFreqRelProfile-keys'
  grouping moc-McpcPCellNrFreqRelProfile {
    description "Mobility Control at Poor Coverage (MCPC) for PCell.\n\nApplies to UEs which use the cell as PCell. Attributes are used on NR frequency relation level.\n\nMCPC for PCell is enabled per NRCellCU MO by setting NRCellCU::mcpcPCellEnabled attribute.\nIf NRFreqRelation::mcpcPCellNrFreqRelProfileRef is non-empty, attributes from referred MO instance are used.\nIf NRFreqRelation::mcpcPCellNrFreqRelProfileRef is empty, attribute default values according to MO class definition are used.";
    leaf userLabel {
      description "Label for free use.";
      type erienmnrmgnbcucp:ddt-UserLabel;
    }
    container rsrpCandidateA5Offsets {
      description "Downlink RSRP A5 measurement offsets when searching for PCell candidate.";
      erienmyext:enm-type STRUCT;
      uses erienmnrmgnbcucp:struct-ReportConfigA5RsrpOffsets;
    } // end 'container rsrpCandidateA5Offsets'
    leaf inhibitMeasForCellCandidate {
      description "Whether UE measurement searching for PCell candidate on this frequency is inhibited.";
      yexte:takes-effect "Next usage.";
      type boolean;
      default false;
    }
    leaf-list reservedBy {
      min-elements 0;
      config false;
      description "Contains a list of MO instances that reserve this MO instance.";
      notife:notifiable-state-data true;
      erienmyext:enm-type MOREF;
      type string;
    }
  } // end 'grouping moc-McpcPCellNrFreqRelProfile'
  grouping moc-UeGroupSelection-keys {
    description "Key(s) for MOC UeGroupSelection";
    leaf id {
      status current {
        yexte:preliminary;
      }
      erienmyext:no-notification;
      description "The value component of the RDN.";
      mandatory true;
      yexte:ecim-name ueGroupSelectionId;
      type string;
    }
  } // end 'grouping moc-UeGroupSelection-keys'
  grouping moc-UeGroupSelection {
    description "Container class for UeGroupSelectionProfiles and PrefUeGroupSelectionProfiles.\n\nThe RDN of this MO must be UeGroupSelection=1.";
  } // end 'grouping moc-UeGroupSelection'
  grouping moc-CUCPSliceQosInfo-keys {
    description "Key(s) for MOC CUCPSliceQosInfo";
    leaf id {
      status obsolete {
        yexte:status-information "Since 20.Q2. Deprecated: Since 19.Q4. Planned to be removed.";
      }
      erienmyext:no-notification;
      description "The value component of the RDN.";
      mandatory true;
      yexte:ecim-name cUCPSliceQosInfoId;
      type string;
    }
  } // end 'grouping moc-CUCPSliceQosInfo-keys'
  grouping moc-CUCPSliceQosInfo {
    description "CUCP Slice to 5QI table mapping information.";
    leaf-list reservedBy {
      min-elements 0;
      status obsolete {
        yexte:status-information "Since 20.Q2. Deprecated: Since 19.Q4. Planned to be removed.";
      }
      config false;
      description "Contains a list of MO instances that reserve this MO instance.";
      notife:notifiable-state-data true;
      erienmyext:enm-type MOREF;
      type string;
    }
    container pLMNId {
      description "PLMN identifier.";
      status obsolete {
        yexte:status-information "Since 20.Q2. Deprecated: Since 19.Q4. Planned to be removed.";
      }
      erienmyext:enm-type STRUCT;
      uses erienmnrmgnbcucp:struct-PLMNId;
    } // end 'container pLMNId'
    container sNSSAI {
      description "Single Network Slice Selection Assistance Information (S-NSSAI).";
      status obsolete {
        yexte:status-information "Since 20.Q2. Deprecated: Since 19.Q4. Planned to be removed.";
      }
      erienmyext:enm-type STRUCT;
      uses erienmnrmgnbcucp:struct-SliceSelectionAssistInfo;
    } // end 'container sNSSAI'
    leaf cUCP5qiTableRef {
      status obsolete {
        yexte:status-information "Since 20.Q2. Deprecated: Since 19.Q4. Planned to be removed.";
      }
      description "Reference to an instance of CUCP5qiTable MO.";
      yexte:takes-effect "New connection";
      erienmyext:enm-type MOREF;
      type string;
    }
  } // end 'grouping moc-CUCPSliceQosInfo'
  grouping moc-ExternalENodeBFunction-keys {
    description "Key(s) for MOC ExternalENodeBFunction";
    leaf id {
      erienmyext:no-notification;
      description "The value component of the RDN.";
      mandatory true;
      yexte:ecim-name externalENodeBFunctionId;
      type string;
    }
  } // end 'grouping moc-ExternalENodeBFunction-keys'
  grouping moc-ExternalENodeBFunction {
    description "This MO represents an eNodeB.\n\nWhen created by the system, the RDN of this MO is ExternalENodeBFunction=auto<mcc>_<mnc>_<mncLength>_<eNodeBId>.";
    leaf eNodeBId {
      erienmyext:no-notification;
      yexte:restricted;
      description "The ID of an RBS within a Public Land Mobile Network (PLMN).";
      mandatory true;
      type erienmnrmgnbcucp:ddt-GNBCUCP_ExternalENodeBFunction_eNodeBId;
    }
    leaf userLabel {
      description "Label for free use.";
      type erienmnrmgnbcucp:ddt-UserLabel;
    }
    container pLMNId {
      description "PLMN identifier part of global RAN node identity.\n\nThis and eNodeB ID form the global eNodeB ID.\nAn empty pLMNId means that the PLMN is not initiated.\n\nNote: Value MCC=001, MNC=01 means PLMN is not initiated. This value cannot be used as a valid PLMN Identity.";
      erienmyext:enm-type STRUCT;
      uses erienmnrmgnbcucp:struct-PLMNId;
    } // end 'container pLMNId'
    leaf eNBPlmnId {
      status deprecated {
        yexte:status-information "Since 20.Q1. Replaced by pLMNId. Planned to be removed.";
      }
      description "PLMN ID of the node.\nPLMN ID consists of MobileCountryCode (MCC, 3 digits) and MobileNetworkCode (MNC, 2 or 3 digits), separated by a colon. For example, if MCC=125 and MNC=46, then PlmnIdentity=125:46.\nNote: If MCC=001 and MNC=01, then PLMN is not initiated. The value cannot be used as a valid PLMN ID.";
      type erienmnrmgnbcucp:ddt-GNBCUCP_ExternalENodeBFunction_eNBPlmnId;
      default 001:01;
    }
  } // end 'grouping moc-ExternalENodeBFunction'
  grouping moc-ExternalEUtranCell-keys {
    description "Key(s) for MOC ExternalEUtranCell";
    leaf id {
      erienmyext:no-notification;
      description "The value component of the RDN.";
      mandatory true;
      yexte:ecim-name externalEUtranCellId;
      type string;
    }
  } // end 'grouping moc-ExternalEUtranCell-keys'
  grouping moc-ExternalEUtranCell {
    description "External E-UTRAN cell.\n\nContains parameters that are specific for this cell.";
    leaf eUtranFrequencyRef {
      description "Reference to EUtranFrequency MO instance.\nReferenced EUtranFrequency must be under EUtraNetwork under the same GNBCUCPFunction as ExternalEUtranCell.";
      yexte:takes-effect "Next usage.";
      erienmyext:enm-type MOREF;
      type string;
    }
    leaf earfcndl {
      config false;
      description "Channel number for central DL frequency.\nMapping from channel number to physical frequency for specified E-UTRA bands is described in 3GPP TS 36.104. Values that can be used depend on national, operator-specific frequency allocation and on supported frequency bands in RBS.\nEmpty if there is no EN-DC X2 connection.";
      notife:notifiable-state-data true;
      type erienmnrmgnbcucp:ddt-GNBCUCP_ExternalEUtranCell_earfcndl;
    }
    list additionalPlmnList {
      min-elements 0;
      max-elements 5;
      key auto-generated-struct-key;
      leaf auto-generated-struct-key {
        type uint16;
        description "This leaf has been injected to allow for struct instances in a sequence to be ordered.";
        mandatory true;
      }
      description "Additional PLMN IDs supported in External E-UTRAN cell.";
      erienmyext:enm-type STRUCT;
      uses erienmnrmgnbcucp:struct-PLMNId;
    } // end 'list additionalPlmnList'
    leaf cellLocalId {
      description "RBS internal ID attribute for EUtranCell.\nMust be unique in RBS. Together with node ID and PLMN, this is a universally unique cell ID.";
      type erienmnrmgnbcucp:ddt-GNBCUCP_ExternalEUtranCell_cellLocalId;
      default 0;
    }
    leaf dlChannelBandwidth {
      config false;
      description "DL channel bandwidth in LTE cell.\nEmpty if there is no EN-DC X2 connection.";
      notife:notifiable-state-data true;
      type erienmnrmgnbcucp:ddt-GNBCUCP_ExternalEUtranCell_dlChannelBandwidth;
    }
    leaf physicalLayerCellId {
      description "Physical-layer cell ID.";
      yexte:takes-effect "Next usage.";
      type erienmnrmgnbcucp:ddt-GNBCUCP_ExternalEUtranCell_physicalLayerCellId;
      default 0;
    }
    leaf ulChannelBandwidth {
      config false;
      description "UL channel bandwidth in LTE cell.\nEmpty if there is no EN-DC X2 connection.";
      notife:notifiable-state-data true;
      type erienmnrmgnbcucp:ddt-GNBCUCP_ExternalEUtranCell_ulChannelBandwidth;
    }
    leaf earfcnul {
      config false;
      description "Channel number for central UL frequency.\nMapping from channel number to physical frequency for specified E-UTRA bands is described in 3GPP TS 36.104. Values that can be used depend on national, operator-specific frequency allocation and on supported frequency bands in RBS. Value 0 means UL channel number is not available for the DL-only bands.\nEmpty if there is no EN-DC X2 connection.";
      notife:notifiable-state-data true;
      type erienmnrmgnbcucp:ddt-GNBCUCP_ExternalEUtranCell_earfcnul;
    }
    leaf tac {
      description "TAC for external E-UTRAN cell.";
      yexte:takes-effect "Next usage.";
      type erienmnrmgnbcucp:ddt-GNBCUCP_ExternalEUtranCell_tac;
      default 0;
    }
    leaf-list reservedBy {
      min-elements 0;
      config false;
      description "Contains a list of MO instances that reserve this MO instance.";
      notife:notifiable-state-data true;
      erienmyext:enm-type MOREF;
      type string;
    }
    leaf operationalState {
      config false;
      description "The operational state.";
      notife:notifiable-state-data true;
      type erienmnrmgnbcucp:enum-OperState;
    }
    leaf localCellId {
      status deprecated {
        yexte:status-information "Since 20.Q3. Replaced by cellLocalId. Planned to be removed.";
      }
      description "RBS internal ID attribute for EUtranCell.\nMust be unique in RBS. Together with Node ID and PLMN, this is universally unique cell ID.";
      type erienmnrmgnbcucp:ddt-GNBCUCP_ExternalEUtranCell_localCellId;
      default 0;
    }
  } // end 'grouping moc-ExternalEUtranCell'
  grouping moc-ExternalBroadcastPLMNInfo-keys {
    description "Key(s) for MOC ExternalBroadcastPLMNInfo";
    leaf id {
      erienmyext:no-notification;
      description "The value component of the RDN.";
      mandatory true;
      yexte:ecim-name externalBroadcastPLMNInfoId;
      type string;
    }
  } // end 'grouping moc-ExternalBroadcastPLMNInfo-keys'
  grouping moc-ExternalBroadcastPLMNInfo {
    description "PLMN-related information that is served by external NR cell.\n\nCreated automatically when Xn interface is set up or configuration is updated by external gNodeB.\nDeleted automatically when configuration is updated by external gNodeB.\n\nCan also be created and deleted manually.\n\nThe RDNs of these MOs are ExternalBroadcastPLMNInfo=1 to ExternalBroadcastPLMNInfo=12 when created automatically.\nRDN value follows the order received over Xn.\n\nPrecondition: MO can be created and deleted manually, only if TermPointToGNodeB has administrativeState LOCKED.";
    leaf createdBy {
      config false;
      description "Creator of MO.\nCan be one of following:\n- Xn.\n- Operator.";
      notife:notifiable-state-data true;
      type erienmnrmgnbcucp:enum-CreatedByNR;
    }
    leaf nRTAC {
      description "NR Tracking Area Code (TAC).";
      mandatory true;
      yexte:takes-effect "Next MO unlock";
      yexte:precondition "Value can only be changed if TermPointToGNodeB has administrativeState LOCKED.";
      type erienmnrmgnbcucp:ddt-GNBCUCP_ExternalBroadcastPLMNInfo_nRTAC;
    }
    list pLMNIdList {
      min-elements 1;
      max-elements 12;
      key auto-generated-struct-key;
      leaf auto-generated-struct-key {
        type uint16;
        description "This leaf has been injected to allow for struct instances in a sequence to be ordered.";
        mandatory true;
      }
      description "List of broadcast PLMNs.";
      erienmyext:enm-type STRUCT;
      uses erienmnrmgnbcucp:struct-PLMNId;
    } // end 'list pLMNIdList'
  } // end 'grouping moc-ExternalBroadcastPLMNInfo'
  grouping moc-LocalIpEndpoint-keys {
    description "Key(s) for MOC LocalIpEndpoint";
    leaf id {
      erienmyext:no-notification;
      description "The value component of the RDN.";
      mandatory true;
      yexte:ecim-name localIpEndpointId;
      type string;
    }
  } // end 'grouping moc-LocalIpEndpoint-keys'
  grouping moc-LocalIpEndpoint {
    description "Local transport network endpoint for user plane interface.\n\nE1 control plane uses TCP, hence this interface is also configured by this class.";
    leaf-list addressRef {
      min-elements 1;
      max-elements 2;
      description "Reference to IP address MO instance.\nReference to AddressIPv4 or AddressIPv6 MO in embedded CUCP deployment and IPv4AccessPoint or IPv6AccessPoint MO in virtual CUCP deployment.\nMust be unique among LocalIpEndpoint MO instances under EndpointResource. Dual stack is not supported, only one IP address can be referenced.";
      yexte:takes-effect "Node restart";
      erienmyext:enm-type MOREF;
      type string;
    }
    leaf-list interfaceList {
      min-elements 1;
      max-elements 2;
      description "List of user plane interfaces that use the referenced AddressIPv4 or AddressIPv6.\nAllowed value: E1.\nInterface must be unique across LocalIpEndpoints under EndpointResource.";
      yexte:takes-effect "Node restart";
      type erienmnrmgnbcucp:enum-InterfaceName;
    }
  } // end 'grouping moc-LocalIpEndpoint'
  grouping moc-ExternalAdditionalPLMNInfo-keys {
    description "Key(s) for MOC ExternalAdditionalPLMNInfo";
    leaf id {
      status obsolete {
        yexte:status-information "Since 20.Q3. Planned to be removed.";
      }
      erienmyext:no-notification;
      description "The value component of the RDN.";
      mandatory true;
      yexte:ecim-name externalAdditionalPLMNInfoId;
      type string;
    }
  } // end 'grouping moc-ExternalAdditionalPLMNInfo-keys'
  grouping moc-ExternalAdditionalPLMNInfo {
    description "PLMN-related Information that is additionally served by external NR cell.\n\nCreated by system when Xn interface is set up or configuration is updated by external gNodeB.\nDeleted by system when TermPointToGNodeB::operationalState is DISABLED or configuration is updated by external gNodeB.\n\nThe RDNs of these MOs are ExternalAdditionalPLMNInfo=1 to ExternalAdditionalPLMNInfo=11.";
    leaf nRTAC {
      status obsolete {
        yexte:status-information "Since 20.Q3. Planned to be removed.";
      }
      config false;
      description "NR Tracking Area Code (TAC).";
      notife:notifiable-state-data true;
      type int32;
    }
    list pLMNIdList {
      min-elements 1;
      max-elements 12;
      key auto-generated-struct-key;
      leaf auto-generated-struct-key {
        type uint16;
        description "This leaf has been injected to allow for struct instances in a sequence to be ordered.";
        mandatory true;
      }
      description "List of supported PLMNs.";
      status obsolete {
        yexte:status-information "Since 20.Q3. Planned to be removed.";
      }
      erienmyext:enm-type STRUCT;
      uses erienmnrmgnbcucp:struct-PLMNId;
    } // end 'list pLMNIdList'
  } // end 'grouping moc-ExternalAdditionalPLMNInfo'
  grouping moc-TermPointToENodeB-keys {
    description "Key(s) for MOC TermPointToENodeB";
    leaf id {
      erienmyext:no-notification;
      description "The value component of the RDN.";
      mandatory true;
      yexte:ecim-name termPointToENodeBId;
      type string;
    }
  } // end 'grouping moc-TermPointToENodeB-keys'
  grouping moc-TermPointToENodeB {
    description "Models the local ENodeB termination point of an X2 link between the GNodeB and an ENodeB.";
    leaf ipsecEpAddress {
      description "Outer IP address of X2 eNodeB neighbor in EN-DC case.\nManual configuration is only applicable if peer node is not upgraded to support automatic direct X2 IPsec functionality.\nCan be IPv4 or IPv6 address.\nFor IPv4, input format is four fields of digits, separated by dots. Each field can consist of three digits. Value of each field is in range 0-255.\nFor IPv6, input format is eight fields, separated by colons. Each field consists of four hexadecimal characters. Value of each field is in range 0-FFFF.\nLeading zeroes can be omitted in a field.\nMultiple groups of 16 bits of zeroes can be compressed to :: and can appear once in address.";
      yexte:takes-effect "Next MO unlock for the change by operator.\nOuter IP address received from X2 neighbor node overwrites manual configuration by operator, and manual configuration is ignored.";
      type erienmnrmgnbcucp:ddt-GNBCUCP_TermPointToENodeB_ipsecEpAddress;
    }
    leaf administrativeState {
      description "The administrative state.\nIf set to SHUTTINGDOWN, the state is immediately brought to LOCKED.";
      type erienmnrmgnbcucp:enum-AdmState;
      default LOCKED;
    }
    leaf-list availabilityStatus {
      min-elements 0;
      config false;
      description "The availability status.\nIt contains details about operational state.";
      notife:notifiable-state-data true;
      type erienmnrmgnbcucp:enum-AvailStatus;
    }
    leaf operationalState {
      config false;
      description "The operational state.";
      notife:notifiable-state-data true;
      type erienmnrmgnbcucp:enum-OperState;
    }
    leaf upIpAddress {
      description "User plane address of X2 eNodeB neighbor in EN-DC case.\nManual configuration is only applicable if peer node is not upgraded to support automatic direct X2 IPsec functionality.\nCan be IPv4 or IPv6 address.\nFor IPv4, input format is four fields of digits, separated by dots. Each field can consist of three digits. Value of each field is in range 0-255.\nFor IPv6, input format is eight fields, separated by colons. Each field consists of four hexadecimal characters. Value of each field is in range 0-FFFF.\nLeading zeroes can be omitted in a field.\nMultiple groups of 16 bits of zeroes can be compressed to :: and can appear once in address. Multiple groups of 16 bits of zeroes can be compressed to :: and can appear once in address.";
      yexte:takes-effect "Next MO unlock for the change by operator.\nUser plan address received from X2 neighbor node overwrites manual configuration by operator, and manual configuration is ignored.";
      type erienmnrmgnbcucp:ddt-GNBCUCP_TermPointToENodeB_upIpAddress;
    }
  } // end 'grouping moc-TermPointToENodeB'
  grouping moc-ExternalNRCellCU-keys {
    description "Key(s) for MOC ExternalNRCellCU";
    leaf id {
      erienmyext:no-notification;
      description "The value component of the RDN.";
      mandatory true;
      yexte:ecim-name externalNRCellCUId;
      type string;
    }
  } // end 'grouping moc-ExternalNRCellCU-keys'
  grouping moc-ExternalNRCellCU {
    description "Represents an external NRCellCU.\n\nWhen created by the system, the RDN of this MO is ExternalNRCellCU=auto<NCI>, where NCI = <gNBId>*2^(36-<gNBIdLength>) + <cellLocalId>.";
    leaf nRFrequencyRef {
      description "Reference to NRFrequency MO corresponding to cell SSB configuration.";
      mandatory true;
      yexte:takes-effect "Next MO unlock";
      erienmyext:enm-type MOREF;
      type string;
    }
    leaf nRPCI {
      description "Physical cell identity of external NR cell.";
      mandatory true;
      yexte:takes-effect "New connection";
      type erienmnrmgnbcucp:ddt-GNBCUCP_ExternalNRCellCU_nRPCI;
    }
    leaf nRTAC {
      description "Tracking Area Code for the External NR Cell.\nIf empty, Stand Alone is not supported.";
      yexte:takes-effect "New connection";
      type erienmnrmgnbcucp:ddt-GNBCUCP_ExternalNRCellCU_nRTAC;
    }
    container primaryPLMNId {
      description "PLMN ID for NR CGI.";
      erienmyext:enm-type STRUCT;
      uses erienmnrmgnbcucp:struct-PLMNId;
    } // end 'container primaryPLMNId'
    leaf timeOfCreation {
      erienmyext:no-notification;
      config false;
      description "Time and date of MO creation.\nFormat: YYYY-MM-DD HH:MM:SS.";
      type erienmnrmgnbcucp:ddt-GNBCUCP_ExternalNRCellCU_timeOfCreation;
    }
    leaf cellLocalId {
      description "Together with gNodeB identifier, identifies an NR cell within a PLMN.\nMust be unique within gNodeB.\nTogether with gNBId it forms the NR Cell Identifier (NCI).";
      yexte:dependencies "cellLocalId < 2^(36 - ExternalGNBCUCPFunction.gNBIdLength)";
      type erienmnrmgnbcucp:ddt-GNBCUCP_ExternalNRCellCU_cellLocalId;
      default 0;
    }
    leaf serviceState {
      config false;
      description "Service state of external NR cell in remote gNodeB.";
      notife:notifiable-state-data true;
      type erienmnrmgnbcucp:enum-NRCellServiceState;
    }
    container absFrameStartOffset {
      description "Absolute frame start offset.";
      status current {
        yexte:preliminary;
      }
      erienmyext:enm-type STRUCT;
      uses erienmnrmgnbcucp:struct-AbsFrameStartOffset;
    } // end 'container absFrameStartOffset'
    list plmnIdList {
      min-elements 1;
      max-elements 12;
      key auto-generated-struct-key;
      leaf auto-generated-struct-key {
        type uint16;
        description "This leaf has been injected to allow for struct instances in a sequence to be ordered.";
        mandatory true;
      }
      description "List of supported PLMNs.\n\nFirst element of list defines main PLMN, and aligns across gNodeB.\nPLMN ID consists of MobileCountryCode (MCC, three digits) and MobileNetworkCode (MNC, two or three digits).";
      erienmyext:enm-type STRUCT;
      uses erienmnrmgnbcucp:struct-PLMNId;
    } // end 'list plmnIdList'
    list sNSSAIList {
      min-elements 0;
      max-elements 1024;
      key auto-generated-struct-key;
      leaf auto-generated-struct-key {
        type uint16;
        description "This leaf has been injected to allow for struct instances in a sequence to be ordered.";
        mandatory true;
      }
      description "List of supported network slices.";
      erienmyext:enm-type STRUCT;
      uses erienmnrmgnbcucp:struct-SliceSelectionAssistInfo;
    } // end 'list sNSSAIList'
    leaf createdBy {
      config false;
      description "Whether MO is created by the ANR function or operator.";
      notife:notifiable-state-data true;
      type erienmnrmgnbcucp:enum-CreatedByGutran;
    }
    leaf nCI {
      status deprecated {
        yexte:status-information "Since 20.Q3. Replaced by cellLocalId. Planned to be removed.";
      }
      description "Uniquely identifies an External NR cell within a PLMN.";
      yexte:takes-effect "New connection";
      type erienmnrmgnbcucp:ddt-GNBCUCP_ExternalNRCellCU_nCI;
      default 0;
    }
    leaf-list reservedBy {
      min-elements 0;
      config false;
      description "Contains a list of MO instances that reserve this MO instance.";
      notife:notifiable-state-data true;
      erienmyext:enm-type MOREF;
      type string;
    }
  } // end 'grouping moc-ExternalNRCellCU'
  grouping moc-AnrFunctionNR-keys {
    description "Key(s) for MOC AnrFunctionNR";
    leaf id {
      erienmyext:no-notification;
      description "The value component of the RDN.";
      mandatory true;
      yexte:ecim-name anrFunctionNRId;
      type string;
    }
  } // end 'grouping moc-AnrFunctionNR-keys'
  grouping moc-AnrFunctionNR {
    description "NR Automated Neighbor Relation (ANR) functions.\n\nThe RDN of this MO must always be AnrFunctionNR=1.";
    leaf anrEndcX2Enabled {
      description "Whether ANR for EN-DC over X2 is enabled for NR for one RBS.\nOnly takes effect when ANR feature is enabled.";
      type boolean;
      default false;
    }
    leaf gNBIdLength {
      description "Length of gNodeB ID bit string representation.";
      type erienmnrmgnbcucp:ddt-GNBCUCP_AnrFunctionNR_gNBIdLength;
      default 22;
    }
  } // end 'grouping moc-AnrFunctionNR'
  grouping moc-EUtraNetwork-keys {
    description "Key(s) for MOC EUtraNetwork";
    leaf id {
      erienmyext:no-notification;
      description "The value component of the RDN.";
      mandatory true;
      yexte:ecim-name eUtraNetworkId;
      type string;
    }
  } // end 'grouping moc-EUtraNetwork-keys'
  grouping moc-EUtraNetwork {
    description "Container for MOs related to E-UTRA networks.\n\nWhen created by the system, the RDN of this MO is EUtraNetwork=1.";
    leaf userLabel {
      description "Label for free use.";
      type erienmnrmgnbcucp:ddt-UserLabel;
    }
  } // end 'grouping moc-EUtraNetwork'
  grouping moc-EUtranCellRelation-keys {
    description "Key(s) for MOC EUtranCellRelation";
    leaf id {
      erienmyext:no-notification;
      description "The value component of the RDN.";
      mandatory true;
      yexte:ecim-name eUtranCellRelationId;
      type string;
    }
  } // end 'grouping moc-EUtranCellRelation-keys'
  grouping moc-EUtranCellRelation {
    description "Handover relationship between NR cell and a neighboring E-UTRAN cell.";
    leaf essMbsfnSubframeConfig {
      status obsolete {
        yexte:status-information "Since 20.Q3. Planned to be removed.";
      }
      description "MBSFN subframe configuration for eNodeB using four frames.\nESS NSA:\n110000 000000 100000 000000 (decimal 12584960).\nESS SA:\n100100 000000 110100 000000 (decimal 9440512) or\n100100 000000 111100 000000 (decimal 9441024).";
      yexte:takes-effect "Next cell unlock";
      type erienmnrmgnbcucp:ddt-GNBCUCP_EUtranCellRelation_essMbsfnSubframeConfig;
      default 9440512;
    }
    leaf userLabel {
      description "Label for free use.";
      type erienmnrmgnbcucp:ddt-UserLabel;
    }
    leaf isHoAllowed {
      description "Whether handover between cells in this relation is allowed.";
      yexte:takes-effect "Next usage.";
      type boolean;
      default true;
    }
    leaf createdBy {
      config false;
      description "Creator of MO.\nCan be one of following:\n- ANR function.\n- Operator.\n- X2.";
      notife:notifiable-state-data true;
      type erienmnrmgnbcucp:enum-CreatedByGutran;
    }
    leaf isRemoveAllowed {
      description "If ANR function is allowed to remove this object.\nThe setting does not restrict operator removal of object. Objects created by ANR have this parameter set to true initially.";
      type boolean;
      default false;
    }
    leaf cellIndividualOffset {
      description "Offset value for neighbor E-UTRAN cell.\nUsed when UE is in connected mode.";
      yexte:takes-effect "Next usage.";
      type erienmnrmgnbcucp:ddt-GNBCUCP_EUtranCellRelation_cellIndividualOffset;
      default 0;
    }
    list essCellScPairs {
      min-elements 0;
      max-elements 14;
      key auto-generated-struct-key;
      leaf auto-generated-struct-key {
        type uint16;
        description "This leaf has been injected to allow for struct instances in a sequence to be ordered.";
        mandatory true;
      }
      description "The eNodeB-gNodeB Sector Carrier pairs used in cell for ESS operation.";
      erienmyext:enm-type STRUCT;
      uses erienmnrmgnbcucp:struct-EssCellScPair;
    } // end 'list essCellScPairs'
    leaf neighborCellRef {
      description "Reference to ExternalEUtranCell MO.\nMust be unique across essEnabled EUtanCellRelations across all NRCellCUs.";
      mandatory true;
      erienmyext:enm-type MOREF;
      type string;
    }
    leaf essEnabled {
      description "ESS service enabled between cells in this relation.\nOnly one EUtranCellRelation under an NRCellCU can be essEnabled.";
      yexte:takes-effect "Next cell unlock";
      type boolean;
      default false;
    }
  } // end 'grouping moc-EUtranCellRelation'
  grouping moc-NRCellCU-keys {
    description "Key(s) for MOC NRCellCU";
    leaf id {
      erienmyext:no-notification;
      description "The value component of the RDN.";
      mandatory true;
      yexte:ecim-name nRCellCUId;
      type string;
    }
  } // end 'grouping moc-NRCellCU-keys'
  grouping moc-NRCellCU {
    description "Represents NR cell in gNodeB-CU.\n\nManages inter-cell mobility and neighbor relations through ANR.\nEither created by system on receiving configuration message over F1 or manually created by operator.\n\nWhen created by the system, the RDN of this MO is NRCellCU=<NCI>, where NCI = <gNBId>*2^(36-<gNBIdLength>) + <cellLocalId>.\n\nCan only be deleted when the NRCellDU with matching cellLocalId does not exist or has administrativeState LOCKED.";
    leaf transmitSib2 {
      description "Broadcast status of SIB2.";
      yexte:takes-effect "Next cell unlock";
      yexte:precondition "Value can only be changed when NRCellDU with matching cellLocalId does not exist or has administrativeState LOCKED.";
      yexte:dependencies "Can only be set to true if number of NRFreqRelations under cell is greater than 1.";
      type boolean;
      default false;
    }
    leaf userLabel {
      description "Label for free use.";
      type erienmnrmgnbcucp:ddt-UserLabel;
    }
    leaf threshServingLowP {
      description "Srxlev used for cell reselection to lower priority RAT frequencies.";
      yexte:takes-effect "Next cell unlock";
      yexte:precondition "Value can only be changed when NRCellDU with matching cellLocalId does not exist or has administrativeState LOCKED.";
      type erienmnrmgnbcucp:ddt-GNBCUCP_NRCellCU_threshServingLowP;
      default 0;
    }
    leaf threshServingLowQ {
      description "Squal used for cell reselection to lower priority RAT frequencies.\nIf the attribute is set to empty, value is not broadcast in SIB.";
      yexte:takes-effect "Next cell unlock";
      yexte:precondition "Value can only be changed when NRCellDU with matching cellLocalId does not exist or has administrativeState LOCKED.";
      type erienmnrmgnbcucp:ddt-GNBCUCP_NRCellCU_threshServingLowQ;
    }
    leaf sNonIntraSearchP {
      description "Threshold when inter-frequency and inter-RAT measurements are required.\nIf the attribute is set to empty, value is not broadcast in SIB2 and the UE applies the default value of infinity for sNonIntraSearchP.";
      yexte:takes-effect "Next cell unlock";
      yexte:precondition "Value can only be changed when NRCellDU with matching cellLocalId does not exist or has administrativeState LOCKED.";
      type erienmnrmgnbcucp:ddt-GNBCUCP_NRCellCU_sNonIntraSearchP;
      default 0;
    }
    leaf pmUeIntraFreqEnabled {
      description "Whether PM intra-frequency UE Measurements are enabled for NR cell.";
      yexte:takes-effect "Next usage.";
      type boolean;
      default false;
    }
    container primaryPLMNId {
      description "PLMN ID for NR CGI.\n\nIf empty, GNBCUCPFunction::pLMNId is used for PLMN ID in NR CGI.";
      erienmyext:enm-type STRUCT;
      uses erienmnrmgnbcucp:struct-PLMNId;
    } // end 'container primaryPLMNId'
    leaf sNonIntraSearchQ {
      description "Threshold when inter-frequency and inter-RAT measurements are required.\nIf the attribute is set to empty, the value is not broadcast in SIB2, and the UE applies the default value of 0 dB for sNonIntraSearch.";
      yexte:takes-effect "Next cell unlock";
      yexte:precondition "Value can only be changed when NRCellDU with matching cellLocalId does not exist or has administrativeState LOCKED.";
      yexte:dependencies "Must be set to empty if threshServingLowQ is set to empty.";
      type erienmnrmgnbcucp:ddt-GNBCUCP_NRCellCU_sNonIntraSearchQ;
    }
    leaf cellLocalId {
      description "Used together with gNodeB identifier to identify NR cell in PLMN.\nMust be unique in gNodeB.\nUsed together with gNBId to form NCI.";
      mandatory true;
      yexte:takes-effect "Node restart";
      yexte:precondition "Value can only be changed when NRCellDU with matching cellLocalId does not exist or has administrativeState LOCKED.";
      yexte:dependencies "cellLocalId < 2^(36 - gNBIdLength)";
      type erienmnrmgnbcucp:ddt-GNBCUCP_NRCellCU_cellLocalId;
    }
    leaf rrcReconfMsgSizeRed {
      status current {
        yexte:preliminary;
      }
      description "Size reduction options in one single RRCReconfiguration message in NR SA deployment.";
      yexte:takes-effect "New connection";
      type erienmnrmgnbcucp:enum-MsgRedOptions;
      default HO_ESS_MSG_RED_LEVEL1;
    }
    leaf cellState {
      config false;
      description "Current cellState.";
      notife:notifiable-state-data true;
      type erienmnrmgnbcucp:enum-NRCellState;
    }
    leaf transmitSib5 {
      description "Broadcast status of SIB5.";
      yexte:takes-effect "Next cell unlock";
      yexte:precondition "Value can only be changed when NRCellDU with matching cellLocalId does not exist or has administrativeState LOCKED.";
      yexte:dependencies "Can only be set to true if transmitSib2 is true and number of EUtranFreqRelations under cell is between 1 and 8.";
      type boolean;
      default false;
    }
    leaf transmitSib4 {
      description "Broadcast status of SIB4.";
      yexte:takes-effect "Next cell unlock";
      yexte:precondition "Value can only be changed when NRCellDU with matching cellLocalId does not exist or has administrativeState LOCKED.";
      yexte:dependencies "Can only be set to true if transmitSib2 is true and number of NRFreqRelations under cell is between 1 and 9.";
      type boolean;
      default false;
    }
    leaf serviceState {
      config false;
      description "Current service state.";
      notife:notifiable-state-data true;
      type erienmnrmgnbcucp:enum-NRCellServiceState;
    }
    leaf mcpcPSCellProfileRef {
      description "Reference to McpcPSCellProfile MO instance.\nIf reference is non-empty, attributes from referred MO instance are used.\nIf reference is empty, attribute default values according to MO class definition are used.\nReferenced McpcPSCellProfile must be under Mcpc MO under same GNBCUCPFunction as NRCellCU.";
      yexte:takes-effect "Next usage.";
      erienmyext:enm-type MOREF;
      type string;
    }
    list sNSSAIList {
      min-elements 0;
      max-elements 1024;
      key auto-generated-struct-key;
      leaf auto-generated-struct-key {
        type uint16;
        description "This leaf has been injected to allow for struct instances in a sequence to be ordered.";
        mandatory true;
      }
      description "List of supported network slices.";
      erienmyext:enm-type STRUCT;
      uses erienmnrmgnbcucp:struct-SliceSelectionAssistInfo;
    } // end 'list sNSSAIList'
    leaf nCI {
      config false;
      description "NR Cell Identity.";
      notife:notifiable-state-data true;
      type erienmnrmgnbcucp:ddt-GNBCUCP_NRCellCU_nCI;
    }
    leaf serviceStatus {
      status deprecated {
        yexte:status-information "Since 20.Q1. Replaced by serviceState. Planned to be removed.";
      }
      config false;
      description "Current serviceStatus.";
      notife:notifiable-state-data true;
      type erienmnrmgnbcucp:enum-NRCellServiceStatus;
    }
    leaf mcpcPSCellEnabled {
      description "Whether Mobility Control at Poor Coverage (MCPC) for PSCell is enabled for NRCellCU.";
      yexte:takes-effect "Next usage.";
      type boolean;
      default false;
    }
    leaf-list pwsEmergencyAreaIdList {
      min-elements 0;
      max-elements 15;
      description "List of emergency areas that cell belongs to.\nA cell that supports broadcast of warning messages can belong to 1 to 15 emergency areas. Emergency area is identified by an Emergency Area ID, set by the operator.";
      yexte:takes-effect "Next cell unlock";
      yexte:precondition "Value can only be changed when NRCellDU with matching cellLocalId does not exist or has administrativeState LOCKED.";
      type erienmnrmgnbcucp:ddt-GNBCUCP_NRCellCU_pwsEmergencyAreaIdList;
    }
    leaf emergencyFallbackOperation {
      status deprecated {
        yexte:status-information "Since 20.Q4. Planned to be removed.";
      }
      description "EPS fallback or Voice over NR (VoNR) is activated when emergency call is required in NR.\nIf empty, EPS fallback is not used for emergency calls.";
      type erienmnrmgnbcucp:enum-EpsFbOperationTypeEm;
      default FORCED;
    }
    leaf qHyst {
      description "Hysteresis value for ranking criteria at cell reselection.";
      yexte:takes-effect "Next cell unlock";
      yexte:precondition "Value can only be changed when NRCellDU with matching cellLocalId does not exist or has administrativeState LOCKED.";
      type erienmnrmgnbcucp:ddt-GNBCUCP_NRCellCU_qHyst;
      default 4;
    }
    leaf nRFrequencyRef {
      description "Reference to NRFrequency MO corresponding to cell SSB configuration.";
      yexte:takes-effect "Next cell unlock";
      yexte:precondition "Value can only be changed when NRCellDU with matching cellLocalId does not exist or has administrativeState LOCKED.";
      erienmyext:enm-type MOREF;
      type string;
    }
    leaf nRTAC {
      config false;
      description "NR Tracking Area Code (TAC).";
      notife:notifiable-state-data true;
      type int32;
    }
    leaf mcpcEnabled {
      status deprecated {
        yexte:status-information "Since 20.Q4. Replaced by mcpcPSCellEnabled. Planned to be removed.";
      }
      description "Whether mobility control at poor coverage is enabled for NR cell.\nSee Mcpc MO for more information about Mobility Control at Poor Coverage (MCPC).";
      yexte:disturbances "Changing this attribute to true can trigger release of NR resources if UE measurement event condition is fulfilled. UE measurement condition is defined by rsrpCrititcal attribute in McpcPSCellProfile used by the NR cell.";
      yexte:takes-effect "Next usage.";
      type boolean;
      default false;
    }
    leaf mcfbCellProfileRef {
      description "Reference to McfbCellProfile MO instance.\nIf reference is non-empty, attributes from referred MO instance are used.\nIf reference is empty, attribute default values according to MO class definition are used.\nReferenced McfbCellProfile must be under Mcfb MO under the same GNBCUCPFunction as NRCellCU.";
      yexte:takes-effect "Next usage.";
      erienmyext:enm-type MOREF;
      type string;
    }
    container absFrameStartOffset {
      description "Absolute frame start offset.";
      status current {
        yexte:preliminary;
      }
      erienmyext:enm-type STRUCT;
      uses erienmnrmgnbcucp:struct-AbsFrameStartOffset;
    } // end 'container absFrameStartOffset'
    leaf epsFallbackOperation {
      status deprecated {
        yexte:status-information "Since 20.Q4. Planned to be removed.";
      }
      description "EPS fallback or Voice over NR (VoNR) is activated when a voice call is required in NR.";
      yexte:takes-effect "Next cell unlock";
      yexte:precondition "Value can only be changed when NRCellDU with matching cellLocalId does not exist or has administrativeState LOCKED.";
      type erienmnrmgnbcucp:enum-EpsFallbackOperationType;
      default FORCED;
    }
    leaf ueMCCellProfileRef {
      description "Reference to ueMCCellProfile MO instance.\nIf reference is non-empty, attributes from referred MO instance are used.\nIf reference is empty, attribute default values according to MO class definition are used.\nReferenced UeMCCellProfile must be under UeMC MO under same GNBCUCPFunction as NRCellCU.";
      yexte:takes-effect "Next usage.";
      erienmyext:enm-type MOREF;
      type string;
    }
    leaf pmUeIntraFreqCellProfileRef {
      description "Reference to PmUeIntraFreqCellProfile MO instance.\nIf reference is non-empty, attributes from referred MO instance are used.\nIf reference is empty, attribute default values according to MO class definition are used.\nReferenced PmUeIntraFreqCellProfile must be under PmUeMeas MO under same GNBCUCPFunction as NRCellCU.";
      yexte:takes-effect "Next usage.";
      erienmyext:enm-type MOREF;
      type string;
    }
    leaf intraFreqMCCellProfileRef {
      description "Reference to IntraFreqMCCellProfile MO instance.\nIf reference is non-empty, attributes from referred MO instance are used.\nIf reference is empty, attribute default values according to MO class definition are used.\nReferenced IntraFreqMCCellProfile must be under IntraFreqMC MO under same GNBCUCPFunction as NRCellCU.";
      yexte:takes-effect "New connection";
      erienmyext:enm-type MOREF;
      type string;
    }
    leaf mcpcPCellProfileRef {
      description "Reference to McpcPCellProfile MO instance.\nIf reference is non-empty, attributes from referred MO instance are used.\nIf reference is empty, attribute default values according to MO class definition are used.\nReferenced McpcPCellProfile must be under Mcpc MO under same GNBCUCPFunction as NRCellCU.";
      yexte:takes-effect "Next usage.";
      erienmyext:enm-type MOREF;
      type string;
    }
    leaf-list reservedBy {
      min-elements 0;
      config false;
      description "Contains a list of MO instances that reserve this MO instance.";
      notife:notifiable-state-data true;
      erienmyext:enm-type MOREF;
      type string;
    }
    leaf pSCellCapable {
      config false;
      description "Whether cell is Primary Secondary Cell (PSCell) capable in EN-DC.\nIf false, cell is not shared over X2AP.\nIf empty, the value is unknown.";
      notife:notifiable-state-data true;
      type boolean;
    }
    list pLMNIdList {
      min-elements 1;
      max-elements 12;
      key auto-generated-struct-key;
      leaf auto-generated-struct-key {
        type uint16;
        description "This leaf has been injected to allow for struct instances in a sequence to be ordered.";
        mandatory true;
      }
      description "List of supported PLMNs.\n\nFirst element of list defines main PLMN, and aligns across gNodeB.\nPLMN ID consists of MobileCountryCode (MCC, 3 digits) and MobileNetworkCode (MNC, 2 or 3 digits).";
      erienmyext:enm-type STRUCT;
      uses erienmnrmgnbcucp:struct-PLMNId;
    } // end 'list pLMNIdList'
    list lwNeighborRel {
      min-elements 0;
      key auto-generated-struct-key;
      leaf auto-generated-struct-key {
        type uint16;
        description "This leaf has been injected to allow for struct instances in a sequence to be ordered.";
        mandatory true;
      }
      description "List of lightweight NR neighbor relations.\n\nThese lightweight relations complement the set of relations represented by NRCellRelation MO instances.";
      erienmyext:enm-type STRUCT;
      uses erienmnrmgnbcucp:struct-LwNeighborRelInfo;
    } // end 'list lwNeighborRel'
    leaf mcpcPCellEnabled {
      description "Whether Mobility Control at Poor Coverage (MCPC) for PCell is enabled for NRCellCU.\nIf set to false, function defined in ReportConfigA2 MO is applied.\nIf set to true, function defined in ReportConfigA2 MO is turned off and replaced by the enabled PCell MCPC functionality.";
      yexte:takes-effect "Next usage.";
      type boolean;
      default false;
    }
  } // end 'grouping moc-NRCellCU'
  grouping moc-McpcPCellProfile-keys {
    description "Key(s) for MOC McpcPCellProfile";
    leaf id {
      erienmyext:no-notification;
      description "The value component of the RDN.";
      mandatory true;
      yexte:ecim-name mcpcPCellProfileId;
      type string;
    }
  } // end 'grouping moc-McpcPCellProfile-keys'
  grouping moc-McpcPCellProfile {
    description "Mobility Control at Poor Coverage (MCPC) for PCell.\n\nApplies to UEs which use the cell as PCell. Attributes are used on cell level.\n\nMCPC for PCell is enabled per NRCellCU MO by setting NRCellCU::mcpcPCellEnabled attribute.\nIf NRCellCU::mcpcPCellProfileRef is non-empty, attributes from referred MO instance are used.\nIf NRCellCU::mcpcPCellProfileRef is empty, attribute default values according to MO class definition are used.";
    container rsrpCandidateB2 {
      description "RSRP B2 measurement report criteria when searching for PCell candidate.";
      erienmyext:enm-type STRUCT;
      uses erienmnrmgnbcucp:struct-ReportConfigB2Rsrp;
    } // end 'container rsrpCandidateB2'
    leaf userLabel {
      description "Label for free use.";
      type erienmnrmgnbcucp:ddt-UserLabel;
    }
    leaf rsrpSearchTimeRestriction {
      description "Search time restriction when searching for PCell candidate using DL RSRP measurements.\nIf set to -1, no time restriction is applied.";
      yexte:takes-effect "Next usage.";
      type erienmnrmgnbcucp:ddt-GNBCUCP_McpcPCellProfile_rsrpSearchTimeRestriction;
      default -1;
    }
    container rsrpSearchZone {
      description "RSRP measurement report criteria that define entering and leaving search zone.";
      erienmyext:enm-type STRUCT;
      uses erienmnrmgnbcucp:struct-ReportConfigA1A2Rsrp;
    } // end 'container rsrpSearchZone'
    leaf-list mcpcQuantityList {
      min-elements 1;
      max-elements 2;
      description "Measurement quantities on which PCell Mobility Control at Poor Coverage function shall be applied.";
      yexte:takes-effect "New connection";
      type erienmnrmgnbcucp:enum-McpcQuantity;
      default RSRP;
    }
    leaf-list reservedBy {
      min-elements 0;
      config false;
      description "Contains a list of MO instances that reserve this MO instance.";
      notife:notifiable-state-data true;
      erienmyext:enm-type MOREF;
      type string;
    }
    container rsrpCandidateA5 {
      description "RSRP A5 measurement report criteria when searching for PCell candidate.";
      erienmyext:enm-type STRUCT;
      uses erienmnrmgnbcucp:struct-ReportConfigA5Rsrp;
    } // end 'container rsrpCandidateA5'
    container rsrpCritical {
      description "RSRP measurement report criteria for detecting critical coverage.";
      erienmyext:enm-type STRUCT;
      uses erienmnrmgnbcucp:struct-ReportConfigA1A2Rsrp;
    } // end 'container rsrpCritical'
  } // end 'grouping moc-McpcPCellProfile'
  grouping moc-EUtranFreqRelation-keys {
    description "Key(s) for MOC EUtranFreqRelation";
    leaf id {
      erienmyext:no-notification;
      description "The value component of the RDN.";
      mandatory true;
      yexte:ecim-name eUtranFreqRelationId;
      type string;
    }
  } // end 'grouping moc-EUtranFreqRelation-keys'
  grouping moc-EUtranFreqRelation {
    description "Mobility relation between NR cell and an E-UTRAN frequency.";
    leaf userLabel {
      description "Label for free use.";
      type erienmnrmgnbcucp:ddt-UserLabel;
    }
    leaf eUtranFrequencyRef {
      yexte:restricted;
      description "Reference to an EUtranFrequency MO.\nMust be unique among EUtranFreqRelations under an NRCellCU.";
      mandatory true;
      erienmyext:enm-type MOREF;
      type string;
    }
    leaf presenceAntennaPort1 {
      description "Use of Antenna Port 1 in neighboring cells.\nValue true means UE expects at least two cell-specific antenna ports are used in neighboring cells.";
      yexte:takes-effect "Next cell unlock";
      type boolean;
      default false;
    }
    leaf connectedModeMobilityPrio {
      description "Prioritizes EUTRAN frequencies among all frequencies related to cell for UEs in connected mode.\nValue 0 means lowest priority.\nValue 7 means highest priority.\nIf set to empty, the frequency is excluded.";
      yexte:takes-effect "New connection";
      type erienmnrmgnbcucp:ddt-GNBCUCP_EUtranFreqRelation_connectedModeMobilityPrio;
      default 7;
    }
    leaf eUtranFallbackPrioEc {
      description "Priority of E-UTRAN frequencies for emergency calls.\nPriority is among all frequencies related to the cell for UEs in connected mode.\nSets priority to alternative target frequency to which release is made with redirection.\nValue 0 means lowest priority.\nValue 7 means highest priority.\nIf set to empty the frequency is excluded.";
      type erienmnrmgnbcucp:ddt-GNBCUCP_EUtranFreqRelation_eUtranFallbackPrioEc;
      default 0;
    }
    leaf allowedMeasBandwidth {
      description "Maximum allowed measurement bandwidth on a carrier frequency.\nValue indicates number of resource blocks and corresponds to channel bandwidth 1.4 MHz, 3 MHz, 5 MHz, 10 MHz, 15 MHz and 20 MHz respectively specified in 3GPP TS 36.104, Evolved Universal Terrestrial Radio Access (E-UTRA); Base Station (BS) radio transmission and reception.";
      yexte:takes-effect "Next cell unlock";
      type erienmnrmgnbcucp:ddt-GNBCUCP_EUtranFreqRelation_allowedMeasBandwidth;
      default 6;
    }
    leaf tReselectionEUtra {
      description "Time for evaluation of criteria before reselection can be done.";
      yexte:takes-effect "Next cell unlock";
      type erienmnrmgnbcucp:ddt-GNBCUCP_EUtranFreqRelation_tReselectionEUtra;
      default 2;
    }
    leaf threshXHighQ {
      description "RSRQ threshold level for reselection to higher priority.\nThe threshold used by the UE when reselecting towards a higher priority frequency X from the current serving frequency.\nEach frequency of E-UTRAN can have a specific threshold.\nIf the attribute is set to empty, the value is not broadcast in SIB5.";
      yexte:takes-effect "Next cell unlock";
      yexte:dependencies "Must be empty if NRCellCU::threshServingLowQ is empty or set if NRCellCU::threshServingLowQ is set.";
      type erienmnrmgnbcucp:ddt-GNBCUCP_EUtranFreqRelation_threshXHighQ;
    }
    leaf threshXHighP {
      description "RSRP threshold level for reselection to higher priority.\nEach frequency of E-UTRAN can have a specific threshold.";
      yexte:takes-effect "Next cell unlock";
      type erienmnrmgnbcucp:ddt-GNBCUCP_EUtranFreqRelation_threshXHighP;
      default 4;
    }
    leaf threshXLowP {
      description "RSRP threshold level for reselection to lower priority.\nEach frequency of E-UTRAN can have a specific threshold.";
      yexte:takes-effect "Next cell unlock";
      type erienmnrmgnbcucp:ddt-GNBCUCP_EUtranFreqRelation_threshXLowP;
      default 0;
    }
    leaf mcpcPCellEUtranFreqRelProfileRef {
      description "Reference to McpcPCellEUtranFreqRelProfile MO instance.\nIf reference is non-empty, attributes from referred MO instance are used.\nIf reference is empty, attribute default values according to MO class definition are used.\nReferenced McpcPCellEUtranFreqRelProfile must be under Mcpc MO under same GNBCUCPFunction as NRCellCU.";
      yexte:takes-effect "Next usage.";
      erienmyext:enm-type MOREF;
      type string;
    }
    leaf threshXLowQ {
      description "RSRQ threshold level for reselection to lower priority.\nThe threshold used by the UE when reselecting towards a lower priority frequency X from the current serving frequency.\nEach frequency of E-UTRAN can have a specific threshold.\nIf the attribute is set to empty, the value is not broadcast in SIB5.";
      yexte:takes-effect "Next cell unlock";
      yexte:dependencies "Must be empty if NRCellCU::threshServingLowQ is empty or set if NRCellCU::threshServingLowQ is set.";
      type erienmnrmgnbcucp:ddt-GNBCUCP_EUtranFreqRelation_threshXLowQ;
    }
    list allowedPlmnList {
      min-elements 0;
      max-elements 15;
      key auto-generated-struct-key;
      leaf auto-generated-struct-key {
        type uint16;
        description "This leaf has been injected to allow for struct instances in a sequence to be ordered.";
        mandatory true;
      }
      description "Lists all Public Land Mobile Network (PLMN) IDs allowed for this frequency relation.\n\nAccording to UE Mobility Restriction List, a UE not supporting a PLMN included in allowedPlmnList does not use frequency.\n\nIf empty, frequency has no restrictions for PLMN.\n\nPLMN ID consists of MobileCountryCode (MCC, 3 digits) and MobileNetworkCode (MNC, 2 or 3 digits).";
      erienmyext:enm-type STRUCT;
      uses erienmnrmgnbcucp:struct-PLMNId;
    } // end 'list allowedPlmnList'
    leaf qRxLevMin {
      description "Minimum received RSRP level for cell reselection.\nCorresponds to parameter Qrxlevmin in 3GPP TS 38.304.";
      yexte:takes-effect "New connection";
      type erienmnrmgnbcucp:ddt-GNBCUCP_EUtranFreqRelation_qRxLevMin;
      default -140;
    }
    leaf voicePrio {
      description "Prioritizes EUTRAN frequencies among all frequencies related to the cell for UEs in connected mode.\nSets priority to which frequency to perform mobility to, for a voice session.\nValue 0 means lowest priority.\nValue 7 means highest priority.\nValue empty means that the frequency is excluded.";
      yexte:takes-effect "New connection";
      type erienmnrmgnbcucp:ddt-GNBCUCP_EUtranFreqRelation_voicePrio;
      default 0;
    }
    leaf cellReselectionPriority {
      description "Absolute priority of the carrier frequency used by the cell reselection procedure.\nThis attribute is broadcast in SIB5.\nValue 0 means lowest priority. The value must be unique between RATs. This means that equal priorities between RATs are not supported.\nIf the attribute is set to empty, value is not broadcast in SIB5.";
      yexte:takes-effect "Next cell unlock";
      yexte:dependencies "The cellReselectionPriority must be unique between NRFreqRelations and EUtranFreqRelations under the same NRCellCU.";
      type erienmnrmgnbcucp:ddt-GNBCUCP_EUtranFreqRelation_cellReselectionPriority;
      default 6;
    }
    leaf pMaxEUtra {
      description "Parameter used to calculate Pcompensation at cell reselection.\nCorresponds to parameter PEMAX in 3GPP TS 38.101.";
      yexte:takes-effect "Next cell unlock";
      type erienmnrmgnbcucp:ddt-GNBCUCP_EUtranFreqRelation_pMaxEUtra;
      default 23;
    }
    leaf qQualMin {
      description "Minimum required quality level in cell (dB).\nThis attribute is broadcast in SIB5.";
      yexte:takes-effect "Next cell unlock";
      type erienmnrmgnbcucp:ddt-GNBCUCP_EUtranFreqRelation_qQualMin;
      default -34;
    }
  } // end 'grouping moc-EUtranFreqRelation'
  grouping moc-IntraFreqMCCellProfile-keys {
    description "Key(s) for MOC IntraFreqMCCellProfile";
    leaf id {
      erienmyext:no-notification;
      description "The value component of the RDN.";
      mandatory true;
      yexte:ecim-name intraFreqMCCellProfileId;
      type string;
    }
  } // end 'grouping moc-IntraFreqMCCellProfile-keys'
  grouping moc-IntraFreqMCCellProfile {
    description "Intra-frequency mobility control cell configuration profile.\n\nIf NRCellCU::intraFreqMCCellProfileRef is non-empty, attributes from referred MO instance are used.\nIf NRCellCU::intraFreqMCCellProfileRef is empty, attribute default values according to MO class definition are used.";
    leaf userLabel {
      description "Label for free use.";
      type erienmnrmgnbcucp:ddt-UserLabel;
    }
    leaf sCellCoverageTriggerQuantity {
      description "Quantity that triggers SCell poor or good coverage measurements.";
      yexte:takes-effect "New connection";
      type erienmnrmgnbcucp:enum-TriggerQuantity;
      default RSRP;
    }
    container rsrpSCellCoverage {
      description "Configures UE measurements to detect poor or good coverage in SCell.\n\nThe cell referring to this profile is used as a PCell or PSCell for UE.\nUsed only when triggerQuantity is set to RSRP.";
      erienmyext:enm-type STRUCT;
      uses erienmnrmgnbcucp:struct-ReportConfigA1A2Rsrp;
    } // end 'container rsrpSCellCoverage'
    container rsrqSCellCoverage {
      description "Configures UE measurements to detect poor or good coverage in SCell.\n\nThe cell referring to this profile is used as a PCell or PSCell for UE.\nUsed only when triggerQuantity is set to RSRQ.";
      erienmyext:enm-type STRUCT;
      uses erienmnrmgnbcucp:struct-ReportConfigA1A2Rsrq;
    } // end 'container rsrqSCellCoverage'
    container rsrqBetterSpCell {
      description "Downlink RSRQ measurement report criteria when searching for better Special Cell.\n\nSpecial Cell is either PCell or PSCell.\nUsed only when triggerQuantity is set to RSRQ.";
      erienmyext:enm-type STRUCT;
      uses erienmnrmgnbcucp:struct-ReportConfigA3Rsrq;
    } // end 'container rsrqBetterSpCell'
    container rsrpBetterSCell {
      description "Configures UE measurement to detect neighboring SCells with better coverage.\n\nThe cell referring to this profile is used as a PCell or PSCell for UE.\nMeasurement trigger quantity for SCell neighbor with better coverage is always RSRP.";
      erienmyext:enm-type STRUCT;
      uses erienmnrmgnbcucp:struct-ReportConfigA6Rsrp;
    } // end 'container rsrpBetterSCell'
    leaf-list reservedBy {
      min-elements 0;
      config false;
      description "Contains a list of MO instances that reserve this MO instance.";
      notife:notifiable-state-data true;
      erienmyext:enm-type MOREF;
      type string;
    }
    container rsrpBetterSpCell {
      description "Downlink RSRP measurement report criteria when searching for better Special Cell.\n\nSpecial Cell is either PCell or PSCell.\nUsed only when triggerQuantity is set to RSRP.";
      erienmyext:enm-type STRUCT;
      uses erienmnrmgnbcucp:struct-ReportConfigA3Rsrp;
    } // end 'container rsrpBetterSpCell'
    leaf endcActionEvalFail {
      description "Action taken when intra-frequency handover evaluation or Secondary Node change procedure fails.\nApplies to UE which use cell as PSCell in EN-DC configuration.";
      yexte:takes-effect "Next usage.";
      type erienmnrmgnbcucp:enum-EndcMobilityAction;
      default RELEASE;
    }
    leaf betterSpCellTriggerQuantity {
      description "Measurement trigger quantity used when searching for better Special Cell.\nSpecial Cell is either PCell or PSCell.";
      yexte:takes-effect "Next usage.";
      type erienmnrmgnbcucp:enum-TriggerQuantity;
      default RSRP;
    }
  } // end 'grouping moc-IntraFreqMCCellProfile'
  grouping moc-ResourcePartitions-keys {
    description "Key(s) for MOC ResourcePartitions";
    leaf id {
      erienmyext:no-notification;
      description "The value component of the RDN.";
      mandatory true;
      yexte:ecim-name resourcePartitionsId;
      type string;
    }
  } // end 'grouping moc-ResourcePartitions-keys'
  grouping moc-ResourcePartitions {
    description "Set of resource partitions.";
  } // end 'grouping moc-ResourcePartitions'
  grouping moc-ReportConfigA3-keys {
    description "Key(s) for MOC ReportConfigA3";
    leaf id {
      status deprecated {
        yexte:status-information "Since 20.Q4. Planned to be removed.";
      }
      erienmyext:no-notification;
      description "The value component of the RDN.";
      mandatory true;
      yexte:ecim-name reportConfigA3Id;
      type string;
    }
  } // end 'grouping moc-ReportConfigA3-keys'
  grouping moc-ReportConfigA3 {
    description "Report configuration for UE A3 measurement.\n\nThe RDN of this MO is ReportConfigA3=1.";
    leaf endcActionA3EvalFail {
      status deprecated {
        yexte:status-information "Since 20.Q4. Planned to be removed.";
      }
      description "Controls action when intra-frequency handover evaluation or SN change procedure fails.";
      yexte:takes-effect "New connection";
      type erienmnrmgnbcucp:enum-EndcMobilityAction;
      default RELEASE;
    }
    leaf triggerQuantity {
      status deprecated {
        yexte:status-information "Since 20.Q4. Planned to be removed.";
      }
      description "Quantity that triggers event A3.";
      yexte:takes-effect "New connection";
      type erienmnrmgnbcucp:enum-TriggerQuantity;
      default RSRP;
    }
    leaf offset {
      status deprecated {
        yexte:status-information "Since 20.Q4. Planned to be removed.";
      }
      description "Offset value for event A3 measurement.";
      yexte:takes-effect "New connection";
      type erienmnrmgnbcucp:ddt-GNBCUCP_ReportConfigA3_offset;
      default 30;
    }
    leaf timeToTrigger {
      status deprecated {
        yexte:status-information "Since 20.Q4. Planned to be removed.";
      }
      description "Time-to-trigger value for event A3 measurement.";
      yexte:takes-effect "New connection";
      type erienmnrmgnbcucp:ddt-GNBCUCP_ReportConfigA3_timeToTrigger;
      default 640;
    }
    leaf hysteresis {
      status deprecated {
        yexte:status-information "Since 20.Q4. Planned to be removed.";
      }
      description "Hysteresis value for event A3 measurement.";
      yexte:takes-effect "New connection";
      type erienmnrmgnbcucp:ddt-GNBCUCP_ReportConfigA3_hysteresis;
      default 10;
    }
  } // end 'grouping moc-ReportConfigA3'
  grouping moc-ExternalGNBCUCPFunction-keys {
    description "Key(s) for MOC ExternalGNBCUCPFunction";
    leaf id {
      erienmyext:no-notification;
      description "The value component of the RDN.";
      mandatory true;
      yexte:ecim-name externalGNBCUCPFunctionId;
      type string;
    }
  } // end 'grouping moc-ExternalGNBCUCPFunction-keys'
  grouping moc-ExternalGNBCUCPFunction {
    description "Represents external gNodeB-CU-CP function.\n\nWhen created by the system, the RDN of this MO is ExternalGNBCUCPFunction=auto<mcc>_<mnc>_<mncLength>_<gNodeBId>.";
    leaf createdBy {
      config false;
      description "Whether MO is created by the ANR function or operator.";
      notife:notifiable-state-data true;
      type erienmnrmgnbcucp:enum-CreatedByGutran;
    }
    leaf timeOfCreation {
      erienmyext:no-notification;
      config false;
      description "Time and date of MO creation.\nFormat: YYYY-MM-DD HH:MM:SS.";
      type erienmnrmgnbcucp:ddt-GNBCUCP_ExternalGNBCUCPFunction_timeOfCreation;
    }
    leaf gNBId {
      yexte:restricted;
      description "Identifies a gNodeB within a PLMN.";
      mandatory true;
      yexte:takes-effect "New connection";
      yexte:dependencies "The gNBId, gNBIdLength, and pLMNId attribute combination must be unique across ExternalGNBCUCPFunction MO instances.";
      type erienmnrmgnbcucp:ddt-GNBCUCP_ExternalGNBCUCPFunction_gNBId;
    }
    container pLMNId {
      description "PLMN identifier part of global RAN node identity.\n\nThis and gNodeB ID form the global gNodeB ID.\nNote: Value MCC=001, MNC=01 means PLMN is not initiated. This value cannot be used as a valid PLMN Identity.";
      erienmyext:enm-type STRUCT;
      uses erienmnrmgnbcucp:struct-PLMNId;
    } // end 'container pLMNId'
    leaf gNBIdLength {
      yexte:restricted;
      description "Number of bits for encoding gNodeB ID.";
      yexte:takes-effect "New connection";
      yexte:dependencies "The gNBId, gNBIdLength, and pLMNId attribute combination must be unique across ExternalGNBCUCPFunction MO instances.";
      type erienmnrmgnbcucp:ddt-GNBCUCP_ExternalGNBCUCPFunction_gNBIdLength;
      default 22;
    }
  } // end 'grouping moc-ExternalGNBCUCPFunction'
  grouping moc-PmUeMeas-keys {
    description "Key(s) for MOC PmUeMeas";
    leaf id {
      erienmyext:no-notification;
      description "The value component of the RDN.";
      mandatory true;
      yexte:ecim-name pmUeMeasId;
      type string;
    }
  } // end 'grouping moc-PmUeMeas-keys'
  grouping moc-PmUeMeas {
    description "Container class for PM UE measurement profile classes.\n\nThe RDN of this MO must always be PmUeMeas=1.";
  } // end 'grouping moc-PmUeMeas'
  grouping moc-LocalSctpEndpoint-keys {
    description "Key(s) for MOC LocalSctpEndpoint";
    leaf id {
      erienmyext:no-notification;
      description "The value component of the RDN.";
      mandatory true;
      yexte:ecim-name localSctpEndpointId;
      type string;
    }
  } // end 'grouping moc-LocalSctpEndpoint-keys'
  grouping moc-LocalSctpEndpoint {
    description "Local transport network endpoint for control plane interface.\n\nE1 control plane uses TCP, hence this interface is configured in MO class LocalIpEndpoint.";
    leaf sctpEndpointRef {
      description "Reference to SctpEndpoint MO instance.\nMust be unique among LocalSctpEndpoint MO instances under EndpointResource.";
      mandatory true;
      yexte:takes-effect "Node restart";
      yexte:dependencies "If sctpEndpointRef is the same for LocalSctpEndpoint MO instances, interfaceUsed must be the same.";
      erienmyext:enm-type MOREF;
      type string;
    }
    leaf interfaceUsed {
      description "Control plane interface that uses the referenced SctpEndpoint.\nAllowed values: NG, F1, X2 or Xn.\nInterface must be unique across LocalSctpEndpoints under EndpointResource.";
      mandatory true;
      yexte:takes-effect "Node restart";
      yexte:dependencies "Must be the same for LocalSctpEndpoint MO instances, if sctpEndpointRef is the same.";
      type erienmnrmgnbcucp:enum-InterfaceName;
    }
  } // end 'grouping moc-LocalSctpEndpoint'
  grouping moc-Mcfb-keys {
    description "Key(s) for MOC Mcfb";
    leaf id {
      erienmyext:no-notification;
      description "The value component of the RDN.";
      mandatory true;
      yexte:ecim-name mcfbId;
      type string;
    }
  } // end 'grouping moc-Mcfb-keys'
  grouping moc-Mcfb {
    description "Container class for Mobility Control Fallback attributes and profile classes.\n\nThe RDN of this MO is Mcfb=1.";
    leaf mcfbCellProfileEnabled {
      description "McfbCellProfile MO class usage indication.\nIf it set false, the legacy fallback function is used and fallback operation is defined by attributes emergencyFallbackOperation and epsFallbackOperation under NRCellCU.\nIf it set true, fallback function is defined by McfbCellProfile referred by NRCellCU.";
      yexte:takes-effect "Next usage.";
      type boolean;
      default false;
    }
  } // end 'grouping moc-Mcfb'
  grouping moc-TermPointToGNBDU-keys {
    description "Key(s) for MOC TermPointToGNBDU";
    leaf id {
      erienmyext:no-notification;
      description "The value component of the RDN.";
      mandatory true;
      yexte:ecim-name termPointToGNBDUId;
      type string;
    }
  } // end 'grouping moc-TermPointToGNBDU-keys'
  grouping moc-TermPointToGNBDU {
    description "Models an F1-C link to a gNodeB-DU.\n\nCreated by the system when F1-C link is set up.\nDeleted by the system at node restart.\n\nThe RDN of this MO is TermPointToGNBDU=[gNBDUId].";
    leaf usedIpAddress {
      config false;
      description "Destination address used in underlying SCTP association.\nContains address of latest successful F1-C setup.\nIP address can be an IPv4 or an IPv6 address.";
      notife:notifiable-state-data true;
      type string;
    }
    leaf administrativeState {
      status obsolete {
        yexte:status-information "Since 20.Q2. Deprecated: Since 20.Q1. Planned to be removed.";
      }
      description "The administrative state.";
      yexte:disturbances "Changing this attribute to LOCKED causes loss of traffic.";
      type erienmnrmgnbcucp:enum-AdmState;
      default LOCKED;
    }
    leaf-list reservedBy {
      min-elements 0;
      status obsolete {
        yexte:status-information "Since 20.Q2. Deprecated: Since 20.Q1. Planned to be removed.";
      }
      config false;
      description "Contains a list of MO instances that reserve this MO instance.";
      notife:notifiable-state-data true;
      erienmyext:enm-type MOREF;
      type string;
    }
    leaf gNBDUId {
      config false;
      description "Distributed Unit (DU) Identity within the gNodeB.";
      notife:notifiable-state-data true;
      type erienmnrmgnbcucp:ddt-GNBCUCP_TermPointToGNBDU_gNBDUId;
    }
    leaf-list availabilityStatus {
      min-elements 0;
      config false;
      description "The availability status.\nIt contains details about operational state.";
      notife:notifiable-state-data true;
      type erienmnrmgnbcucp:enum-AvailStatus;
    }
    leaf operationalState {
      config false;
      description "The operational state.";
      notife:notifiable-state-data true;
      type erienmnrmgnbcucp:enum-OperState;
    }
    leaf gNBDUName {
      config false;
      description "Distributed Unit (DU) name.";
      notife:notifiable-state-data true;
      type erienmnrmgnbcucp:ddt-GNBCUCP_TermPointToGNBDU_gNBDUName;
    }
  } // end 'grouping moc-TermPointToGNBDU'
  grouping moc-McpcPCellEUtranFreqRelProfile-keys {
    description "Key(s) for MOC McpcPCellEUtranFreqRelProfile";
    leaf id {
      erienmyext:no-notification;
      description "The value component of the RDN.";
      mandatory true;
      yexte:ecim-name mcpcPCellEUtranFreqRelProfileId;
      type string;
    }
  } // end 'grouping moc-McpcPCellEUtranFreqRelProfile-keys'
  grouping moc-McpcPCellEUtranFreqRelProfile {
    description "Mobility Control at Poor Coverage (MCPC) for PCell.\n\nApplies to UEs that use the cell as PCell. Attributes are used on E-UTRAN frequency relation level.\n\nMCPC for PCell is enabled for each NRCellCU MO by setting NRCellCU::mcpcPCellEnabled attribute.\nIf EUtranFreqRelation::mcpcPCellEUtranFreqRelProfileRef is non-empty, attributes from referred MO instance are used.\nIf EUtranFreqRelation::mcpcPCellEUtranFreqRelProfileRef is empty, attribute default values are used according to MO class definition.";
    leaf userLabel {
      description "Label for free use.";
      type erienmnrmgnbcucp:ddt-UserLabel;
    }
    leaf inhibitMeasForCellCandidate {
      description "Whether UE measurement searching for PCell candidate on this frequency is inhibited.";
      yexte:takes-effect "Next usage.";
      type boolean;
      default false;
    }
    container rsrpCandidateB2Offsets {
      description "Downlink RSRP B2 measurement offsets when searching for PCell candidate.";
      erienmyext:enm-type STRUCT;
      uses erienmnrmgnbcucp:struct-ReportConfigB2RsrpOffsets;
    } // end 'container rsrpCandidateB2Offsets'
    leaf-list reservedBy {
      min-elements 0;
      config false;
      description "Contains a list of MO instances that reserve this MO instance.";
      notife:notifiable-state-data true;
      erienmyext:enm-type MOREF;
      type string;
    }
  } // end 'grouping moc-McpcPCellEUtranFreqRelProfile'
  grouping moc-ReportConfigA2-keys {
    description "Key(s) for MOC ReportConfigA2";
    leaf id {
      status deprecated {
        yexte:status-information "Since 20.Q4. Planned to be removed.";
      }
      erienmyext:no-notification;
      description "The value component of the RDN.";
      mandatory true;
      yexte:ecim-name reportConfigA2Id;
      type string;
    }
  } // end 'grouping moc-ReportConfigA2-keys'
  grouping moc-ReportConfigA2 {
    description "Report configuration for UE A2 measurement event.\n\nFunction defined by ReportConfigA2 MO is only applied if attribute NRCellCU::mcpcPCellEnabled is set to false.\nIf attribute mcpcPCellEnabled is set to true function defined by ReportConfigA2 MO is turned off.\n\nThe RDN of this MO is ReportConfigA2=1.";
    leaf thresholdRsrp {
      status deprecated {
        yexte:status-information "Since 20.Q4. Planned to be removed.";
      }
      description "The Reference Signal Received Power (RSRP) threshold value for eventA2.\nUsed only when triggerQuantity is set to RSRP.\nValue -29 corresponds to special value of SS-RSRP = infinity.";
      yexte:takes-effect "New connection";
      type erienmnrmgnbcucp:ddt-GNBCUCP_ReportConfigA2_thresholdRsrp;
      default -140;
    }
    leaf thresholdRsrq {
      status deprecated {
        yexte:status-information "Since 20.Q4. Planned to be removed.";
      }
      description "The Reference Signal Received Quality (RSRQ) threshold value for eventA2.\nUsed only when triggerQuantity is set to RSRQ.";
      yexte:takes-effect "New connection";
      type erienmnrmgnbcucp:ddt-GNBCUCP_ReportConfigA2_thresholdRsrq;
      default -435;
    }
    leaf triggerQuantity {
      status deprecated {
        yexte:status-information "Since 20.Q4. Planned to be removed.";
      }
      description "The quantity that triggers the eventA2.";
      yexte:takes-effect "New connection";
      type erienmnrmgnbcucp:enum-TriggerQuantity;
      default RSRP;
    }
    leaf timeToTrigger {
      status deprecated {
        yexte:status-information "Since 20.Q4. Planned to be removed.";
      }
      description "The time-to-trigger value for the eventA2 measurement.";
      yexte:takes-effect "New connection";
      type erienmnrmgnbcucp:ddt-GNBCUCP_ReportConfigA2_timeToTrigger;
      default 640;
    }
    leaf hysteresis {
      status deprecated {
        yexte:status-information "Since 20.Q4. Planned to be removed.";
      }
      description "The hysteresis value for the eventA2 measurement.";
      yexte:takes-effect "New connection";
      type erienmnrmgnbcucp:ddt-GNBCUCP_ReportConfigA2_hysteresis;
      default 10;
    }
  } // end 'grouping moc-ReportConfigA2'
  grouping moc-NRNetwork-keys {
    description "Key(s) for MOC NRNetwork";
    leaf id {
      erienmyext:no-notification;
      description "The value component of the RDN.";
      mandatory true;
      yexte:ecim-name nRNetworkId;
      type string;
    }
  } // end 'grouping moc-NRNetwork-keys'
  grouping moc-NRNetwork {
    description "Container for MOs related to NR networks.\n\nWhen created by the system, the RDN of this MO is NRNetwork=1.";
  } // end 'grouping moc-NRNetwork'
  grouping moc-IntraFreqMC-keys {
    description "Key(s) for MOC IntraFreqMC";
    leaf id {
      erienmyext:no-notification;
      description "The value component of the RDN.";
      mandatory true;
      yexte:ecim-name intraFreqMCId;
      type string;
    }
  } // end 'grouping moc-IntraFreqMC-keys'
  grouping moc-IntraFreqMC {
    description "This is a container for Intra-frequency mobility control profiles.\n\nThe RDN of this MO must always be IntraFreqMC=1.";
    leaf intraFreqMCCellProfileUsage {
      description "IntraFreqMCCellProfile MO class usage in relation to the deprecated MO class ReportConfigA3.";
      yexte:takes-effect "Next usage.";
      type erienmnrmgnbcucp:enum-IntraFreqMCCellProfileUsage;
      default LIMITED_USAGE;
    }
  } // end 'grouping moc-IntraFreqMC'
  grouping moc-SecurityHandling-keys {
    description "Key(s) for MOC SecurityHandling";
    leaf id {
      erienmyext:no-notification;
      description "The value component of the RDN.";
      mandatory true;
      yexte:ecim-name securityHandlingId;
      type string;
    }
  } // end 'grouping moc-SecurityHandling-keys'
  grouping moc-SecurityHandling {
    description "Manageable characteristics of security handling except during X2 handover and S1 handover.\n\nThe RDN of this MO is SecurityHandling=1.";
    leaf-list integrityProtectAlgoPrio {
      min-elements 1;
      max-elements 3;
      description "Array of allowed integrity algorithms with priority order.\nMinimum length of 1, maximum length of 3. Algorithm in index zero has highest priority. Each algorithm written only once in array.";
      yexte:takes-effect "New connection";
      type erienmnrmgnbcucp:enum-IntegrityAlgorithmID;
      default NIA2;
      default NIA1;
    }
    leaf-list cipheringAlgoPrio {
      min-elements 1;
      max-elements 4;
      description "Array of allowed ciphering algorithms with priority order.\nMinimum length of 1, maximum length of 4. Algorithm in index zero has highest priority. Each algorithm written only once in array.";
      yexte:takes-effect "New connection";
      type erienmnrmgnbcucp:enum-CipheringAlgorithmID;
      default NEA1;
      default NEA2;
      default NEA0;
    }
    leaf personalDataProtectionEnabled {
      description "Whether personal data protection is enabled.\nWhen personal data protection is enabled, subscriber personal data is not logged.\nIf protection is disabled, there are rare traffic occasions when subscriber personal data is revealed and can be logged in PM events and other short-lived on-demand troubleshooting logs.\nAlert is raised when personal data protection is set to be disabled.";
      yexte:takes-effect "Node restart";
      type boolean;
      default true;
    }
  } // end 'grouping moc-SecurityHandling'
  grouping moc-CUCP5qiTable-keys {
    description "Key(s) for MOC CUCP5qiTable";
    leaf id {
      erienmyext:no-notification;
      description "The value component of the RDN.";
      mandatory true;
      yexte:ecim-name cUCP5qiTableId;
      type string;
    }
  } // end 'grouping moc-CUCP5qiTable-keys'
  grouping moc-CUCP5qiTable {
    description "Mapping from 5G QoS Identifier to parameters that have impact on QoS.\n\nThe table must contain at least one CUCP5qi with resource type NON_GBR.";
    leaf default5qiTable {
      description "Indicates that the CUCP5qiTable instance is a default 5QI table.\nThe default 5QI table will be used when no CUCP5qiTable has been configured for a resource partition.";
      yexte:takes-effect "New connection";
      yexte:dependencies "Only one CUCP5qiTable instance can have the attribute default5qiTable set to TRUE.";
      type boolean;
      default false;
    }
    leaf-list reservedBy {
      min-elements 0;
      config false;
      description "Contains a list of MO instances that reserve this MO instance.";
      notife:notifiable-state-data true;
      erienmyext:enm-type MOREF;
      type string;
    }
    leaf resourcePartitionRef {
      status obsolete {
        yexte:status-information "Since 20.Q2. Deprecated: Since 20.Q1. Planned to be removed.";
      }
      description "Reference to an instance of ResourcePartition MO.";
      yexte:takes-effect "New connection";
      erienmyext:enm-type MOREF;
      type string;
    }
  } // end 'grouping moc-CUCP5qiTable'
  grouping moc-McfbCellProfile-keys {
    description "Key(s) for MOC McfbCellProfile";
    leaf id {
      erienmyext:no-notification;
      description "The value component of the RDN.";
      mandatory true;
      yexte:ecim-name mcfbCellProfileId;
      type string;
    }
  } // end 'grouping moc-McfbCellProfile-keys'
  grouping moc-McfbCellProfile {
    description "Profile of Mobility Control Fallback for cell.\n\nApplies to UEs which use the cell as PCell. Attributes are used on cell level.";
    leaf epsFallbackOperation {
      description "Policy for EPS fallback or Voice over NR (VoNR) for voice calls.";
      yexte:takes-effect "Next usage.";
      type erienmnrmgnbcucp:enum-EpsFallbackOperationType;
      default FORCED;
    }
    leaf epsFbTargetSearchTimer {
      description "Length of time the gNodeB waits for reports from B1 measurement for EPS Fallback reasons.";
      yexte:takes-effect "Next usage.";
      type erienmnrmgnbcucp:ddt-GNBCUCP_McfbCellProfile_epsFbTargetSearchTimer;
      default 500;
    }
    container rsrqCellCandidate {
      description "RSRQ B1 measurement report criteria when searching for E-UTRAN cell candidate.";
      erienmyext:enm-type STRUCT;
      uses erienmnrmgnbcucp:struct-ReportConfigB1Rsrq;
    } // end 'container rsrqCellCandidate'
    leaf triggerQuantity {
      description "Quantity that triggers the event B1 and A2.";
      yexte:takes-effect "Next usage.";
      type erienmnrmgnbcucp:enum-TriggerQuantity;
      default RSRP;
    }
    container rsrpCellCandidate {
      description "RSRP B1 measurement report criteria when searching for E-UTRAN cell candidate.";
      erienmyext:enm-type STRUCT;
      uses erienmnrmgnbcucp:struct-ReportConfigB1Rsrp;
    } // end 'container rsrpCellCandidate'
    leaf-list reservedBy {
      min-elements 0;
      config false;
      description "Contains a list of MO instances that reserve this MO instance.";
      notife:notifiable-state-data true;
      erienmyext:enm-type MOREF;
      type string;
    }
    container rsrpCriticalCoverage {
      description "RSRP A2 measurement report criteria for detecting critical coverage.";
      erienmyext:enm-type STRUCT;
      uses erienmnrmgnbcucp:struct-ReportConfigA1A2Rsrp;
    } // end 'container rsrpCriticalCoverage'
    container rsrqCriticalCoverage {
      description "RSRQ A2 measurement report criteria for detecting critical coverage.";
      erienmyext:enm-type STRUCT;
      uses erienmnrmgnbcucp:struct-ReportConfigA1A2Rsrq;
    } // end 'container rsrqCriticalCoverage'
    leaf epsFallbackOperationEm {
      description "Policy for EPS fallback or Voice over NR (VoNR) for emergency calls.";
      yexte:takes-effect "Next usage.";
      type erienmnrmgnbcucp:enum-EpsFbOperationTypeEm;
      default FORCED;
    }
  } // end 'grouping moc-McfbCellProfile'
  grouping moc-CUCPResourcePartition-keys {
    description "Key(s) for MOC CUCPResourcePartition";
    leaf id {
      status obsolete {
        yexte:status-information "Since 20.Q2. Deprecated: Since 19.Q4. Planned to be removed.";
      }
      erienmyext:no-notification;
      description "The value component of the RDN.";
      mandatory true;
      yexte:ecim-name cUCPResourcePartitionId;
      type string;
    }
  } // end 'grouping moc-CUCPResourcePartition-keys'
  grouping moc-CUCPResourcePartition {
    description "Combination of attributes specifying in which resource partition a UE is included.";
    leaf-list mappedSliceList {
      min-elements 0;
      max-elements 36;
      status obsolete {
        yexte:status-information "Since 20.Q2. Deprecated: Since 19.Q4. Planned to be removed.";
      }
      description "List of mapped slices to 5QI table.";
      yexte:takes-effect "New connection";
      erienmyext:enm-type MOREF;
      type string;
    }
  } // end 'grouping moc-CUCPResourcePartition'
  grouping moc-CUCP5qi-keys {
    description "Key(s) for MOC CUCP5qi";
    leaf id {
      erienmyext:no-notification;
      description "The value component of the RDN.";
      mandatory true;
      yexte:ecim-name cUCP5qiId;
      type string;
    }
  } // end 'grouping moc-CUCP5qi-keys'
  grouping moc-CUCP5qi {
    description "QoS configuration corresponding to 3GPP-defined and operator-defined 5QI profiles.\n\nMaximum number of operator-defined profiles is 9.\n\nEach profile can be present once in each table.";
    leaf serviceType {
      status current {
        yexte:preliminary;
      }
      description "Service of flow.";
      yexte:dependencies "VOIP if profile5qi is 1.\nIMS_SIGNALING if profile5qi is 5.\nPTT if profile5qi is 65 or 66.\nMC_SIGNALING if profile5qi is 69.\nUNDEFINED if profile5qi is 2, 3, 4, 6 ,7, 8, 9, 67, 70, 79, 80, 82, 83, 84 or 85.";
      type erienmnrmgnbcucp:enum-ServiceType;
      default UNDEFINED;
    }
    leaf tPdcpDiscard {
      description "UL PDCP discard timer used in UE.\nFollowing values are recommended:\n-150 if profile5qi is 1.\n-200 if profile5qi is 2, 3, 4, 65, 66, 67, 69, 70, 79, 80, 82, 83, 84 or 85.\n- 1500 if profile5qi is 6, 7, 8 or 9.\n- 2147483646 (infinity) if profile5qi is 5.";
      type erienmnrmgnbcucp:ddt-GNBCUCP_CUCP5qi_tPdcpDiscard;
      default 1500;
    }
    leaf userLabel {
      status current {
        yexte:preliminary;
      }
      description "Label for free use.";
      type erienmnrmgnbcucp:ddt-UserLabel;
    }
    leaf profile5qi {
      description "5G QoS Identifier unique within a table.\nFor 3GPP-defined 5QIs, 5QI can be 1, 2, 3, 4, 5, 6, 7, 8, 9, 65, 66, 67, 69, 70, 79, 80, 82, 83, 84 or 85.";
      mandatory true;
      yexte:dependencies "Value must be unique in 5qiTable.\nFor 3GPP-defined profiles:\n- profile5qi=1, resourceType must be GBR, packetErrorRateScalar must be 1, packetErrorRateExp must be 2, rlcMode must be UM and serviceType must be VOIP.\n- profile5qi=2, resourceType must be GBR, packetErrorRateScalar must be 1, packetErrorRateExp must be 3 and serviceType must be UNDEFINED.\n- profile5qi=3, resourceType must be GBR, packetErrorRateScalar must be 1, packetErrorRateExp must be 3 and serviceType must be UNDEFINED.\n- profile5qi=4, resourceType must be GBR, packetErrorRateScalar must be 1, packetErrorRateExp must be 6 and serviceType must be UNDEFINED.\n- profile5qi=5, resourceType must be NON_GBR, packetErrorRateScalar must be 1, packetErrorRateExp must be 6, rlcMode must be AM and serviceType must be IMS_SIGNALING.\n- profile5qi=6, resourceType must be NON_GBR, packetErrorRateScalar must be 1, packetErrorRateExp must be 6 and serviceType must be UNDEFINED.\n- profile5qi=7, resourceType must be NON_GBR, packetErrorRateScalar must be 1, packetErrorRateExp must be 3 and serviceType must be UNDEFINED.\n- profile5qi=8, resourceType must be NON_GBR, packetErrorRateScalar must be 1, packetErrorRateExp must be 6 and serviceType must be UNDEFINED.\n- profile5qi=9, resourceType must be NON_GBR, packetErrorRateScalar must be 1, packetErrorRateExp must be 6 and serviceType must be UNDEFINED.\n- profile5qi=65, resourceType must be GBR, packetErrorRateScalar must be 1, packetErrorRateExp must be 2, rlcMode must be UM and serviceType must be PTT.\n- profile5qi=66, resourceType must be GBR, packetErrorRateScalar must be 1, packetErrorRateExp must be 2, rlcMode must be UM and serviceType must be PTT.\n- profile5qi=67, resourceType must be GBR, packetErrorRateScalar must be 1, packetErrorRateExp must be 3 and serviceType must be UNDEFINED.\n- profile5qi=69, resourceType must be NON_GBR, packetErrorRateScalar must be 1, packetErrorRateExp must be 6, rlcMode must be AM and serviceType must be MC_SIGNALING.\n- profile5qi=70, resourceType must be NON_GBR, packetErrorRateScalar must be 1, packetErrorRateExp must be 6 and serviceType must be UNDEFINED.\n- profile5qi=79, resourceType must be NON_GBR, packetErrorRateScalar must be 1, packetErrorRateExp must be 2, rlcMode must be UM and serviceType must be UNDEFINED.\n- profile5qi=80, resourceType must be NON_GBR, packetErrorRateScalar must be 1, packetErrorRateExp must be 6, rlcMode must be UM and serviceType must be UNDEFINED.\n- profile5qi=82, resourceType must be DC_GBR, packetErrorRateScalar must be 1, packetErrorRateExp must be 4, rlcMode must be UM and serviceType must be UNDEFINED.\n- profile5qi=83, resourceType must be DC_GBR, packetErrorRateScalar must be 1, packetErrorRateExp must be 4, rlcMode must be UM and serviceType must be UNDEFINED.\n- profile5qi=84, resourceType must be DC_GBR, packetErrorRateScalar must be 1, packetErrorRateExp must be 5, rlcMode must be UM and serviceType must be UNDEFINED.\n- profile5qi=85, resourceType must be DC_GBR, packetErrorRateScalar must be 1, packetErrorRateExp must be 5, rlcMode must be UM and serviceType must be UNDEFINED.";
      type erienmnrmgnbcucp:ddt-GNBCUCP_CUCP5qi_profile5qi;
    }
    leaf tReorderingUl {
      description "T-reordering UL timer used by the receiving-end PDCP entity in the gNodeB.\nRecommended value is 20 if profile5qi is 1, 2, 3, 4, 5, 6, 7, 8, 9, 65, 66, 67, 69, 70, 79, 80, 82, 83, 84 or 85.";
      type erienmnrmgnbcucp:ddt-GNBCUCP_CUCP5qi_tReorderingUl;
      default 20;
    }
    leaf tReorderingDl {
      description "T-reordering DL timer used by the receiving-end PDCP entity in the UE.\nRecommended value is 200 if profile5qi is 1, 2, 3, 4, 5, 6, 7, 8, 9, 65, 66, 67, 69, 70, 79, 80, 82, 83, 84 or 85.";
      type erienmnrmgnbcucp:ddt-GNBCUCP_CUCP5qi_tReorderingDl;
      default 200;
    }
    leaf rlcMode {
      description "RLC mode for DRB.\nRecommended values for non-restricted 5QIs:\nUM if profile5qi is 2.\nAM if profile5qi is 6, 7, 8, 9 or 70.";
      yexte:dependencies "For restricted 5QIs:\nUM if profile5qi is 1, 65, 66, 79, 80, 82, 83, 84, or 85.\nAM if profile5qi is 5 or 69.";
      type erienmnrmgnbcucp:enum-RlcMode;
      default AM;
    }
    leaf packetErrorRateScalar {
      status current {
        yexte:preliminary;
      }
      description "Scalar value of following packet error rate expression, where k is the exponent: Scalar x 10 - k.";
      yexte:dependencies "Must be 1 if profile5qi is 1, 2, 3, 4, 5, 6, 7, 8, 9, 65, 66, 67, 69, 70, 79, 80, 82, 83, 84 or 85.";
      type erienmnrmgnbcucp:ddt-GNBCUCP_CUCP5qi_packetErrorRateScalar;
      default 1;
    }
    leaf packetErrorRateExp {
      status current {
        yexte:preliminary;
      }
      description "Exponent value of following packet error rate expression, where k is the exponent: Scalar x 10 - k.";
      yexte:dependencies "Must be 2 if profile5qi is 1, 65, 66 or 79.\nMust be 3 if profile5qi is 2, 3, 7 or 67.\nMust be 6 if profile5qi is 4, 5, 6, 8, 9, 69, 70 or 80.\nMust be 4 if profile5qi is 82 or 83.\nMust be 5 if profile5qi is 84 or 85.";
      type erienmnrmgnbcucp:ddt-GNBCUCP_CUCP5qi_packetErrorRateExp;
      default 6;
    }
    leaf pdcpSnSize {
      description "PDCP sequence number length.\nFollowing values are recommended:\n-12 if profile5qi is 1, 2, 3, 4, 5, 6, 7, 65, 66, 67, 69, 70, 79, 80, 82, 83, 84 or 85.\n-18 if profile5qi is 8 or 9.";
      type erienmnrmgnbcucp:ddt-GNBCUCP_CUCP5qi_pdcpSnSize;
      default 18;
    }
    leaf resourceType {
      status current {
        yexte:preliminary;
      }
      description "Resource type of the Quality of Service indicator (5QI).";
      yexte:dependencies "GBR if profile5qi is 1, 2, 3, 4, 65, 66 or 67.\nNON_GBR if profile5qi is 5, 6, 7, 8, 9, 69, 70, 79 or 80.\nDC_GBR if profile5qi is 82, 83, 84 or 85.";
      type erienmnrmgnbcucp:enum-ResourceType;
      default NON_GBR;
    }
  } // end 'grouping moc-CUCP5qi'
  grouping moc-UeMC-keys {
    description "Key(s) for MOC UeMC";
    leaf id {
      erienmyext:no-notification;
      description "The value component of the RDN.";
      mandatory true;
      yexte:ecim-name ueMCId;
      type string;
    }
  } // end 'grouping moc-UeMC-keys'
  grouping moc-UeMC {
    description "Container class for UE Mobility Control (UeMC) attributes and UeMC profile classes.\n\nThe RDN of this MO must always be UeMC=1";
    leaf userLabel {
      description "Label for free use.";
      type erienmnrmgnbcucp:ddt-UserLabel;
    }
    leaf ueMCCellProfileEnabled {
      description "UeMCCellProfile MO class usage in relation to the deprecated MO class UeMeasControl.\nIf set to false attribute values from UeMCCellProfile MO class instances are not used.\nInstead attribute values from deprecated UeMeasControl MO class instances are used.\nIf set to true attribute values from UeMCCellProfile MO class instances are used.\nAttribute values from instances of deprecated MO class UeMeasControl are not used.";
      yexte:takes-effect "Next usage.";
      type boolean;
      default false;
    }
  } // end 'grouping moc-UeMC'
  grouping moc-TermPointToGNBCUUP-keys {
    description "Key(s) for MOC TermPointToGNBCUUP";
    leaf id {
      erienmyext:no-notification;
      description "The value component of the RDN.";
      mandatory true;
      yexte:ecim-name termPointToGNBCUUPId;
      type string;
    }
  } // end 'grouping moc-TermPointToGNBCUUP-keys'
  grouping moc-TermPointToGNBCUUP {
    description "Models an E1 link to a gNodeB-CU-UP.\n\nCreated by the system when E1 link is set up.\nDeleted by the system at node restart.\n\nThe RDN of this MO is TermPointToGNBCUUP=[Local Ip Address]_[Remote Ip Address].";
    leaf usedIpAddress {
      config false;
      description "Destination address used in underlying connection.\nContains address of latest successful E1 setup.\nIP address can be an IPv4 or an IPv6 address.";
      notife:notifiable-state-data true;
      type string;
    }
    leaf gNBCUUPName {
      config false;
      description "Central Unit User Plane (CUUP) name.";
      notife:notifiable-state-data true;
      type string;
    }
    leaf gNBCUUPId {
      config false;
      description "Central Unit User Plane (CUUP) identity within gNodeB.";
      notife:notifiable-state-data true;
      type int64;
    }
    leaf-list availabilityStatus {
      min-elements 0;
      config false;
      description "The availability status.\nIt contains details about operationalState.";
      notife:notifiable-state-data true;
      type erienmnrmgnbcucp:enum-AvailStatus;
    }
    leaf operationalState {
      config false;
      description "The operational state.";
      notife:notifiable-state-data true;
      type erienmnrmgnbcucp:enum-OperState;
    }
  } // end 'grouping moc-TermPointToGNBCUUP'
  grouping moc-GNBCUCPFunction-keys {
    description "Key(s) for MOC GNBCUCPFunction";
    leaf id {
      erienmyext:no-notification;
      description "The value component of the RDN.";
      mandatory true;
      yexte:ecim-name gNBCUCPFunctionId;
      type string;
    }
  } // end 'grouping moc-GNBCUCPFunction-keys'
  grouping moc-GNBCUCPFunction {
    description "Represents the logical node gNodeB-CU-CP.";
    leaf userLabel {
      description "Label for free use.";
      type erienmnrmgnbcucp:ddt-UserLabel;
    }
    leaf xnSctpEndPointRef {
      status deprecated {
        yexte:status-information "Since 20.Q3. Replaced by LocalSctpEndpoint::sctpEndpointRef. Planned to be removed.";
      }
      description "Reference to SctpEndpoint MO for Xn control connections.";
      yexte:takes-effect "Node restart";
      yexte:dependencies "Cannot refer to same MO as ngcSctpEndPointRef, x2SctpEndPointRef, or f1SctpEndPointRef.";
      erienmyext:enm-type MOREF;
      type string;
    }
    leaf pwsServiceState {
      status obsolete {
        yexte:status-information "Since 20.Q3. Planned to be removed.";
      }
      config false;
      description "Value true if PWS broadcast is scheduled.";
      notife:notifiable-state-data true;
      type boolean;
    }
    leaf release {
      config false;
      description "The product release of the ManagedFunction.";
      notife:notifiable-state-data true;
      type string;
    }
    leaf endpointResDepHEnabled {
      description "Whether endpoint resource deprecation handling is enabled.\nIf true, updating following deprecated attributes also updates the IP addresses configured with MO classes EndPointResource, LocalSctpEndpoint and LocalIpEndpoint:\n- x2SctpEndPointRef\n- xnSctpEndPointRef\n- f1SctpEndPointRef\n- intraRanIpAddressRef\n- ngcSctpEndPointRef\nIf false, updating the deprecated attributes does not update following MO classes:\n- EndPointResource\n- LocalSctpEndpoint\n- LocalIpEndpoint\nNode always uses the IP addresses configured with following MO classes:\n- EndPointResource\n- LocalSctpEndpoint\n- LocalIpEndpoint\nUpdating these MO classes never updates deprecated attributes. Deprecated attributes cannot express all configurations.\nDeprecation handling can be disabled. This protects following MO classes from modification from older management system versions where only the deprecated attributes are visible:\n- EndPointResource\n- LocalSctpEndpoint\n- LocalIpEndpoint";
      type boolean;
      default true;
    }
    leaf maxCommonProcTime {
      description "Maximum time until an expected response message to a common procedure is considered lost.";
      yexte:takes-effect "New connection";
      type erienmnrmgnbcucp:ddt-GNBCUCP_GNBCUCPFunction_maxCommonProcTime;
      default 30;
    }
    leaf ngcDedProcTime {
      description "Time until response to UE-dedicated NGAP message considered lost.";
      yexte:takes-effect "New connection";
      type erienmnrmgnbcucp:ddt-GNBCUCP_GNBCUCPFunction_ngcDedProcTime;
      default 5;
    }
    leaf ngcSctpEndPointRef {
      status deprecated {
        yexte:status-information "Since 20.Q3. Replaced by LocalSctpEndpoint::sctpEndpointRef. Planned to be removed.";
      }
      description "Reference to SctpEndpoint MO in gNodeB for NG-C interface to AMF.";
      yexte:takes-effect "Node restart";
      yexte:dependencies "Cannot refer to same MO as x2SctpEndPointRef, f1SctpEndPointRef, or xnSctpEndPointRef.";
      erienmyext:enm-type MOREF;
      type string;
    }
    leaf endpointResourceRef {
      description "Reference to EndpointResource MO instance.\nResourcePartitionMember MO can also refer to EndpointResource MO instances only valid for specific PLMN or NSSAI. If ResourcePartitionMember::endpointResourceRef is empty, this reference is used.";
      yexte:takes-effect "Node restart";
      erienmyext:enm-type MOREF;
      type string;
    }
    container pLMNId {
      description "PLMN identifier to be used as part of global RAN node identity.\n\nValue (MCC=001, MNC=01) indicates that PLMN is not initiated and cannot be used as a valid PLMN Identity.";
      erienmyext:enm-type STRUCT;
      uses erienmnrmgnbcucp:struct-PLMNId;
    } // end 'container pLMNId'
    leaf tInactivityTimer {
      description "Time NR SA UE can be inactive before released.";
      yexte:takes-effect "New connection";
      type erienmnrmgnbcucp:ddt-GNBCUCP_GNBCUCPFunction_tInactivityTimer;
      default 10;
    }
    leaf f1SctpEndPointRef {
      status deprecated {
        yexte:status-information "Since 20.Q3. Replaced by LocalSctpEndpoint::sctpEndpointRef. Planned to be removed.";
      }
      description "Reference to SctpEndpoint MO for F1 control connections.";
      yexte:takes-effect "Node restart";
      yexte:dependencies "Cannot refer to same MO as ngcSctpEndPointRef, x2SctpEndPointRef, or xnSctpEndPointRef.";
      erienmyext:enm-type MOREF;
      type string;
    }
    leaf tDcOverall {
      description "Waiting time in EN-DC setup procedure.\nWaiting time for SN STATUS TRANSFER and SGNB RECONFIGURATION COMPLETE during SgNB Addition on X2AP.";
      yexte:takes-effect "New connection";
      type erienmnrmgnbcucp:ddt-GNBCUCP_GNBCUCPFunction_tDcOverall;
      default 7;
    }
    leaf pwsBroadcastStarted {
      config false;
      description "Whether PWS service is started.";
      notife:notifiable-state-data true;
      type boolean;
    }
    leaf nasInactivityTime {
      description "NAS inactivity time to pass before NGAP UE Context Release Request procedure initiated.";
      yexte:takes-effect "New connection";
      type erienmnrmgnbcucp:ddt-GNBCUCP_GNBCUCPFunction_nasInactivityTime;
      default 5;
    }
    leaf x2SctpEndPointRef {
      status deprecated {
        yexte:status-information "Since 20.Q3. Replaced by LocalSctpEndpoint::sctpEndpointRef. Planned to be removed.";
      }
      description "Reference to SctpEndpoint MO for X2 control connections.";
      yexte:takes-effect "Node restart";
      yexte:dependencies "Cannot refer to same MO as ngcSctpEndPointRef, f1SctpEndPointRef, or xnSctpEndPointRef.";
      erienmyext:enm-type MOREF;
      type string;
    }
    leaf intraRanIpAddressRef {
      status deprecated {
        yexte:status-information "Since 20.Q3. Replaced by LocalIpEndpoint::addressRef. Planned to be removed.";
      }
      description "Reference to IP address for Intra-RAN connections.\nMust be configured for NR Virtual Packet Processing. Used for Intra-RAN control connections.\nReference to MO type AddressIPv4 or AddressIPv6 in embedded CU-CP deployment and IPv4AccessPoint or IPv6AccessPoint in virtual CU-CP deployment.";
      yexte:takes-effect "Node restart";
      erienmyext:enm-type MOREF;
      type string;
    }
    leaf gNBId {
      description "Identity of gNodeB within a PLMN.\nPart of the NR Cell Global Identity. Identifies node over NG-C and X2.";
      mandatory true;
      yexte:takes-effect "Node restart";
      yexte:dependencies "gNBId =< (2^gNBIdLength)-1";
      type erienmnrmgnbcucp:ddt-GNBCUCP_GNBCUCPFunction_gNBId;
    }
    leaf maxNgRetryTime {
      description "Maximum time between consecutive NG setup attempts.\nTime between retry attempts is increasing for every retry. This value sets un upperbound to it.";
      yexte:takes-effect "New connection";
      type erienmnrmgnbcucp:ddt-GNBCUCP_GNBCUCPFunction_maxNgRetryTime;
      default 30;
    }
    leaf gNBIdLength {
      description "Length of gNBId bit string representation.\nIf gNBId bit representation exceeds 22 bits, gNBIdLength value must be at least minimum bit length that can accommodate gNBId.\ngNBId =< (2^gNBIdLength)-1";
      yexte:takes-effect "Node restart";
      type erienmnrmgnbcucp:ddt-GNBCUCP_GNBCUCPFunction_gNBIdLength;
      default 22;
    }
    leaf noOfSupportedNRCellCU {
      erienmyext:no-notification;
      config false;
      description "Supported number of NRCellCU instances in current deployment.";
      type int32;
    }
    leaf gNBCUName {
      description "Central Unit (CU) name.";
      yexte:takes-effect "New connection";
      type erienmnrmgnbcucp:ddt-GNBCUCP_GNBCUCPFunction_gNBCUName;
    }
  } // end 'grouping moc-GNBCUCPFunction'
  grouping moc-UeMCCellProfile-keys {
    description "Key(s) for MOC UeMCCellProfile";
    leaf id {
      erienmyext:no-notification;
      description "The value component of the RDN.";
      mandatory true;
      yexte:ecim-name ueMCCellProfileId;
      type string;
    }
  } // end 'grouping moc-UeMCCellProfile-keys'
  grouping moc-UeMCCellProfile {
    description "UE Mobility Control attributes.\n\nThe attributes are used on cell level.\n\nIf NRCellCU::ueMCCellProfileRef is non-empty, attributes from referred MO instance are used.\nIf NRCellCU::ueMCCellProfileRef is empty, attribute default values according to MO class definition are used.";
    leaf freqClassificationThreshold {
      description "Frequency classification threshold.\nThreshold is provided as ARFCN-ValueNR value and defines which filter coefficients that will be used by UE when measuring on NR frequencies.";
      yexte:takes-effect "Next usage.";
      type erienmnrmgnbcucp:ddt-GNBCUCP_UeMCCellProfile_freqClassificationThreshold;
      default 3279163;
    }
    leaf userLabel {
      description "Label for free use.";
      type erienmnrmgnbcucp:ddt-UserLabel;
    }
    leaf filterCoefficientEUtraRsrp {
      description "Layer 3 average filter coefficient applied in UE performing RSRP measurements on E-UTRA frequencies.";
      yexte:takes-effect "Next usage.";
      type erienmnrmgnbcucp:ddt-GNBCUCP_UeMCCellProfile_filterCoefficientEUtraRsrp;
      default 4;
    }
    leaf filterCoefficientNrRsrqHigh {
      description "Layer 3 average filter coefficient applied in UE performing RSRQ measurements on NR frequencies.\nFilter coefficient for measurement of NR frequencies with ARFCN-ValueNR value higher than ARFCN-ValueNR defined by attribute freqClassificationThreshold.";
      yexte:takes-effect "Next usage.";
      type erienmnrmgnbcucp:ddt-GNBCUCP_UeMCCellProfile_filterCoefficientNrRsrqHigh;
      default 11;
    }
    leaf sMeasure {
      description "RSRP measurement threshold when UE is required to perform measurements on non-serving cells.\nCorresponds to RRC parameter s-MeasureConfig and choice ssb-RSRP.\nIf set to empty, threshold is not used.\nValue -29 corresponds to special value of ssb-RSRP = infinity.";
      yexte:takes-effect "Next usage.";
      type erienmnrmgnbcucp:ddt-GNBCUCP_UeMCCellProfile_sMeasure;
      default -29;
    }
    leaf filterCoefficientEUtraRsrq {
      description "Layer 3 average filter coefficient applied in UE performing RSRQ measurements on E-UTRA frequencies.";
      yexte:takes-effect "Next usage.";
      type erienmnrmgnbcucp:ddt-GNBCUCP_UeMCCellProfile_filterCoefficientEUtraRsrq;
      default 11;
    }
    leaf-list reservedBy {
      min-elements 0;
      config false;
      description "Contains a list of MO instances that reserve this MO instance.";
      notife:notifiable-state-data true;
      erienmyext:enm-type MOREF;
      type string;
    }
    leaf filterCoefficientNrRsrpHigh {
      description "Layer 3 average filter coefficient applied in UE performing RSRP measurements on NR frequencies.\nFilter coefficient for measurement of NR frequencies with ARFCN-ValueNR value higher than ARFCN-ValueNR defined by attribute freqClassificationThreshold.";
      yexte:takes-effect "Next usage.";
      type erienmnrmgnbcucp:ddt-GNBCUCP_UeMCCellProfile_filterCoefficientNrRsrpHigh;
      default 4;
    }
    leaf filterCoefficientNrRsrqLow {
      description "Layer 3 average filter coefficient applied in UE performing RSRQ measurements on NR frequencies.\nFilter coefficient for measurement of NR frequencies with ARFCN-ValueNR value lower than or equal to ARFCN-ValueNR defined by attribute freqClassificationThreshold.";
      yexte:takes-effect "Next usage.";
      type erienmnrmgnbcucp:ddt-GNBCUCP_UeMCCellProfile_filterCoefficientNrRsrqLow;
      default 11;
    }
    leaf filterCoefficientNrRsrpLow {
      description "Layer 3 average filter coefficient applied in UE performing RSRP measurements on NR frequencies.\nFilter coefficient for measurement of NR frequencies with ARFCN-ValueNR value lower than or equal to ARFCN-ValueNR defined by attribute freqClassificationThreshold.";
      yexte:takes-effect "Next usage.";
      type erienmnrmgnbcucp:ddt-GNBCUCP_UeMCCellProfile_filterCoefficientNrRsrpLow;
      default 4;
    }
  } // end 'grouping moc-UeMCCellProfile'
  grouping moc-ResourcePartitionMember-keys {
    description "Key(s) for MOC ResourcePartitionMember";
    leaf id {
      erienmyext:no-notification;
      description "The value component of the RDN.";
      mandatory true;
      yexte:ecim-name resourcePartitionMemberId;
      type string;
    }
  } // end 'grouping moc-ResourcePartitionMember-keys'
  grouping moc-ResourcePartitionMember {
    description "Set of member information of resource partition.";
    list sNSSAIList {
      min-elements 0;
      max-elements 1024;
      key auto-generated-struct-key;
      leaf auto-generated-struct-key {
        type uint16;
        description "This leaf has been injected to allow for struct instances in a sequence to be ordered.";
        mandatory true;
      }
      description "List of Single Network Slice Selection Assistance Information (S-NSSAI).";
      erienmyext:enm-type STRUCT;
      uses erienmnrmgnbcucp:struct-SliceSelectionAssistInfo;
    } // end 'list sNSSAIList'
    leaf endpointResourceRef {
      description "Reference to EndpointResource MO instance.\nThe reference setting defines the Transport Network configuration for specific PLMN or NSSAI.\nIf this reference is empty, attribute GNBCUCPFunction::endpointResourceRef is used.\nCannot refer to EndpointResource MO which has LocalSctpEndpoint::interfaceUsed set to F1. F1 SctpEndpoint can only be referenced from GNBCUCPFunction::endpointResourceRef.";
      yexte:takes-effect "Node restart";
      yexte:dependencies "Must be empty if ResourcePartition::related5qiTableRef is non-empty.\nIf endpointResourceRef is non-empty, the following dependencies apply:\n- pLMNIdList must be non-empty.\n- Only sNSSAIList or pLMNIdList can have more than one element.\n- If sNSSAIList is empty, PLMNId must be unique among ResourcePartitionMember MOs.\n- If sNSSAIList is non-empty, the combination of PLMNId and SliceSelectionAssistInfo must be unique among ResourcePartitionMember MOs.\n- If pLMNIdList and sNSSAIList are non-empty, the EndpointResource.LocalSctpEndpoint::interfaceUsed must not be X2.\n- If pLMNIdList is non-empty and sNSSAIList is empty, the EndpointResource.LocalSctpEndpoint::interfaceUsed must not be NG or XN.\n- If pLMNIdList and sNSSAIList are non-empty, and the EndpointResource contains at least one LocalSctpEndpoint instance, PLMNId must be unique among ResourcePartitionMember MOs.";
      erienmyext:enm-type MOREF;
      type string;
    }
    list pLMNIdList {
      min-elements 0;
      max-elements 12;
      key auto-generated-struct-key;
      leaf auto-generated-struct-key {
        type uint16;
        description "This leaf has been injected to allow for struct instances in a sequence to be ordered.";
        mandatory true;
      }
      description "List of PLMN identifier.";
      erienmyext:enm-type STRUCT;
      uses erienmnrmgnbcucp:struct-PLMNId;
    } // end 'list pLMNIdList'
  } // end 'grouping moc-ResourcePartitionMember'
  grouping moc-AnrFunction-keys {
    description "Key(s) for MOC AnrFunction";
    leaf id {
      erienmyext:no-notification;
      description "The value component of the RDN.";
      mandatory true;
      yexte:ecim-name anrFunctionId;
      type string;
    }
  } // end 'grouping moc-AnrFunction-keys'
  grouping moc-AnrFunction {
    description "Parameters and constraints for ANR functions.\n\nThe RDN of this MO must always be AnrFunction=1.";
    leaf removeNrelTime {
      description "Maximum time that unused NR cell relation remain in RBS.\nValue 1000 means no automatic removal is performed.";
      type erienmnrmgnbcucp:ddt-GNBCUCP_AnrFunction_removeNrelTime;
      default 7;
    }
  } // end 'grouping moc-AnrFunction'
  grouping moc-EUtranFrequency-keys {
    description "Key(s) for MOC EUtranFrequency";
    leaf id {
      erienmyext:no-notification;
      description "The value component of the RDN.";
      mandatory true;
      yexte:ecim-name eUtranFrequencyId;
      type string;
    }
  } // end 'grouping moc-EUtranFrequency-keys'
  grouping moc-EUtranFrequency {
    description "Container for information of a specific EUTRAN frequency.\n\nThe RDNs of these MOs are EUtranFrequency=<number>, for example EUtranFrequency=2586.\nRDN must match attribute arfcnValueEUtranDl.";
    leaf userLabel {
      description "Label for free use.";
      type erienmnrmgnbcucp:ddt-UserLabel;
    }
    leaf-list reservedBy {
      min-elements 0;
      config false;
      description "Contains a list of MO instances that reserve this MO instance.";
      notife:notifiable-state-data true;
      erienmyext:enm-type MOREF;
      type string;
    }
    leaf-list freqBandList {
      min-elements 1;
      max-elements 9;
      config false;
      description "List of frequency bands that the frequency belongs to.\nThe primary frequency band that the frequency belongs to, according to its defined EARFCN, is the first element in the list.";
      notife:notifiable-state-data true;
      type erienmnrmgnbcucp:ddt-GNBCUCP_EUtranFrequency_freqBandList;
    }
    leaf arfcnValueEUtranDl {
      yexte:restricted;
      description "ARFCN applicable for a downlink E-UTRA carrier frequency.\nFor TDD this also indicates the ARFCN for uplink.\nValues that can be used depend on national operator-specific frequency allocation and supported frequency bands of the equipment in the eNodeB.\nMust match the eUtranFrequencyId.";
      mandatory true;
      yexte:dependencies "Must match RDN of MO, EUtranFrequency=<arfcnValueEUtranDl>.\nFor example, EUtranFrequency=2586.";
      type erienmnrmgnbcucp:ddt-GNBCUCP_EUtranFrequency_arfcnValueEUtranDl;
    }
    leaf-list excludeAdditionalFreqBandList {
      min-elements 0;
      max-elements 8;
      description "A list of frequency bands to be excluded from the list in the freqBandList attribute.\nThe list must not include the frequency band indicated by the EARFCN value of the frequency (primary frequency band).\nThese frequency bands are excluded from the list of broadcast additional frequency bands in SystemInformationBlockType5 in case the feature Multiple Frequency Band Indicators is enabled in the cell.";
      yexte:takes-effect "New connection";
      type erienmnrmgnbcucp:ddt-GNBCUCP_EUtranFrequency_excludeAdditionalFreqBandList;
    }
  } // end 'grouping moc-EUtranFrequency'
  augment /erienmnrmcomtop:ManagedElement/erienmnrmgnbcucp:GNBCUCPFunction/erienmnrmgnbcucp:NRNetwork {
    list NRFrequency {
      key id;
      max-elements 64;
      description "NRFrequency and related measurement parameters.\n\nNRFrequencies on the Global Synchronization Channel Raster present a value in attribute gscn.\n\nThe RDN of this MO is NRFrequency=arfcnValueNRDl-smtcScs-smtcPeriodicity-smtcOffset-smtcDuration.\nExample: \"NRFrequency=630000-30-20-0-1\".";
      erienmyext:enm-type MOC;
      uses moc-NRFrequency-keys;
      container attributes {
        description "Attributes for NRFrequency";
        uses moc-NRFrequency;
      } // end 'container attributes'
    } // end 'list NRFrequency'
  }
  augment /erienmnrmcomtop:ManagedElement/erienmnrmgnbcucp:GNBCUCPFunction/erienmnrmgnbcucp:NRCellCU {
    list UeMeasControl {
      key id;
      max-elements 1;
      description "Manageable characteristics of a cell for UE measurements.\n\nThe RDN of this MO is UeMeasControl=1.";
      status deprecated {
        yexte:status-information "Since 20.Q4. Planned to be removed.";
      }
      yexte:is-system-created;
      erienmyext:enm-type MOC;
      uses moc-UeMeasControl-keys;
      container attributes {
        description "Attributes for UeMeasControl";
        uses moc-UeMeasControl;
      } // end 'container attributes'
    } // end 'list UeMeasControl'
  }
  augment /erienmnrmcomtop:ManagedElement/erienmnrmgnbcucp:GNBCUCPFunction/erienmnrmgnbcucp:NRCellCU {
    list NRFreqRelation {
      key id;
      max-elements 16;
      description "Mobility relation between NR cell and an NR frequency.\n\nMust use an NRFrequency on the Global Synchronization Channel Raster (indicated in NRFrequency::gscn) for Standalone operation.\nFrequency relation not on the GSCN are not included in SIB4, nor used for PCell mobility.";
      erienmyext:enm-type MOC;
      uses moc-NRFreqRelation-keys;
      container attributes {
        description "Attributes for NRFreqRelation";
        uses moc-NRFreqRelation;
      } // end 'container attributes'
    } // end 'list NRFreqRelation'
  }
  augment /erienmnrmcomtop:ManagedElement/erienmnrmgnbcucp:GNBCUCPFunction/erienmnrmgnbcucp:UeGroupSelection {
    list PrefUeGroupSelectionProfile {
      key id;
      max-elements 7;
      description "A set of preference UE group selection criteria used to define a subset of all UEs.";
      status current {
        yexte:preliminary;
      }
      erienmyext:enm-type MOC;
      uses moc-PrefUeGroupSelectionProfile-keys;
      container attributes {
        description "Attributes for PrefUeGroupSelectionProfile";
        uses moc-PrefUeGroupSelectionProfile;
      } // end 'container attributes'
    } // end 'list PrefUeGroupSelectionProfile'
  }
  augment /erienmnrmcomtop:ManagedElement/erienmnrmgnbcucp:GNBCUCPFunction {
    list Mcpc {
      key id;
      max-elements 1;
      description "Configuration of Mobility Control at Poor Coverage (MCPC) and container for MCPC profiles.\n\nThe RDN of this MO must always be Mcpc=1.";
      erienmyext:enm-type MOC;
      uses moc-Mcpc-keys;
    } // end 'list Mcpc'
  }
  augment /erienmnrmcomtop:ManagedElement/erienmnrmgnbcucp:GNBCUCPFunction/erienmnrmgnbcucp:NRCellCU {
    list NRCellRelation {
      key id;
      max-elements 512;
      description "Handover relationship between NR cell and a neighboring NR cell.";
      erienmyext:enm-type MOC;
      uses moc-NRCellRelation-keys;
      container attributes {
        description "Attributes for NRCellRelation";
        uses moc-NRCellRelation;
      } // end 'container attributes'
    } // end 'list NRCellRelation'
  }
  augment /erienmnrmcomtop:ManagedElement/erienmnrmgnbcucp:GNBCUCPFunction/erienmnrmgnbcucp:UeGroupSelection {
    list UeGroupSelectionProfile {
      key id;
      max-elements 15;
      description "A set of UE group selection criteria used to define a subset of all UEs.";
      status current {
        yexte:preliminary;
      }
      erienmyext:enm-type MOC;
      uses moc-UeGroupSelectionProfile-keys;
      container attributes {
        description "Attributes for UeGroupSelectionProfile";
        uses moc-UeGroupSelectionProfile;
      } // end 'container attributes'
    } // end 'list UeGroupSelectionProfile'
  }
  augment /erienmnrmcomtop:ManagedElement/erienmnrmgnbcucp:GNBCUCPFunction/erienmnrmgnbcucp:NRCellCU {
    list AdditionalPLMNInfo {
      key id;
      max-elements 11;
      description "PLMN-related Information that can be additionally served by NR cell.\n\nCreated by system when F1 interface is set up or configuration is updated by GNBDUFunction.\nDeleted by system when configuration is updated by GNBDUFunction.\n\nThe RDNs of these MOs are AdditionalPLMNInfo=1 to AdditionalPLMNInfo=11.";
      yexte:is-system-created;
      erienmyext:enm-type MOC;
      uses moc-AdditionalPLMNInfo-keys;
      container attributes {
        description "Attributes for AdditionalPLMNInfo";
        uses moc-AdditionalPLMNInfo;
      } // end 'container attributes'
    } // end 'list AdditionalPLMNInfo'
  }
  augment /erienmnrmcomtop:ManagedElement/erienmnrmgnbcucp:GNBCUCPFunction {
    list EmCall {
      key id;
      max-elements 12;
      description "Emergency call configuration for NRCellCU MOs.";
      erienmyext:enm-type MOC;
      uses moc-EmCall-keys;
      container attributes {
        description "Attributes for EmCall";
        uses moc-EmCall;
      } // end 'container attributes'
    } // end 'list EmCall'
  }
  augment /erienmnrmcomtop:ManagedElement/erienmnrmgnbcucp:GNBCUCPFunction/erienmnrmgnbcucp:ResourcePartitions {
    list ResourcePartition {
      key id;
      max-elements 36;
      description "Combination of attributes specifying in which resource partition a UE is included.";
      erienmyext:enm-type MOC;
      uses moc-ResourcePartition-keys;
      container attributes {
        description "Attributes for ResourcePartition";
        uses moc-ResourcePartition;
      } // end 'container attributes'
    } // end 'list ResourcePartition'
  }
  augment /erienmnrmcomtop:ManagedElement/erienmnrmgnbcucp:GNBCUCPFunction {
    list EndpointResource {
      key id;
      description "Transport network endpoints for RAN interfaces.\n\nConfiguration is valid for an entity that refers to an instance of this MO.";
      erienmyext:enm-type MOC;
      uses moc-EndpointResource-keys;
      container attributes {
        description "Attributes for EndpointResource";
        uses moc-EndpointResource;
      } // end 'container attributes'
    } // end 'list EndpointResource'
  }
  augment /erienmnrmcomtop:ManagedElement/erienmnrmgnbcucp:GNBCUCPFunction {
    list TermPointToAmf {
      key id;
      max-elements 64;
      description "Models an NG link AMF termination point.";
      erienmyext:enm-type MOC;
      uses moc-TermPointToAmf-keys;
      container attributes {
        description "Attributes for TermPointToAmf";
        uses moc-TermPointToAmf;
      } // end 'container attributes'
    } // end 'list TermPointToAmf'
  }
  augment /erienmnrmcomtop:ManagedElement/erienmnrmgnbcucp:GNBCUCPFunction/erienmnrmgnbcucp:NRNetwork/erienmnrmgnbcucp:ExternalGNBCUCPFunction {
    list TermPointToGNodeB {
      key id;
      max-elements 1;
      description "Local gNodeB termination point of Xn link between gNodeB and neighbor gNodeB.\n\nWhen created by the system, the RDN of this MO is TermPointToGNodeB=auto1.";
      erienmyext:enm-type MOC;
      uses moc-TermPointToGNodeB-keys;
      container attributes {
        description "Attributes for TermPointToGNodeB";
        uses moc-TermPointToGNodeB;
      } // end 'container attributes'
    } // end 'list TermPointToGNodeB'
  }
  augment /erienmnrmcomtop:ManagedElement/erienmnrmgnbcucp:GNBCUCPFunction {
    list CUCPResourcePartitions {
      key id;
      max-elements 1;
      description "Set of resource partitions.";
      status obsolete {
        yexte:status-information "Since 20.Q2. Deprecated: Since 19.Q4. Planned to be removed.";
      }
      erienmyext:enm-type MOC;
      uses moc-CUCPResourcePartitions-keys;
    } // end 'list CUCPResourcePartitions'
  }
  augment /erienmnrmcomtop:ManagedElement/erienmnrmgnbcucp:GNBCUCPFunction/erienmnrmgnbcucp:Mcpc {
    list McpcPSCellProfile {
      key id;
      description "Mobility Control at Poor Coverage (MCPC) for PSCell.\n\nApplies to UEs which use the cell as PSCell. Attributes are used on cell level.\n\nMCPC for PSCell is enabled per NRCellCU MO by setting NRCellCU::mcpcPSCellEnabled attribute.\nIf NRCellCU::mcpcPSCellProfileRef is non-empty, attributes from referred MO instance are used.\nIf NRCellCU::mcpcPSCellProfileRef is empty, attribute default values according to MO class definition are used.\n\nThe option to create McpcPSCellProfile MO under NRCellCU is obsolete since 20.Q4 and that option will be removed.";
      erienmyext:enm-type MOC;
      uses moc-McpcPSCellProfile-keys;
      container attributes {
        description "Attributes for McpcPSCellProfile";
        uses moc-McpcPSCellProfile;
      } // end 'container attributes'
    } // end 'list McpcPSCellProfile'
  }
  augment /erienmnrmcomtop:ManagedElement/erienmnrmgnbcucp:GNBCUCPFunction/erienmnrmgnbcucp:NRCellCU {
    list McpcPSCellProfile {
      key id;
      max-elements 1;
      description "Mobility Control at Poor Coverage (MCPC) for PSCell.\n\nApplies to UEs which use the cell as PSCell. Attributes are used on cell level.\n\nMCPC for PSCell is enabled per NRCellCU MO by setting NRCellCU::mcpcPSCellEnabled attribute.\nIf NRCellCU::mcpcPSCellProfileRef is non-empty, attributes from referred MO instance are used.\nIf NRCellCU::mcpcPSCellProfileRef is empty, attribute default values according to MO class definition are used.\n\nThe option to create McpcPSCellProfile MO under NRCellCU is obsolete since 20.Q4 and that option will be removed.";
      erienmyext:enm-type MOC;
      uses moc-McpcPSCellProfile-keys;
      container attributes {
        description "Attributes for McpcPSCellProfile";
        uses moc-McpcPSCellProfile;
      } // end 'container attributes'
    } // end 'list McpcPSCellProfile'
  }
  augment /erienmnrmcomtop:ManagedElement/erienmnrmgnbcucp:GNBCUCPFunction {
    list QciProfileEndcConfigExt {
      key id;
      max-elements 1;
      description "Managing QoS-related parameters for Data Radio Bearers in EN-DC.\n\nExtension of the configuration in MO class QciProfileEndcConfig.\n\nThe RDN of this MO is QciProfileEndcConfigExt=1.";
      yexte:is-system-created;
      erienmyext:enm-type MOC;
      uses moc-QciProfileEndcConfigExt-keys;
      container attributes {
        description "Attributes for QciProfileEndcConfigExt";
        uses moc-QciProfileEndcConfigExt;
      } // end 'container attributes'
    } // end 'list QciProfileEndcConfigExt'
  }
  augment /erienmnrmcomtop:ManagedElement/erienmnrmgnbcucp:GNBCUCPFunction/erienmnrmgnbcucp:PmUeMeas {
    list PmUeIntraFreqCellProfile {
      key id;
      max-elements 10;
      description "Profile for PM intra-frequency UE measurements.\n\nIf NRCellCU::pmUeIntraFreqCellProfileRef is non-empty, attributes from referred MO instance are used.\nIf NRCellCU::pmUeIntraFreqCellProfileRef is empty, attribute default values according to MO class definition are used.";
      erienmyext:enm-type MOC;
      uses moc-PmUeIntraFreqCellProfile-keys;
      container attributes {
        description "Attributes for PmUeIntraFreqCellProfile";
        uses moc-PmUeIntraFreqCellProfile;
      } // end 'container attributes'
    } // end 'list PmUeIntraFreqCellProfile'
  }
  augment /erienmnrmcomtop:ManagedElement/erienmnrmgnbcucp:GNBCUCPFunction/erienmnrmgnbcucp:Mcpc {
    list McpcPCellNrFreqRelProfile {
      key id;
      description "Mobility Control at Poor Coverage (MCPC) for PCell.\n\nApplies to UEs which use the cell as PCell. Attributes are used on NR frequency relation level.\n\nMCPC for PCell is enabled per NRCellCU MO by setting NRCellCU::mcpcPCellEnabled attribute.\nIf NRFreqRelation::mcpcPCellNrFreqRelProfileRef is non-empty, attributes from referred MO instance are used.\nIf NRFreqRelation::mcpcPCellNrFreqRelProfileRef is empty, attribute default values according to MO class definition are used.";
      erienmyext:enm-type MOC;
      uses moc-McpcPCellNrFreqRelProfile-keys;
      container attributes {
        description "Attributes for McpcPCellNrFreqRelProfile";
        uses moc-McpcPCellNrFreqRelProfile;
      } // end 'container attributes'
    } // end 'list McpcPCellNrFreqRelProfile'
  }
  augment /erienmnrmcomtop:ManagedElement/erienmnrmgnbcucp:GNBCUCPFunction {
    list UeGroupSelection {
      key id;
      max-elements 1;
      description "Container class for UeGroupSelectionProfiles and PrefUeGroupSelectionProfiles.\n\nThe RDN of this MO must be UeGroupSelection=1.";
      status current {
        yexte:preliminary;
      }
      erienmyext:enm-type MOC;
      uses moc-UeGroupSelection-keys;
    } // end 'list UeGroupSelection'
  }
  augment /erienmnrmcomtop:ManagedElement/erienmnrmgnbcucp:GNBCUCPFunction {
    list CUCPSliceQosInfo {
      key id;
      max-elements 36;
      description "CUCP Slice to 5QI table mapping information.";
      status obsolete {
        yexte:status-information "Since 20.Q2. Deprecated: Since 19.Q4. Planned to be removed.";
      }
      erienmyext:enm-type MOC;
      uses moc-CUCPSliceQosInfo-keys;
      container attributes {
        description "Attributes for CUCPSliceQosInfo";
        uses moc-CUCPSliceQosInfo;
      } // end 'container attributes'
    } // end 'list CUCPSliceQosInfo'
  }
  augment /erienmnrmcomtop:ManagedElement/erienmnrmgnbcucp:GNBCUCPFunction/erienmnrmgnbcucp:EUtraNetwork {
    list ExternalENodeBFunction {
      key id;
      max-elements 256;
      description "This MO represents an eNodeB.\n\nWhen created by the system, the RDN of this MO is ExternalENodeBFunction=auto<mcc>_<mnc>_<mncLength>_<eNodeBId>.";
      erienmyext:enm-type MOC;
      uses moc-ExternalENodeBFunction-keys;
      container attributes {
        description "Attributes for ExternalENodeBFunction";
        uses moc-ExternalENodeBFunction;
      } // end 'container attributes'
    } // end 'list ExternalENodeBFunction'
  }
  augment /erienmnrmcomtop:ManagedElement/erienmnrmgnbcucp:GNBCUCPFunction/erienmnrmgnbcucp:EUtraNetwork/erienmnrmgnbcucp:ExternalENodeBFunction {
    list ExternalEUtranCell {
      key id;
      max-elements 24;
      description "External E-UTRAN cell.\n\nContains parameters that are specific for this cell.";
      erienmyext:enm-type MOC;
      uses moc-ExternalEUtranCell-keys;
      container attributes {
        description "Attributes for ExternalEUtranCell";
        uses moc-ExternalEUtranCell;
      } // end 'container attributes'
    } // end 'list ExternalEUtranCell'
  }
  augment /erienmnrmcomtop:ManagedElement/erienmnrmgnbcucp:GNBCUCPFunction/erienmnrmgnbcucp:NRNetwork/erienmnrmgnbcucp:ExternalGNBCUCPFunction/erienmnrmgnbcucp:ExternalNRCellCU {
    list ExternalBroadcastPLMNInfo {
      key id;
      max-elements 12;
      description "PLMN-related information that is served by external NR cell.\n\nCreated automatically when Xn interface is set up or configuration is updated by external gNodeB.\nDeleted automatically when configuration is updated by external gNodeB.\n\nCan also be created and deleted manually.\n\nThe RDNs of these MOs are ExternalBroadcastPLMNInfo=1 to ExternalBroadcastPLMNInfo=12 when created automatically.\nRDN value follows the order received over Xn.\n\nPrecondition: MO can be created and deleted manually, only if TermPointToGNodeB has administrativeState LOCKED.";
      erienmyext:enm-type MOC;
      uses moc-ExternalBroadcastPLMNInfo-keys;
      container attributes {
        description "Attributes for ExternalBroadcastPLMNInfo";
        uses moc-ExternalBroadcastPLMNInfo;
      } // end 'container attributes'
    } // end 'list ExternalBroadcastPLMNInfo'
  }
  augment /erienmnrmcomtop:ManagedElement/erienmnrmgnbcucp:GNBCUCPFunction/erienmnrmgnbcucp:EndpointResource {
    list LocalIpEndpoint {
      key id;
      description "Local transport network endpoint for user plane interface.\n\nE1 control plane uses TCP, hence this interface is also configured by this class.";
      erienmyext:enm-type MOC;
      uses moc-LocalIpEndpoint-keys;
      container attributes {
        description "Attributes for LocalIpEndpoint";
        uses moc-LocalIpEndpoint;
      } // end 'container attributes'
    } // end 'list LocalIpEndpoint'
  }
  augment /erienmnrmcomtop:ManagedElement/erienmnrmgnbcucp:GNBCUCPFunction/erienmnrmgnbcucp:NRNetwork/erienmnrmgnbcucp:ExternalGNBCUCPFunction/erienmnrmgnbcucp:ExternalNRCellCU {
    list ExternalAdditionalPLMNInfo {
      key id;
      max-elements 11;
      description "PLMN-related Information that is additionally served by external NR cell.\n\nCreated by system when Xn interface is set up or configuration is updated by external gNodeB.\nDeleted by system when TermPointToGNodeB::operationalState is DISABLED or configuration is updated by external gNodeB.\n\nThe RDNs of these MOs are ExternalAdditionalPLMNInfo=1 to ExternalAdditionalPLMNInfo=11.";
      status obsolete {
        yexte:status-information "Since 20.Q3. Planned to be removed.";
      }
      yexte:is-system-created;
      erienmyext:enm-type MOC;
      uses moc-ExternalAdditionalPLMNInfo-keys;
      container attributes {
        description "Attributes for ExternalAdditionalPLMNInfo";
        uses moc-ExternalAdditionalPLMNInfo;
      } // end 'container attributes'
    } // end 'list ExternalAdditionalPLMNInfo'
  }
  augment /erienmnrmcomtop:ManagedElement/erienmnrmgnbcucp:GNBCUCPFunction/erienmnrmgnbcucp:EUtraNetwork/erienmnrmgnbcucp:ExternalENodeBFunction {
    list TermPointToENodeB {
      key id;
      max-elements 1;
      description "Models the local ENodeB termination point of an X2 link between the GNodeB and an ENodeB.";
      erienmyext:enm-type MOC;
      uses moc-TermPointToENodeB-keys;
      container attributes {
        description "Attributes for TermPointToENodeB";
        uses moc-TermPointToENodeB;
      } // end 'container attributes'
    } // end 'list TermPointToENodeB'
  }
  augment /erienmnrmcomtop:ManagedElement/erienmnrmgnbcucp:GNBCUCPFunction/erienmnrmgnbcucp:NRNetwork/erienmnrmgnbcucp:ExternalGNBCUCPFunction {
    list ExternalNRCellCU {
      key id;
      max-elements 256;
      description "Represents an external NRCellCU.\n\nWhen created by the system, the RDN of this MO is ExternalNRCellCU=auto<NCI>, where NCI = <gNBId>*2^(36-<gNBIdLength>) + <cellLocalId>.";
      erienmyext:enm-type MOC;
      uses moc-ExternalNRCellCU-keys;
      container attributes {
        description "Attributes for ExternalNRCellCU";
        uses moc-ExternalNRCellCU;
      } // end 'container attributes'
    } // end 'list ExternalNRCellCU'
  }
  augment /erienmnrmcomtop:ManagedElement/erienmnrmgnbcucp:GNBCUCPFunction/erienmnrmgnbcucp:AnrFunction {
    list AnrFunctionNR {
      key id;
      max-elements 1;
      description "NR Automated Neighbor Relation (ANR) functions.\n\nThe RDN of this MO must always be AnrFunctionNR=1.";
      erienmyext:enm-type MOC;
      uses moc-AnrFunctionNR-keys;
      container attributes {
        description "Attributes for AnrFunctionNR";
        uses moc-AnrFunctionNR;
      } // end 'container attributes'
    } // end 'list AnrFunctionNR'
  }
  augment /erienmnrmcomtop:ManagedElement/erienmnrmgnbcucp:GNBCUCPFunction {
    list EUtraNetwork {
      key id;
      max-elements 1;
      description "Container for MOs related to E-UTRA networks.\n\nWhen created by the system, the RDN of this MO is EUtraNetwork=1.";
      erienmyext:enm-type MOC;
      uses moc-EUtraNetwork-keys;
      container attributes {
        description "Attributes for EUtraNetwork";
        uses moc-EUtraNetwork;
      } // end 'container attributes'
    } // end 'list EUtraNetwork'
  }
  augment /erienmnrmcomtop:ManagedElement/erienmnrmgnbcucp:GNBCUCPFunction/erienmnrmgnbcucp:NRCellCU {
    list EUtranCellRelation {
      key id;
      max-elements 128;
      description "Handover relationship between NR cell and a neighboring E-UTRAN cell.";
      erienmyext:enm-type MOC;
      uses moc-EUtranCellRelation-keys;
      container attributes {
        description "Attributes for EUtranCellRelation";
        uses moc-EUtranCellRelation;
      } // end 'container attributes'
    } // end 'list EUtranCellRelation'
  }
  augment /erienmnrmcomtop:ManagedElement/erienmnrmgnbcucp:GNBCUCPFunction {
    list NRCellCU {
      key id;
      description "Represents NR cell in gNodeB-CU.\n\nManages inter-cell mobility and neighbor relations through ANR.\nEither created by system on receiving configuration message over F1 or manually created by operator.\n\nWhen created by the system, the RDN of this MO is NRCellCU=<NCI>, where NCI = <gNBId>*2^(36-<gNBIdLength>) + <cellLocalId>.\n\nCan only be deleted when the NRCellDU with matching cellLocalId does not exist or has administrativeState LOCKED.";
      erienmyext:enm-type MOC;
      uses moc-NRCellCU-keys;
      container attributes {
        description "Attributes for NRCellCU";
        uses moc-NRCellCU;
      } // end 'container attributes'
    } // end 'list NRCellCU'
  }
  augment /erienmnrmcomtop:ManagedElement/erienmnrmgnbcucp:GNBCUCPFunction/erienmnrmgnbcucp:Mcpc {
    list McpcPCellProfile {
      key id;
      description "Mobility Control at Poor Coverage (MCPC) for PCell.\n\nApplies to UEs which use the cell as PCell. Attributes are used on cell level.\n\nMCPC for PCell is enabled per NRCellCU MO by setting NRCellCU::mcpcPCellEnabled attribute.\nIf NRCellCU::mcpcPCellProfileRef is non-empty, attributes from referred MO instance are used.\nIf NRCellCU::mcpcPCellProfileRef is empty, attribute default values according to MO class definition are used.";
      erienmyext:enm-type MOC;
      uses moc-McpcPCellProfile-keys;
      container attributes {
        description "Attributes for McpcPCellProfile";
        uses moc-McpcPCellProfile;
      } // end 'container attributes'
    } // end 'list McpcPCellProfile'
  }
  augment /erienmnrmcomtop:ManagedElement/erienmnrmgnbcucp:GNBCUCPFunction/erienmnrmgnbcucp:NRCellCU {
    list EUtranFreqRelation {
      key id;
      max-elements 16;
      description "Mobility relation between NR cell and an E-UTRAN frequency.";
      erienmyext:enm-type MOC;
      uses moc-EUtranFreqRelation-keys;
      container attributes {
        description "Attributes for EUtranFreqRelation";
        uses moc-EUtranFreqRelation;
      } // end 'container attributes'
    } // end 'list EUtranFreqRelation'
  }
  augment /erienmnrmcomtop:ManagedElement/erienmnrmgnbcucp:GNBCUCPFunction/erienmnrmgnbcucp:IntraFreqMC {
    list IntraFreqMCCellProfile {
      key id;
      description "Intra-frequency mobility control cell configuration profile.\n\nIf NRCellCU::intraFreqMCCellProfileRef is non-empty, attributes from referred MO instance are used.\nIf NRCellCU::intraFreqMCCellProfileRef is empty, attribute default values according to MO class definition are used.";
      erienmyext:enm-type MOC;
      uses moc-IntraFreqMCCellProfile-keys;
      container attributes {
        description "Attributes for IntraFreqMCCellProfile";
        uses moc-IntraFreqMCCellProfile;
      } // end 'container attributes'
    } // end 'list IntraFreqMCCellProfile'
  }
  augment /erienmnrmcomtop:ManagedElement/erienmnrmgnbcucp:GNBCUCPFunction {
    list ResourcePartitions {
      key id;
      max-elements 1;
      description "Set of resource partitions.";
      erienmyext:enm-type MOC;
      uses moc-ResourcePartitions-keys;
    } // end 'list ResourcePartitions'
  }
  augment /erienmnrmcomtop:ManagedElement/erienmnrmgnbcucp:GNBCUCPFunction/erienmnrmgnbcucp:NRCellCU/erienmnrmgnbcucp:UeMeasControl {
    list ReportConfigA3 {
      key id;
      max-elements 1;
      description "Report configuration for UE A3 measurement.\n\nThe RDN of this MO is ReportConfigA3=1.";
      status deprecated {
        yexte:status-information "Since 20.Q4. Planned to be removed.";
      }
      yexte:is-system-created;
      erienmyext:enm-type MOC;
      uses moc-ReportConfigA3-keys;
      container attributes {
        description "Attributes for ReportConfigA3";
        uses moc-ReportConfigA3;
      } // end 'container attributes'
    } // end 'list ReportConfigA3'
  }
  augment /erienmnrmcomtop:ManagedElement/erienmnrmgnbcucp:GNBCUCPFunction/erienmnrmgnbcucp:NRNetwork {
    list ExternalGNBCUCPFunction {
      key id;
      max-elements 512;
      description "Represents external gNodeB-CU-CP function.\n\nWhen created by the system, the RDN of this MO is ExternalGNBCUCPFunction=auto<mcc>_<mnc>_<mncLength>_<gNodeBId>.";
      erienmyext:enm-type MOC;
      uses moc-ExternalGNBCUCPFunction-keys;
      container attributes {
        description "Attributes for ExternalGNBCUCPFunction";
        uses moc-ExternalGNBCUCPFunction;
      } // end 'container attributes'
    } // end 'list ExternalGNBCUCPFunction'
  }
  augment /erienmnrmcomtop:ManagedElement/erienmnrmgnbcucp:GNBCUCPFunction {
    list PmUeMeas {
      key id;
      max-elements 1;
      description "Container class for PM UE measurement profile classes.\n\nThe RDN of this MO must always be PmUeMeas=1.";
      erienmyext:enm-type MOC;
      uses moc-PmUeMeas-keys;
    } // end 'list PmUeMeas'
  }
  augment /erienmnrmcomtop:ManagedElement/erienmnrmgnbcucp:GNBCUCPFunction/erienmnrmgnbcucp:EndpointResource {
    list LocalSctpEndpoint {
      key id;
      description "Local transport network endpoint for control plane interface.\n\nE1 control plane uses TCP, hence this interface is configured in MO class LocalIpEndpoint.";
      erienmyext:enm-type MOC;
      uses moc-LocalSctpEndpoint-keys;
      container attributes {
        description "Attributes for LocalSctpEndpoint";
        uses moc-LocalSctpEndpoint;
      } // end 'container attributes'
    } // end 'list LocalSctpEndpoint'
  }
  augment /erienmnrmcomtop:ManagedElement/erienmnrmgnbcucp:GNBCUCPFunction {
    list Mcfb {
      key id;
      max-elements 1;
      description "Container class for Mobility Control Fallback attributes and profile classes.\n\nThe RDN of this MO is Mcfb=1.";
      erienmyext:enm-type MOC;
      uses moc-Mcfb-keys;
      container attributes {
        description "Attributes for Mcfb";
        uses moc-Mcfb;
      } // end 'container attributes'
    } // end 'list Mcfb'
  }
  augment /erienmnrmcomtop:ManagedElement/erienmnrmgnbcucp:GNBCUCPFunction {
    list TermPointToGNBDU {
      key id;
      description "Models an F1-C link to a gNodeB-DU.\n\nCreated by the system when F1-C link is set up.\nDeleted by the system at node restart.\n\nThe RDN of this MO is TermPointToGNBDU=[gNBDUId].";
      yexte:is-system-created;
      erienmyext:enm-type MOC;
      uses moc-TermPointToGNBDU-keys;
      container attributes {
        description "Attributes for TermPointToGNBDU";
        uses moc-TermPointToGNBDU;
      } // end 'container attributes'
    } // end 'list TermPointToGNBDU'
  }
  augment /erienmnrmcomtop:ManagedElement/erienmnrmgnbcucp:GNBCUCPFunction/erienmnrmgnbcucp:Mcpc {
    list McpcPCellEUtranFreqRelProfile {
      key id;
      description "Mobility Control at Poor Coverage (MCPC) for PCell.\n\nApplies to UEs that use the cell as PCell. Attributes are used on E-UTRAN frequency relation level.\n\nMCPC for PCell is enabled for each NRCellCU MO by setting NRCellCU::mcpcPCellEnabled attribute.\nIf EUtranFreqRelation::mcpcPCellEUtranFreqRelProfileRef is non-empty, attributes from referred MO instance are used.\nIf EUtranFreqRelation::mcpcPCellEUtranFreqRelProfileRef is empty, attribute default values are used according to MO class definition.";
      erienmyext:enm-type MOC;
      uses moc-McpcPCellEUtranFreqRelProfile-keys;
      container attributes {
        description "Attributes for McpcPCellEUtranFreqRelProfile";
        uses moc-McpcPCellEUtranFreqRelProfile;
      } // end 'container attributes'
    } // end 'list McpcPCellEUtranFreqRelProfile'
  }
  augment /erienmnrmcomtop:ManagedElement/erienmnrmgnbcucp:GNBCUCPFunction/erienmnrmgnbcucp:NRCellCU/erienmnrmgnbcucp:UeMeasControl {
    list ReportConfigA2 {
      key id;
      max-elements 1;
      description "Report configuration for UE A2 measurement event.\n\nFunction defined by ReportConfigA2 MO is only applied if attribute NRCellCU::mcpcPCellEnabled is set to false.\nIf attribute mcpcPCellEnabled is set to true function defined by ReportConfigA2 MO is turned off.\n\nThe RDN of this MO is ReportConfigA2=1.";
      status deprecated {
        yexte:status-information "Since 20.Q4. Planned to be removed.";
      }
      yexte:is-system-created;
      erienmyext:enm-type MOC;
      uses moc-ReportConfigA2-keys;
      container attributes {
        description "Attributes for ReportConfigA2";
        uses moc-ReportConfigA2;
      } // end 'container attributes'
    } // end 'list ReportConfigA2'
  }
  augment /erienmnrmcomtop:ManagedElement/erienmnrmgnbcucp:GNBCUCPFunction {
    list NRNetwork {
      key id;
      max-elements 1;
      description "Container for MOs related to NR networks.\n\nWhen created by the system, the RDN of this MO is NRNetwork=1.";
      erienmyext:enm-type MOC;
      uses moc-NRNetwork-keys;
    } // end 'list NRNetwork'
  }
  augment /erienmnrmcomtop:ManagedElement/erienmnrmgnbcucp:GNBCUCPFunction {
    list IntraFreqMC {
      key id;
      max-elements 1;
      description "This is a container for Intra-frequency mobility control profiles.\n\nThe RDN of this MO must always be IntraFreqMC=1.";
      erienmyext:enm-type MOC;
      uses moc-IntraFreqMC-keys;
      container attributes {
        description "Attributes for IntraFreqMC";
        uses moc-IntraFreqMC;
      } // end 'container attributes'
    } // end 'list IntraFreqMC'
  }
  augment /erienmnrmcomtop:ManagedElement/erienmnrmgnbcucp:GNBCUCPFunction {
    list SecurityHandling {
      key id;
      max-elements 1;
      description "Manageable characteristics of security handling except during X2 handover and S1 handover.\n\nThe RDN of this MO is SecurityHandling=1.";
      yexte:is-system-created;
      erienmyext:enm-type MOC;
      uses moc-SecurityHandling-keys;
      container attributes {
        description "Attributes for SecurityHandling";
        uses moc-SecurityHandling;
      } // end 'container attributes'
    } // end 'list SecurityHandling'
  }
  augment /erienmnrmcomtop:ManagedElement/erienmnrmgnbcucp:GNBCUCPFunction {
    list CUCP5qiTable {
      key id;
      max-elements 36;
      description "Mapping from 5G QoS Identifier to parameters that have impact on QoS.\n\nThe table must contain at least one CUCP5qi with resource type NON_GBR.";
      erienmyext:enm-type MOC;
      uses moc-CUCP5qiTable-keys;
      container attributes {
        description "Attributes for CUCP5qiTable";
        uses moc-CUCP5qiTable;
      } // end 'container attributes'
    } // end 'list CUCP5qiTable'
  }
  augment /erienmnrmcomtop:ManagedElement/erienmnrmgnbcucp:GNBCUCPFunction/erienmnrmgnbcucp:Mcfb {
    list McfbCellProfile {
      key id;
      description "Profile of Mobility Control Fallback for cell.\n\nApplies to UEs which use the cell as PCell. Attributes are used on cell level.";
      erienmyext:enm-type MOC;
      uses moc-McfbCellProfile-keys;
      container attributes {
        description "Attributes for McfbCellProfile";
        uses moc-McfbCellProfile;
      } // end 'container attributes'
    } // end 'list McfbCellProfile'
  }
  augment /erienmnrmcomtop:ManagedElement/erienmnrmgnbcucp:GNBCUCPFunction/erienmnrmgnbcucp:CUCPResourcePartitions {
    list CUCPResourcePartition {
      key id;
      max-elements 1;
      description "Combination of attributes specifying in which resource partition a UE is included.";
      status obsolete {
        yexte:status-information "Since 20.Q2. Deprecated: Since 19.Q4. Planned to be removed.";
      }
      erienmyext:enm-type MOC;
      uses moc-CUCPResourcePartition-keys;
      container attributes {
        description "Attributes for CUCPResourcePartition";
        uses moc-CUCPResourcePartition;
      } // end 'container attributes'
    } // end 'list CUCPResourcePartition'
  }
  augment /erienmnrmcomtop:ManagedElement/erienmnrmgnbcucp:GNBCUCPFunction/erienmnrmgnbcucp:CUCP5qiTable {
    list CUCP5qi {
      key id;
      max-elements 29;
      description "QoS configuration corresponding to 3GPP-defined and operator-defined 5QI profiles.\n\nMaximum number of operator-defined profiles is 9.\n\nEach profile can be present once in each table.";
      erienmyext:enm-type MOC;
      uses moc-CUCP5qi-keys;
      container attributes {
        description "Attributes for CUCP5qi";
        uses moc-CUCP5qi;
      } // end 'container attributes'
    } // end 'list CUCP5qi'
  }
  augment /erienmnrmcomtop:ManagedElement/erienmnrmgnbcucp:GNBCUCPFunction {
    list UeMC {
      key id;
      max-elements 1;
      description "Container class for UE Mobility Control (UeMC) attributes and UeMC profile classes.\n\nThe RDN of this MO must always be UeMC=1";
      erienmyext:enm-type MOC;
      uses moc-UeMC-keys;
      container attributes {
        description "Attributes for UeMC";
        uses moc-UeMC;
      } // end 'container attributes'
    } // end 'list UeMC'
  }
  augment /erienmnrmcomtop:ManagedElement/erienmnrmgnbcucp:GNBCUCPFunction {
    list TermPointToGNBCUUP {
      key id;
      description "Models an E1 link to a gNodeB-CU-UP.\n\nCreated by the system when E1 link is set up.\nDeleted by the system at node restart.\n\nThe RDN of this MO is TermPointToGNBCUUP=[Local Ip Address]_[Remote Ip Address].";
      yexte:is-system-created;
      erienmyext:enm-type MOC;
      uses moc-TermPointToGNBCUUP-keys;
      container attributes {
        description "Attributes for TermPointToGNBCUUP";
        uses moc-TermPointToGNBCUUP;
      } // end 'container attributes'
    } // end 'list TermPointToGNBCUUP'
  }
  augment /erienmnrmcomtop:ManagedElement {
    list GNBCUCPFunction {
      key id;
      description "Represents the logical node gNodeB-CU-CP.";
      erienmyext:enm-type MOC;
      uses moc-GNBCUCPFunction-keys;
      container attributes {
        description "Attributes for GNBCUCPFunction";
        uses moc-GNBCUCPFunction;
      } // end 'container attributes'
    } // end 'list GNBCUCPFunction'
  }
  augment /erienmnrmcomtop:ManagedElement/erienmnrmgnbcucp:GNBCUCPFunction/erienmnrmgnbcucp:UeMC {
    list UeMCCellProfile {
      key id;
      description "UE Mobility Control attributes.\n\nThe attributes are used on cell level.\n\nIf NRCellCU::ueMCCellProfileRef is non-empty, attributes from referred MO instance are used.\nIf NRCellCU::ueMCCellProfileRef is empty, attribute default values according to MO class definition are used.";
      erienmyext:enm-type MOC;
      uses moc-UeMCCellProfile-keys;
      container attributes {
        description "Attributes for UeMCCellProfile";
        uses moc-UeMCCellProfile;
      } // end 'container attributes'
    } // end 'list UeMCCellProfile'
  }
  augment /erienmnrmcomtop:ManagedElement/erienmnrmgnbcucp:GNBCUCPFunction/erienmnrmgnbcucp:ResourcePartitions/erienmnrmgnbcucp:ResourcePartition {
    list ResourcePartitionMember {
      key id;
      max-elements 36;
      description "Set of member information of resource partition.";
      erienmyext:enm-type MOC;
      uses moc-ResourcePartitionMember-keys;
      container attributes {
        description "Attributes for ResourcePartitionMember";
        uses moc-ResourcePartitionMember;
      } // end 'container attributes'
    } // end 'list ResourcePartitionMember'
  }
  augment /erienmnrmcomtop:ManagedElement/erienmnrmgnbcucp:GNBCUCPFunction {
    list AnrFunction {
      key id;
      max-elements 1;
      description "Parameters and constraints for ANR functions.\n\nThe RDN of this MO must always be AnrFunction=1.";
      erienmyext:enm-type MOC;
      uses moc-AnrFunction-keys;
      container attributes {
        description "Attributes for AnrFunction";
        uses moc-AnrFunction;
      } // end 'container attributes'
    } // end 'list AnrFunction'
  }
  augment /erienmnrmcomtop:ManagedElement/erienmnrmgnbcucp:GNBCUCPFunction/erienmnrmgnbcucp:EUtraNetwork {
    list EUtranFrequency {
      key id;
      max-elements 32;
      description "Container for information of a specific EUTRAN frequency.\n\nThe RDNs of these MOs are EUtranFrequency=<number>, for example EUtranFrequency=2586.\nRDN must match attribute arfcnValueEUtranDl.";
      erienmyext:enm-type MOC;
      uses moc-EUtranFrequency-keys;
      container attributes {
        description "Attributes for EUtranFrequency";
        uses moc-EUtranFrequency;
      } // end 'container attributes'
    } // end 'list EUtranFrequency'
  }
}
