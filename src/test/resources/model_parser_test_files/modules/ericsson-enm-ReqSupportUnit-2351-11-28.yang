module ericsson-enm-ReqSupportUnit {
  yang-version 1.1;
  namespace urn:rdns:com:ericsson:ericsson-enm-ReqSupportUnit;
  prefix erienmnrmreqsupportunit;
  yexte:ecim-name ReqSupportUnit;
  revision 2351-11-28 {
    yexte:version 3;
    yexte:release 0;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqEquipment {
    prefix erienmnrmreqequipment;
  }
  typedef enum-ProvidedServices {
    description "Services provided by the support unit.";
    type enumeration {
      enum POWER_SUPPLY {
        description "Supplies power.";
        value 0;
      }
      enum POWER_DISTRIBUTION {
        description "Distributes power.";
        value 1;
      }
      enum FAN {
        description "Provides air flow, typically for cooling purposes.";
        value 2;
      }
      enum EXTERNAL_ALARM_PORTS {
        description "Provides external alarm ports.";
        value 3;
      }
      enum BATTERY_BACKUP {
        description "Provides battery backup.";
        value 4;
      }
    }
  }
  typedef enum-OperState {
    description "Operational states of a resource.";
    type enumeration {
      enum DISABLED {
        description "The resource is  totally inoperable.";
        value 0;
      }
      enum ENABLED {
        description "The resource is partially or fully operable.";
        value 1;
      }
    }
  }
  typedef enum-AdmState {
    description "Administrative state of a resource.";
    type enumeration {
      enum LOCKED {
        description "The resource is administratively prohibited from performing services for its users.";
        value 0;
      }
      enum UNLOCKED {
        description "The resource is administratively permitted to perform services for its users.
\nThis is independent of its inherent operability.";
        value 1;
      }
      enum SHUTTINGDOWN {
        description "Use of the resource is administratively permitted to existing instances of use only.
\nWhile the system remains in the shutting down state the manager may at any time cause the managed object to revert to the locked state.";
        value 2;
      }
    }
  }
  typedef enum-AvailStatus {
    description "The availability status is used to qualify the operational state.
\n It indicates why the operational state has changed its value. ";
    type enumeration {
      enum IN_TEST {
        description "The resource is undergoing a test procedure. 
\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.
\nThe semantics are defined in CCITT Rec. X.735 | ISO/IEC 10164-6. ";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef enum-IndicatorStatus {
    description IndicatorStatus.;
    type enumeration {
      enum NOT_APPLICABLE {
        description "The indicator is not supported.";
        value 0;
      }
      enum NOT_AVAILABLE {
        description "The indicator state is currently not available.";
        value 1;
      }
      enum OFF {
        description "The indicator is off.";
        value 2;
      }
      enum STEADY_ON {
        description "The indicator is on continuously.";
        value 3;
      }
      enum SLOW_BLINK {
        description "The indicator blinks slowly.";
        value 4;
      }
      enum FAST_BLINK {
        description "The indicator blinks quickly.";
        value 6;
      }
      enum DOUBLE_FLASH_AND_STEADY_ON {
        description "The indicator blinks twice and is then on for a short time. This cycle is then repeated.";
        value 7;
      }
      enum DOUBLE_FLASH_AND_OFF {
        description "The indicator blinks twice and is then off for a short time. This cycle is then repeated.";
        value 8;
      }
    }
  }
  typedef ddt-ReqCabinet_ApcProductData_productionDate {
    type string {
      length 5..8;
    }
  }
  typedef ddt-ReqSupportUnit_SuAddressInfo_hostedSupportUnitReference {
    type int32 {
      range 0..8;
    }
  }
  typedef ddt-ReqCabinet_ApcProductData_serialNumber {
    type string {
      length 1..13;
    }
  }
  typedef ddt-ReqCabinet_ApcProductData_productRevision {
    type string {
      length 1..7;
    }
  }
  typedef ddt-ReqFieldReplaceableUnit_SpecialIndicator_indicatorName {
    type string {
      length 0..128;
    }
  }
  typedef ddt-ReqCabinet_ApcProductData_productName {
    type string {
      length 1..32;
    }
  }
  typedef ddt-ReqCabinet_ApcProductData_productNumber {
    type string {
      length 1..24;
    }
  }
  grouping struct-SpecialIndicator {
    description "Special indicator data.";
    leaf indicatorName {
      description "The name of the special indicator.";
      type erienmnrmreqsupportunit:ddt-ReqFieldReplaceableUnit_SpecialIndicator_indicatorName;
      mandatory true;
    }
    leaf indicatorStatus {
      description "The current status of the special Indicator.";
      type erienmnrmreqsupportunit:enum-IndicatorStatus;
      mandatory true;
    }
  } // end 'grouping struct-SpecialIndicator'
  grouping struct-SuAddressInfo {
    description "The address elements of the support unit, one set per host the support unit is connected to. Note that a support unit can be directly connected to one or several hosts by one support unit bus for each host. Alternatively, it can be connected indirectly by another support unit, which in turn is connected to the hosts. If indirectly connected, the support unit is referred to as a \"hosted support unit\".";
    leaf supportUnitBusAddress {
      description "The high level data link control (HDLC) address of the support unit on the support unit bus.";
      type int32;
      mandatory true;
    }
    leaf hostPortNumber {
      description "Port on the host that the support unit is connected to by the support unit bus.";
      type int32;
      mandatory true;
    }
    leaf hostObjectReference {
      description "LDN or FRO ID of the support unit host.";
      type string;
      mandatory true;
    }
    leaf supportUnitHostPortNumber {
      description "Port on the support unit the host is connected to by the support unit bus.";
      type int32;
      mandatory true;
    }
    leaf hostedSupportUnitReference {
      description "Reference to a hosted support unit. The support unit that terminates the support unit bus interface has reference 0. Hosted support units have a reference > 0.";
      type erienmnrmreqsupportunit:ddt-ReqSupportUnit_SuAddressInfo_hostedSupportUnitReference;
      mandatory true;
    }
  } // end 'grouping struct-SuAddressInfo'
  grouping struct-ApcProductData {
    description ".
\n";
    leaf productionDate {
      description "The production date is represented in two ways:
\n
\n- the preferred syntax is four-digits for the year, two digits for the month, and two digits for the day.
\nExample: 19991231
\n
\n- the date is also be represented by two digits for the year, followed by the letter W for week, and two digits for the number of the week.
\nExample: 99W52";
      type erienmnrmreqsupportunit:ddt-ReqCabinet_ApcProductData_productionDate;
      mandatory true;
    }
    leaf serialNumber {
      description "The serial number of the product. ";
      type erienmnrmreqsupportunit:ddt-ReqCabinet_ApcProductData_serialNumber;
      mandatory true;
    }
    leaf productNumber {
      description "The product number of the product.
\n
\nExamples: ABC 101 001, CXC 123 456, 1/BFD 101 999
\n";
      type erienmnrmreqsupportunit:ddt-ReqCabinet_ApcProductData_productNumber;
      mandatory true;
    }
    leaf productName {
      description "The name of the product.";
      type erienmnrmreqsupportunit:ddt-ReqCabinet_ApcProductData_productName;
      mandatory true;
    }
    leaf productRevision {
      description "The revision state of the product.
\n
\nExamples: R1, R1A, R1A02, P7B ";
      type erienmnrmreqsupportunit:ddt-ReqCabinet_ApcProductData_productRevision;
      mandatory true;
    }
  } // end 'grouping struct-ApcProductData'
  grouping moc-SupportUnit-keys {
    description "Key(s) for MOC SupportUnit";
    leaf id {
      erienmyext:no-notification;
      description "The value component of the RDN.";
      mandatory true;
      yexte:ecim-name supportUnitId;
      type string;
    }
  } // end 'grouping moc-SupportUnit-keys'
  grouping moc-SupportUnit {
    description "A unit that provides support to adjacent units, in terms of power, climate and/or external alarms. 
\n
\nRDNs of these MOs are SupportUnit=1, SupportUnit=2 and so on. Autocreated when the support unit is detected by the system.";
    leaf operationalIndicator {
      erienmyext:no-notification;
      config false;
      description "Operational status of the support unit as shown by the operational indicator on the unit.
\n
\nPossible values:
\n• NOT_APPLICABLE = The indicator is not supported.
\n• NOT_AVAILABLE = The indicator state is currently not available.
\n• OFF = No power.
\n• STEADY_ON = Operational, the unit can perform its intended purpose.
\n• SLOW_BLINK = Dependent resource missing, the unit is non-operational.";
      type erienmnrmreqsupportunit:enum-IndicatorStatus;
    }
    leaf administrativeState {
      description "Defines the administrative state.";
      yexte:takes-effect IMMEDIATELY;
      type erienmnrmreqsupportunit:enum-AdmState;
      default UNLOCKED;
    }
    leaf faultIndicator {
      erienmyext:no-notification;
      config false;
      description "Fault status of the support unit as shown by the fault indicator on the unit. 
\n
\nPossible values:
\n• NOT_APPLICABLE = The indicator is not supported.
\n• NOT_AVAILABLE = The indicator state is currently not available.
\n• OFF = No hardware fault.
\n• STEADY_ON = Hardware fault.";
      type erienmnrmreqsupportunit:enum-IndicatorStatus;
    }
    list specialIndicator {
      min-elements 0;
      key auto-generated-struct-key;
      leaf auto-generated-struct-key {
        type uint16;
        description "This leaf has been injected to allow for struct instances in a sequence to be ordered.";
        mandatory true;
      }
      description "Current status of special indicators on the unit.\nThe possible status values and semantics of these vary depending on the name of the indicator.\n\nPossible values:\nFan [<no.>] Fault Indicator\n• OFF = Fans connected and no fault exists in the fan or fan group, or optional fan or fan group not connected.\n• STEADY_ON = A HW fault exists in this fan or fan group.";
      erienmyext:enm-type STRUCT;
      uses erienmnrmreqsupportunit:struct-SpecialIndicator;
    } // end 'list specialIndicator'
    leaf-list reservedBy {
      min-elements 0;
      config false;
      description " Contains a list of MO instances that reserve this MO instance.";
      notife:notifiable-state-data true;
      erienmyext:enm-type MOREF;
      type string;
    }
    container productData {
      description "Product data of the support unit.";
      erienmyext:enm-type STRUCT;
      uses erienmnrmreqsupportunit:struct-ApcProductData;
    } // end 'container productData'
    list suAddressInfo {
      min-elements 0;
      key auto-generated-struct-key;
      leaf auto-generated-struct-key {
        type uint16;
        description "This leaf has been injected to allow for struct instances in a sequence to be ordered.";
        mandatory true;
      }
      description "The address elements of the support unit, one set per host the support unit is connected to. Note that a support unit can be directly connected to one or several hosts by one support unit bus for each host. Alternatively, it can be connected indirectly by another support unit, which in turn is connected to the hosts. If indirectly connected, the support unit is referred to as a \"hosted support unit\".";
      erienmyext:enm-type STRUCT;
      uses erienmnrmreqsupportunit:struct-SuAddressInfo;
    } // end 'list suAddressInfo'
    leaf-list availabilityStatus {
      min-elements 0;
      erienmyext:no-notification;
      config false;
      description "The availability status. It contains details about operationalState.";
      type erienmnrmreqsupportunit:enum-AvailStatus;
    }
    leaf operationalState {
      config false;
      description "Defines the operational state.";
      notife:notifiable-state-data true;
      type erienmnrmreqsupportunit:enum-OperState;
    }
    leaf-list providedServices {
      min-elements 0;
      config false;
      description "Services provided by the support unit.";
      notife:notifiable-state-data true;
      type erienmnrmreqsupportunit:enum-ProvidedServices;
    }
    action deregisterSupportUnit {
      description "Deregisters support unit in support unit hosts. That is, SupportUnit MO is removed from supportUnitRef attribute in corresponding FieldReplaceableUnit MOs. When SupportUnit MO is no longer referred to (reservedBy attribute has become empty), SupportUnit MO is automatically deleted.\nTransaction required: Yes";
    }
  } // end 'grouping moc-SupportUnit'
  augment /erienmnrmcomtop:ManagedElement/erienmnrmreqequipment:Equipment {
    list SupportUnit {
      key id;
      description "A unit that provides support to adjacent units, in terms of power, climate and/or external alarms. 
\n
\nRDNs of these MOs are SupportUnit=1, SupportUnit=2 and so on. Autocreated when the support unit is detected by the system.";
      yexte:is-system-created;
      erienmyext:enm-type MOC;
      uses moc-SupportUnit-keys;
      container attributes {
        description "Attributes for SupportUnit";
        uses moc-SupportUnit;
      } // end 'container attributes'
    } // end 'list SupportUnit'
  }
}
