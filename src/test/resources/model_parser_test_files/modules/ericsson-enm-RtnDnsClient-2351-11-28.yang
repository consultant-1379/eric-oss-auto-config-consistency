module ericsson-enm-RtnDnsClient {
  yang-version 1.1;
  namespace urn:rdns:com:ericsson:ericsson-enm-RtnDnsClient;
  prefix erienmnrmrtndnsclient;
  yexte:ecim-name RtnDnsClient;
  revision 2351-11-28 {
    yexte:version 2;
    yexte:release 11;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RtnL3Router {
    prefix erienmnrmrtnl3router;
  }
  typedef enum-DnsConfigMode {
    description "Method of IP address configuration.";
    type enumeration {
      enum MANUAL {
        description "DNS server address(es) are configured manually.";
        value 0;
      }
      enum AUTOMATIC {
        description "DNS server address(es) are configured automatically.";
        value 1;
      }
    }
  }
  typedef ddt-IpDNSAddress {
    description "The IpDNSAddress type represents an IP address or a DNS domain name.\n\nA unicast IPv4 address is presented in three-digit decimal blocks. It is specified in dotted-quad decimal notation (i.e. three-digit decimal blocks) in accordance with RFC791, The blocks are separated by a dot.\n- The unicast IPV4 address is within range [1-126,128-223].[0-255].[0-255].[0-255], 7-15 characters.\n- The IP address range 127.0.0.0 – 127.255.255.255 is reserved for loopback\n- The IP address range 0– 0.255.255.255 are reserved\n- The IP address range 169.254.1.0 - 169.254.254.255 is used for link-local addresses.\n\nAn IPv6 address is specified by 8 groups of 16 bit hexadecimal values separated by colons as described in RFC 4291. If multiple consecutive groups contain only zeros, the use of “::” indicates one or more groups of 16 bits of zeros, as described in RFC 4291, section 2.2 bullet 2. A link-local address will have prefix fe80::/10. The format of the embedded IPv4/IPv6 addresses is described in RFC 6052.\n- IPv6 minimum length = 3 and maximum length = 39.\n- Valid characters: 0123456789abcdefABCDEF:\n\nA domain name is specified in dot separated alphanumeric notation as described in RFC 1034. The domain name consists of one or more parts, called labels, that are delimited by dots.\n- Domain Name's length: 253 characters\n- Label's length: 63 characters.\n- Valid characters: a-z, A-Z, 0,1,2,3,4,5,6,7,8,9,-\n- The Label’s first character is a letter.\n- Labels shall not start or end with a hyphen.\n- Labels shall not start with a numbers\n- Labels shall end with a number or a letter.";
    type string {
      length 1..253;
    }
  }
  typedef ddt-RtnDnsClient_DnsClient_dscp {
    type uint8 {
      range 0..63;
    }
  }
  typedef ddt-RtnDnsClient_DnsClient_userLabel {
    type string {
      length 1..128;
    }
  }
  typedef ddt-RtnDnsClient_DomainFilter_domain {
    type string;
  }
  typedef ddt-RtnDnsClient_DomainFilter_userLabel {
    type string {
      length 1..128;
    }
  }
  typedef ddt-IpAddress {
    description "Regular expression pattern for IP assigned address, covering both IPv4 and IPv6.
\n
\nThe type is ((IPv4 address)|(IPv6 address)), without leading 0s.
\n
\nIpV4 address = ((22[0-3]|2[01][0-9]|1[013456789][0-9]|12[012345689]|1[0-9][0-9]|[1-9][0-9]|[1-9])\\.(25[0-5]|2[0-4][0-9]|1[0-9][0-9]|[1-9][0-9]|[0-9])\\.(25[0-5]|2[0-4][0-9]|1[0-9][0-9]|[1-9][0-9]|[0-9])\\.(25[0-5]|2[0-4][0-9]|1[0-9][0-9]|[1-9][0-9]|[0-9]))
\n
\nIPv6 address = (\\s*((((([1-9A-Fa-f][0-9A-Fa-f]{0,3}|0):){7}(([1-9A-Fa-f][0-9A-Fa-f]{0,3}|0)|:))|((([1-9A-Fa-f][0-9A-Fa-f]{0,3}|0):){6}(:([1-9A-Fa-f][0-9A-Fa-f]{0,3}|0)|((25[0-5]|2[0-4][0-9]|1[0-9][0-9]|[1-9]?[0-9])(\\.(25[0-5]|2[0-4][0-9]|1[0-9][0-9]|[1-9]?[0-9])){3})|:))|((([1-9A-Fa-f][0-9A-Fa-f]{0,3}|0):){5}(((:([1-9A-Fa-f][0-9A-Fa-f]{0,3}|0)){1,2})|:((25[0-5]|2[0-4][0-9]|1[0-9][0-9]|[1-9]?[0-9])(\\.(25[0-5]|2[0-4][0-9]|1[0-9][0-9]|[1-9]?[0-9])){3})|:))|((([1-9A-Fa-f][0-9A-Fa-f]{0,3}|0):){4}(((:([1-9A-Fa-f][0-9A-Fa-f]{0,3}|0)){1,3})|((:([1-9A-Fa-f][0-9A-Fa-f]{0,3}|0))?:((25[0-5]|2[0-4][0-9]|1[0-9][0-9]|[1-9]?[0-9])(\\.(25[0-5]|2[0-4][0-9]|1[0-9][0-9]|[1-9]?[0-9])){3}))|:))|((([1-9A-Fa-f][0-9A-Fa-f]{0,3}|0):){3}(((:([1-9A-Fa-f][0-9A-Fa-f]{0,3}|0)){1,4})|((:([1-9A-Fa-f][0-9A-Fa-f]{0,3}|0)){0,2}:((25[0-5]|2[0-4][0-9]|1[0-9][0-9]|[1-9]?[0-9])(\\.(25[0-5]|2[0-4][0-9]|1[0-9][0-9]|[1-9]?[0-9])){3}))|:))|((([1-9A-Fa-f][0-9A-Fa-f]{0,3}|0):){2}(((:([1-9A-Fa-f][0-9A-Fa-f]{0,3}|0)){1,5})|((:([1-9A-Fa-f][0-9A-Fa-f]{0,3}|0)){0,3}:((25[0-5]|2[0-4][0-9]|1[0-9][0-9]|[1-9]?[0-9])(\\.(25[0-5]|2[0-4][0-9]|1[0-9][0-9]|[1-9]?[0-9])){3}))|:))|((([1-9A-Fa-f][0-9A-Fa-f]{0,3}|0):){1}(((:([1-9A-Fa-f][0-9A-Fa-f]{0,3}|0)){1,6})|((:([1-9A-Fa-f][0-9A-Fa-f]{0,3}|0)){0,4}:((25[0-5]|2[0-4][0-9]|1[0-9][0-9]|[1-9]?[0-9])(\\.(25[0-5]|2[0-4][0-9]|1[0-9][0-9]|[1-9]?[0-9])){3}))|:))|(:(((:([1-9A-Fa-f][0-9A-Fa-f]{0,3}|0)){1,7})|((:([1-9A-Fa-f][0-9A-Fa-f]{0,3}|0)){0,5}:((25[0-5]|2[0-4][0-9]|1[0-9][0-9]|[1-9]?[0-9])(\\.(25[0-5]|2[0-4][0-9]|1[0-9][0-9]|[1-9]?[0-9])){3}))|:)))(%.+)?\\s*)
\n
\nMatching example is: 192.168.21.3
\nAnother matching example is: 2001:db8:85a3:8d3:1319:8a2e:370:7348";
    type string;
  }
  grouping moc-DnsClient-keys {
    description "Key(s) for MOC DnsClient";
    leaf id {
      erienmyext:no-notification;
      description "The value component of the RDN.";
      mandatory true;
      yexte:ecim-name dnsClientId;
      type string;
    }
  } // end 'grouping moc-DnsClient-keys'
  grouping moc-DnsClient {
    description "Represents DNS client.";
    leaf configurationMode {
      description "Whether DNS server addresses are configured manually or are retrieved automatically using either DHCP, IPv6 autoconfiguration or IKE configuration payload method.\nIf AUTOMATIC, up to three DNS server addresses are retrieved either from security gateway, DHCP server or router.\nRetrieved addresses are listed in usedServerAddresses.";
      yexte:dependencies "If AUTOMATIC, there must be AddressIPv4 MO or AddressIPv6 MO with configurationMode other than MANUAL within Router MO.\nIf AUTOMATIC, there can be no child DomainFilter MO.\nIf AUTOMATIC, serverAddress cannot be set.\nIf AUTOMATIC, localIpAddress attribute must either not be set or it must refer to AddressIPv4 MO or AddressIPv6 MO with configuration mode other than MANUAL.\nIf AUTOMATIC, and there is one AddressIPv4 MO and one AddressIPv6 MO with configurationMode other than MANUAL within Router MO, localIpAddress attribute must be set.";
      type erienmnrmrtndnsclient:enum-DnsConfigMode;
      default MANUAL;
    }
    leaf-list usedServerAddress {
      min-elements 0;
      max-elements 3;
      config false;
      description "List of used DNS server addresses.\nIPv4 address is specified in dotted quad notation, for example 130.100.92.154. RFC 791 describes syntax details.\nIPv6 address is specified by 8 groups of 16 bit hexadecimal values separated by colons, for example 2001:0db8:85a3:0000:0000:8a2e:0370:7334.\nRFC 4291 describes syntax details.\n";
      yexte:dependencies "If configurationMode is MANUAL, attribute has the same content as serverAddress.\nIf configurationMode is AUTOMATIC, retrieved addresses are shown in this attribute.";
      notife:notifiable-state-data true;
      type string;
    }
    leaf userLabel {
      description "Label for free use. ";
      type erienmnrmrtndnsclient:ddt-RtnDnsClient_DnsClient_userLabel;
    }
    leaf dscp {
      description "DSCP value for DNS related IP packets.\nOnly IP packets originated from this node are tagged with DSCP value.";
      type erienmnrmrtndnsclient:ddt-RtnDnsClient_DnsClient_dscp;
      default 40;
    }
    leaf-list reservedBy {
      min-elements 0;
      config false;
      description "Contains a list of MO instances that reserve this MO instance.";
      notife:notifiable-state-data true;
      erienmyext:enm-type MOREF;
      type string;
    }
    leaf-list serverAddress {
      min-elements 0;
      max-elements 3;
      description "List of configured DNS server addresses.";
      yexte:dependencies "Server addresses must be of same type, either IPv4 or IPv6 address.\nServer addresses must be of same type as localIpAddress (IPv4 or IPv6).\nMust be of same type as serverAddress in DomainFilter MO, either IPv4 or IPv6 address.\nIf configurationMode is AUTOMATIC, serverAddress cannot be set.";
      type erienmnrmrtndnsclient:ddt-IpDNSAddress;
    }
    leaf localIpAddress {
      description "Reference to address.\nIf set, DNS requests are sent from address configured by referenced MO type AddressIPv4 or AddressIPv6.\nIf unset, DNS requests are sent from address, within Router MO, selected by system.";
      yexte:dependencies "Referred MO type AddressIPv4 or AddressIPv6 must be within same Router MO.\nMust be of same type as serverAddress in DomainFilter MO, either IPv4 or IPv6 address.\nIf configurationMode is AUTOMATIC, this attribute must either not be set or it must refer to  AddressIPv4 MO or AddressIPv6 MO with configuration mode other than MANUAL.\nIf configurationMode is AUTOMATIC, and there is one AddressIPv4 MO and one AddressIPv6 MO with configurationMode other than MANUAL within Router MO, this attribute must be set.\n";
      erienmyext:enm-type MOREF;
      type string;
    }
  } // end 'grouping moc-DnsClient'
  grouping moc-DomainFilter-keys {
    description "Key(s) for MOC DomainFilter";
    leaf id {
      erienmyext:no-notification;
      description "The value component of the RDN.";
      mandatory true;
      yexte:ecim-name domainFilterId;
      type string;
    }
  } // end 'grouping moc-DomainFilter-keys'
  grouping moc-DomainFilter {
    description "Represents domain filter, that enables sending DNS requests for one or more domains to special DNS server.\nDefault DNS server is defined in DnsClient MO and DomainFilter MO can provide exceptions for specific domains.";
    leaf userLabel {
      description "Label for free use.
\n";
      type erienmnrmrtndnsclient:ddt-RtnDnsClient_DomainFilter_userLabel;
    }
    leaf-list domain {
      min-elements 1;
      max-elements 5;
      description "DNS requests matching one of domains will be sent to servers specified in serverAddress instead of servers in DnsClient MO.\nExample: example.com will match requests like host.example.com.";
      type erienmnrmrtndnsclient:ddt-RtnDnsClient_DomainFilter_domain;
    }
    leaf-list serverAddress {
      min-elements 1;
      max-elements 3;
      description "List of addresses of DNS servers.";
      yexte:dependencies "Server addresses must be of same type, either IPv4 or IPv6 address.\nServer addresses must be of same type as localIpAddress (IPv4 or IPv6) in DnsClient MO.\nServer addresses must be of same type as serverAddress (IPv4 or IPv6) in DnsClient MO.";
      type erienmnrmrtndnsclient:ddt-IpAddress;
    }
  } // end 'grouping moc-DomainFilter'
  augment /erienmnrmcomtop:ManagedElement/erienmnrmcomtop:Transport/erienmnrmrtnl3router:Router {
    list DnsClient {
      key id;
      max-elements 1;
      description "Represents DNS client.";
      erienmyext:enm-type MOC;
      uses moc-DnsClient-keys;
      container attributes {
        description "Attributes for DnsClient";
        uses moc-DnsClient;
      } // end 'container attributes'
    } // end 'list DnsClient'
  }
  augment /erienmnrmcomtop:ManagedElement/erienmnrmcomtop:Transport/erienmnrmrtnl3router:Router/erienmnrmrtndnsclient:DnsClient {
    list DomainFilter {
      key id;
      max-elements 2;
      description "Represents domain filter, that enables sending DNS requests for one or more domains to special DNS server.\nDefault DNS server is defined in DnsClient MO and DomainFilter MO can provide exceptions for specific domains.";
      erienmyext:enm-type MOC;
      uses moc-DomainFilter-keys;
      container attributes {
        description "Attributes for DomainFilter";
        uses moc-DomainFilter;
      } // end 'container attributes'
    } // end 'list DomainFilter'
  }
}
