module ericsson-enm-RmeTlsSupport {
  yang-version 1.1;
  namespace urn:rdns:com:ericsson:ericsson-enm-RmeTlsSupport;
  prefix erienmnrmrmetlssupport;
  yexte:ecim-name RmeTlsSupport;
  revision 2351-11-28 {
    yexte:version 1;
    yexte:release 0;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RmeSupport {
    prefix erienmnrmrmesupport;
  }
  typedef ddt-maxTls {
    description "Maximum number of simultaneous TLS sessions.";
    type uint8 {
      range 20..70;
    }
  }
  grouping moc-TlsSupport-keys {
    description "Key(s) for MOC TlsSupport";
    leaf id {
      erienmyext:no-notification;
      description "The value component of the RDN.";
      mandatory true;
      yexte:ecim-name tlsSupportId;
      type string;
    }
  } // end 'grouping moc-TlsSupport-keys'
  grouping moc-TlsSupport {
    description "Proprietary parameters for TLS.";
    leaf maxTlsSessions {
      description "Maximum number of simultaneous TLS sessions allowed on the OAM TLS servers.";
      type erienmnrmrmetlssupport:ddt-maxTls;
      default 20;
    }
  } // end 'grouping moc-TlsSupport'
  augment /erienmnrmcomtop:ManagedElement/erienmnrmrmesupport:NodeSupport {
    list TlsSupport {
      key id;
      max-elements 1;
      description "Proprietary parameters for TLS.";
      erienmyext:enm-type MOC;
      uses moc-TlsSupport-keys;
      container attributes {
        description "Attributes for TlsSupport";
        uses moc-TlsSupport;
      } // end 'container attributes'
    } // end 'list TlsSupport'
  }
}
