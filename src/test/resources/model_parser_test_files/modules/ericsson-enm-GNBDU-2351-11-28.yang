module ericsson-enm-GNBDU {
  yang-version 1.1;
  namespace urn:rdns:com:ericsson:ericsson-enm-GNBDU;
  prefix erienmnrmgnbdu;
  yexte:ecim-name GNBDU;
  revision 2351-11-28 {
    yexte:version 27;
    yexte:release 0;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef enum-NValue {
    description "Number of PFs in the DRX cycle.";
    type enumeration {
      enum T {
        description "One T is every radio frame.";
        value 0;
      }
      enum T1_2 {
        description "Every second radio frame.";
        value 1;
      }
      enum T1_4 {
        description "Every fourth radio frame.";
        value 2;
      }
      enum T1_8 {
        description "Every eighth radio frame.";
        value 3;
      }
      enum T1_16 {
        description "Every sixteenth radio frame.";
        value 4;
      }
    }
  }
  typedef enum-CsiRsControl2Ports {
    description "Value for configuration of 2-port CSI-RS.";
    type enumeration {
      enum OFF {
        description "2-port CSI-RS disabled.";
        value 0;
      }
      enum ON {
        description "2-port CSI-RS enabled.";
        value 1;
      }
    }
  }
  typedef enum-CsiRsControl32Ports {
    description "Value for configuration of 32-port CSI-RS.";
    type enumeration {
      enum OFF {
        description "32 port CSIRS is disabled.";
        value 0;
      }
      enum EIGHT_TWO_N1AZ {
        description "32 port CSI-RS is enabled; PMI feedback will be based on Type 1 single panel codebook (N1=8 N2=2).\n\nThe N1 (i11) codebook dimension is associated with azimuth.";
        value 1;
      }
      enum FOUR_FOUR {
        description "32 port CSI-RS is enabled; PMI feedback will be based on Type 1 single panel codebook (N1=4 N2=4).";
        value 2;
      }
    }
  }
  typedef enum-CsiRsControl8Ports {
    description "Value for configuration of 8-port CSI-RS.";
    type enumeration {
      enum OFF {
        description "The 8 port CSI-RS is disabled.";
        value 0;
      }
      enum FOUR_ONE_N1AZ {
        description "8 port CSI-RS is enabled; PMI feedback will be based on Type 1 single panel codebook (N1=4 N2=1).\n\nThe N1 (i11) codebook dimension is associated with azimuth.";
        value 1;
      }
      enum FOUR_ONE_N1EL {
        description "8 port CSI-RS is enabled; PMI feedback will be based on Type 1 single panel codebook (N1=4 N2=1).\n\nThe N1 (i11) codebook dimension is associated with elevation.";
        value 2;
      }
      enum TWO_TWO {
        description "8 port CSI-RS is enabled; PMI feedback will be based on Type 1 single panel codebook (N1=2 N2=2).";
        value 3;
      }
    }
  }
  typedef enum-NRCellState {
    description "Cell states.";
    type enumeration {
      enum IDLE {
        description "The resource is not currently in use.";
        value 0;
      }
      enum INACTIVE {
        description "The cell is known by both the gNodeB-DU and the gNodeB-CU-CP.\n\nThe cell shall not serve UEs.";
        value 1;
      }
      enum ACTIVE {
        description "The cell is known by both the gNodeB-DU and the gNodeB-CU-CP.\n\nThe cell should try to provide service to the UEs.";
        value 2;
      }
    }
  }
  typedef enum-AdmState {
    description "Administrative state of a resource.";
    type enumeration {
      enum LOCKED {
        description "The resource is administratively prohibited from performing services for its users.";
        value 0;
      }
      enum UNLOCKED {
        description "The resource is administratively permitted to perform services for its users.\nThis is independent of its inherent operability.";
        value 1;
      }
      enum SHUTTINGDOWN {
        description "Use of the resource is administratively permitted to existing instances of use only.\nWhile the system remains in the shutting down state the manager may at any time cause the managed object to revert to the locked state.";
        value 2;
      }
    }
  }
  typedef enum-CellBarred {
    description "Indicates if the NR cell is barred.";
    type enumeration {
      enum BARRED {
        description "The NR cell is barred";
        value 0;
      }
      enum NOT_BARRED {
        description "The NR cell is not barred";
        value 1;
      }
    }
  }
  typedef enum-OperState {
    description "Operational states of a resource.";
    type enumeration {
      enum DISABLED {
        description "The resource is  totally inoperable.";
        value 0;
      }
      enum ENABLED {
        description "The resource is partially or fully operable.";
        value 1;
      }
    }
  }
  typedef enum-TddSpecialSlotPatternType {
    description "Defines downlink, guard, and uplink symbols within special slot or slots.\n\nSymbols are listed in downlink:guard:uplink order.\nFor example, a pattern given as 3:8:3 starts with three downlink symbols followed by an eight symbol guard and ending with three uplink symbols.";
    type enumeration {
      enum TDD_SPECIAL_SLOT_PATTERN_00 {
        description "Special slot pattern 11:3:0.";
        value 0;
      }
      enum TDD_SPECIAL_SLOT_PATTERN_01 {
        description "Special slot pattern 3:8:3.";
        value 1;
      }
      enum TDD_SPECIAL_SLOT_PATTERN_02 {
        description "Special slot pattern 10:2:2.";
        value 2;
      }
      enum TDD_SPECIAL_SLOT_PATTERN_03 {
        description "NR special slot equivalent to LTE SSF conf 7, with 6 DL symbols, 4 guard symbols, and 4 UL symbols.";
        value 3;
      }
      enum TDD_SPECIAL_SLOT_PATTERN_04 {
        description "NR special slot equivalent to LTE SSF conf 6, with 4 DL symbols, 6 guard symbols, and 4 UL symbols.";
        value 4;
      }
      enum TDD_SPECIAL_SLOT_PATTERN_05 {
        description "NR special slots {6:8:0; 0:10:4} equivalent to LTE SSF conf 5, with two consecutive special slots.";
        value 5;
      }
    }
  }
  typedef enum-CoverageShape {
    description "Specifies the coverage shape of a sector carrier.";
    type enumeration {
      enum PRODUCT_DEFAULT {
        description "Product specific default coverage shape.";
        value 0;
      }
      enum MACRO_1 {
        description "Coverage shape with larger beam space ratio in azimuth plane than in elevation plane.\n\nBeam space ratio for MACRO is product specific.";
        value 1;
      }
      enum HIGHRISE_1 {
        description "Coverage shape with larger beam space ration in elevation plane than in azimuth plane.\n\nBeam space ratio for HIGHRISE is product specific.";
        value 2;
      }
      enum HOTSPOT_1 {
        description "Coverage shape with full beam space in both azimuth and elevation.\n\nFull beam space range is product specific.";
        value 3;
      }
    }
  }
  typedef enum-DrxInactivityTimer {
    description "Inactivity timer value for DRX.";
    type enumeration {
      enum INACTIVITYTIMER_0MS {
        description "Inactivity timer value 0.";
        value 0;
      }
      enum INACTIVITYTIMER_1MS {
        description "Inactivity timer value 1 ms.";
        value 1;
      }
      enum INACTIVITYTIMER_2MS {
        description "Inactivity timer value 2 ms.";
        value 2;
      }
      enum INACTIVITYTIMER_3MS {
        description "Inactivity timer value 3 ms.";
        value 3;
      }
      enum INACTIVITYTIMER_4MS {
        description "Inactivity timer value 4 ms.";
        value 4;
      }
      enum INACTIVITYTIMER_5MS {
        description "Inactivity timer value 5 ms.";
        value 5;
      }
      enum INACTIVITYTIMER_6MS {
        description "Inactivity timer value 6 ms.";
        value 6;
      }
      enum INACTIVITYTIMER_8MS {
        description "Inactivity timer value 8 ms.";
        value 7;
      }
      enum INACTIVITYTIMER_10MS {
        description "Inactivity timer value 10 ms.";
        value 8;
      }
      enum INACTIVITYTIMER_20MS {
        description "Inactivity timer value 20 ms.";
        value 9;
      }
      enum INACTIVITYTIMER_30MS {
        description "Inactivity timer value 30 ms.";
        value 10;
      }
      enum INACTIVITYTIMER_40MS {
        description "Inactivity timer value 40 ms.";
        value 11;
      }
      enum INACTIVITYTIMER_50MS {
        description "Inactivity timer value 50 ms.";
        value 12;
      }
      enum INACTIVITYTIMER_60MS {
        description "Inactivity timer value 60 ms.";
        value 13;
      }
      enum INACTIVITYTIMER_80MS {
        description "Inactivity timer value 80 ms.";
        value 14;
      }
      enum INACTIVITYTIMER_100MS {
        description "Inactivity timer value 100 ms.";
        value 15;
      }
      enum INACTIVITYTIMER_200MS {
        description "Inactivity timer value 200 ms.";
        value 16;
      }
      enum INACTIVITYTIMER_300MS {
        description "Inactivity timer value 300 ms.";
        value 17;
      }
      enum INACTIVITYTIMER_500MS {
        description "Inactivity timer value 500 ms.";
        value 18;
      }
      enum INACTIVITYTIMER_750MS {
        description "Inactivity timer value 750 ms.";
        value 19;
      }
      enum INACTIVITYTIMER_1280MS {
        description "Inactivity timer value 1280 ms.";
        value 20;
      }
      enum INACTIVITYTIMER_1920MS {
        description "Inactivity timer value 1920 ms.";
        value 21;
      }
      enum INACTIVITYTIMER_2560MS {
        description "Inactivity timer value 2560 ms.";
        value 22;
      }
    }
  }
  typedef enum-NRCellServiceState {
    description "Cell service state.";
    type enumeration {
      enum OUT_OF_SERVICE {
        description "Cell is not operational and cannot serve UE instances.\n\nThe gNodeB Distributed Unit (gNodeB-DU) is trying to make cell operational.";
        value 0;
      }
      enum IN_SERVICE {
        description "Cell is operational and can serve UE instances.";
        value 1;
      }
    }
  }
  typedef enum-AqmMode {
    description "AQM mode.";
    type enumeration {
      enum OFF {
        description "Turned off.";
        status current {
          yexte:preliminary;
        }
        value 0;
      }
      enum MODE1 {
        description Non-GBR.;
        status current {
          yexte:preliminary;
        }
        value 1;
      }
      enum MODE2 {
        description GBR.;
        status current {
          yexte:preliminary;
        }
        value 2;
      }
    }
  }
  typedef enum-CellReservedForOperator {
    description "Whether the NR cell is reserved for operator use.";
    type enumeration {
      enum RESERVED {
        description "NR cell reserved for operator use.";
        value 0;
      }
      enum NOT_RESERVED {
        description "NR cell not reserved for operator use.";
        value 1;
      }
    }
  }
  typedef enum-SiBroadcastStatus {
    description "Broadcast status.";
    type enumeration {
      enum BROADCASTING {
        description "The SI-message is broadcast.";
        value 0;
      }
    }
  }
  typedef enum-MaxUeSpeed {
    description "Maximum UE moving speed support.";
    type enumeration {
      enum UP_TO_10KMPH {
        description "Up to 10 km/h UE speed is supported.";
        value 0;
      }
      enum UP_TO_50KMPH {
        description "Up to 50 km/h UE speed is supported.";
        value 1;
      }
      enum UP_TO_100KMPH {
        description "Up to 100 km/h UE speed is supported.";
        value 2;
      }
      enum UP_TO_200KMPH {
        description "Up to 200 km/h UE speed is supported.";
        value 3;
      }
      enum UP_TO_350KMPH {
        description "Up to 350 km/h UE speed is supported.";
        value 4;
      }
      enum UP_TO_500KMPH {
        description "Up to 500 km/h UE speed is supported.";
        value 5;
      }
    }
  }
  typedef enum-CsiRsControl16Ports {
    description "Value for configuration of 16-port CSI-RS.";
    type enumeration {
      enum OFF {
        description "The 16 port CSIRS is disabled.";
        value 0;
      }
      enum EIGHT_ONE_N1AZ {
        description "16 port CSI-RS is enabled; PMI feedback will be based on Type 1 single panel codebook (N1=8 N2=1).\n\nThe N1 (i11) codebook dimension is associated with azimuth.";
        value 1;
      }
      enum FOUR_TWO_N1AZ {
        description "16 port CSI-RS is enabled; PMI feedback will be based on Type 1 single panel codebook (N1=4 N2=2).\n\nThe N1 (i11) codebook dimension is associated with azimuth.";
        value 2;
      }
      enum FOUR_TWO_N1EL {
        description "16 port CSI-RS is enabled; PMI feedback will be based on Type 1 single panel codebook (N1=4 N2=2).\n\nThe N1 (i11) codebook dimension is associated with elevation.";
        value 3;
      }
    }
  }
  typedef enum-RadioOperatingModeEnhanced {
    description "Operating mode options for cell traffic profile set by operator.";
    type enumeration {
      enum COVERAGE {
        description "Can give higher output power.";
        value 0;
      }
      enum CAPACITY {
        description "Can give better signal quality.";
        value 1;
      }
      enum COVERAGE_GREEN {
        description "Can give higher output power when combined with power savings in some cases.";
        value 2;
      }
      enum CAPACITY_GREEN {
        description "Can give better signal quality when combined with power savings in some cases.";
        value 3;
      }
    }
  }
  typedef enum-ServiceType {
    description "Service type.";
    type enumeration {
      enum UNDEFINED {
        description "No service defined.";
        status current {
          yexte:preliminary;
        }
        value 0;
      }
      enum VOIP {
        description "Service type is VOIP.";
        status current {
          yexte:preliminary;
        }
        value 1;
      }
      enum IMS_SIGNALING {
        description "Service type is IMS signaling.";
        status current {
          yexte:preliminary;
        }
        value 2;
      }
      enum PTT {
        description "Mission-Critical and non-Mission-Critical Push-to-Talk.";
        status current {
          yexte:preliminary;
        }
        value 3;
      }
      enum MC_SIGNALING {
        description "Mission-Critical delay-sensitive signaling.";
        status current {
          yexte:preliminary;
        }
        value 4;
      }
    }
  }
  typedef enum-RachPreambleFormatType {
    description "Defines preamble format for RACH.";
    type enumeration {
      enum RACH_PREAMBLE_FORMAT_00 {
        description "RACH preamble format 0.";
        value 0;
      }
      enum RACH_PREAMBLE_FORMAT_01 {
        description "RACH preamble format B4.";
        value 1;
      }
      enum RACH_PREAMBLE_FORMAT_02 {
        description "RACH preamble format 1.";
        value 2;
      }
      enum RACH_PREAMBLE_FORMAT_03 {
        description "RACH preamble format A3.";
        value 3;
      }
      enum RACH_PREAMBLE_FORMAT_04 {
        description "RACH preamble format C2.";
        value 4;
      }
    }
  }
  typedef enum-NRCellServiceStatus {
    description "Cell service status.";
    type enumeration {
      enum OUT_OF_SERVICE {
        description "The cell is not operational, and it is not able to serve UEs.\n\nThe gNodeB-DU is trying to make the cell operational.";
        status deprecated {
          yexte:status-information "Since 20.Q1. Planned to be removed.";
        }
        value 0;
      }
      enum IN_SERVICE {
        description "The cell is operational and able to serve UEs.";
        status deprecated {
          yexte:status-information "Since 20.Q1. Planned to be removed.";
        }
        value 1;
      }
    }
  }
  typedef enum-InterfaceName {
    description "RAN interfaces.";
    type enumeration {
      enum C5 {
        description "C5 for user plane.";
        value 0;
      }
      enum E1 {
        description "E1 for control and user plane.";
        value 1;
      }
      enum E6 {
        description "E6 for control plane.";
        value 2;
      }
      enum F1 {
        description "F1 for control and user plane.";
        value 3;
      }
      enum NG {
        description "NG for control and user plane.";
        value 4;
      }
      enum S1 {
        description "S1 for user plane.";
        value 5;
      }
      enum XN {
        description "Xn for control and user plane.";
        value 6;
      }
      enum X2 {
        description "X2 for control and user plane.";
        value 7;
      }
    }
  }
  typedef enum-CbfMacroTaperType {
    description "Specifies the taper type used for Macro coverage shape.";
    type enumeration {
      enum STANDARD {
        description "Standard tapering for Macro coverage shape.";
        value 0;
      }
      enum HIGHEIRP {
        description "High EIRP tapering for Macro coverage shape.";
        value 1;
      }
    }
  }
  typedef enum-CsiReportFormat {
    description "Value for CSI Report Format.";
    type enumeration {
      enum CQI_WB_PMI_WB {
        description "Wideband CQI and wideband PMI feedback.";
        value 0;
      }
      enum CQI_WB_PMI_SB {
        description "Wideband CQI and subband PMI feedback.";
        value 1;
      }
      enum CQI_SB_PMI_WB {
        description "Subband CQI and wideband PMI feedback.";
        value 2;
      }
      enum CQI_SB_PMI_SB {
        description "Subband CQI and subband PMI feedback.";
        value 3;
      }
    }
  }
  typedef enum-FixWideBeamsForPeriodicSrType {
    description "Number of fixed wide beams for periodic Scheduling Request (SR).\n\nPeriodic SR is sent in PRACH slot according to SSB relation.";
    type enumeration {
      enum FIX_WB_FOR_PERIODIC_SR_NONE {
        description "Number of fixed wide beams in PRACH slot according to SSB relation for periodic SR is set to 0.";
        value 0;
      }
      enum FIX_WB_FOR_PERIODIC_SR_LOW {
        description "Number of fixed wide beams in PRACH slot according to SSB relation for periodic SR is set to 2.";
        value 1;
      }
      enum FIX_WB_FOR_PERIODIC_SR_MEDIUM {
        description "Number of fixed wide beams in PRACH slot according to SSB relation for periodic SR is set to 4.";
        value 2;
      }
      enum FIX_WB_FOR_PERIODIC_SR_HIGH {
        description "Number of fixed wide beams in PRACH slot according to SSB relation for periodic SR is set to 6.";
        value 3;
      }
    }
  }
  typedef enum-DrxOnDurationTimer {
    description "On-duration timer value for DRX.";
    type enumeration {
      enum ONDURATIONTIMER_1SUBMS {
        description "On-duration value 1/32 ms.";
        value 1;
      }
      enum ONDURATIONTIMER_2SUBMS {
        description "On-duration value 2/32 ms.";
        value 2;
      }
      enum ONDURATIONTIMER_3SUBMS {
        description "On-duration value 3/32 ms.";
        value 3;
      }
      enum ONDURATIONTIMER_4SUBMS {
        description "On-duration value 4/32 ms.";
        value 4;
      }
      enum ONDURATIONTIMER_5SUBMS {
        description "On-duration value 5/32 ms.";
        value 5;
      }
      enum ONDURATIONTIMER_6SUBMS {
        description "On-duration value 6/32 ms.";
        value 6;
      }
      enum ONDURATIONTIMER_7SUBMS {
        description "On-duration value 7/32 ms.";
        value 7;
      }
      enum ONDURATIONTIMER_8SUBMS {
        description "On-duration value 8/32 ms.";
        value 8;
      }
      enum ONDURATIONTIMER_9SUBMS {
        description "On-duration value 9/32 ms.";
        value 9;
      }
      enum ONDURATIONTIMER_10SUBMS {
        description "On-duration value 10/32 ms.";
        value 10;
      }
      enum ONDURATIONTIMER_11SUBMS {
        description "On-duration value 11/32 ms.";
        value 11;
      }
      enum ONDURATIONTIMER_12SUBMS {
        description "On-duration value 12/32 ms.";
        value 12;
      }
      enum ONDURATIONTIMER_13SUBMS {
        description "On-duration value 13/32 ms.";
        value 13;
      }
      enum ONDURATIONTIMER_14SUBMS {
        description "On-duration value 14/32 ms.";
        value 14;
      }
      enum ONDURATIONTIMER_15SUBMS {
        description "On-duration value 15/32 ms.";
        value 15;
      }
      enum ONDURATIONTIMER_16SUBMS {
        description "On-duration value 16/32 ms.";
        value 16;
      }
      enum ONDURATIONTIMER_17SUBMS {
        description "On-duration value 17/32 ms.";
        value 17;
      }
      enum ONDURATIONTIMER_18SUBMS {
        description "On-duration value 18/32 ms.";
        value 18;
      }
      enum ONDURATIONTIMER_19SUBMS {
        description "On-duration value 19/32 ms.";
        value 19;
      }
      enum ONDURATIONTIMER_20SUBMS {
        description "On-duration value 20/32 ms.";
        value 20;
      }
      enum ONDURATIONTIMER_21SUBMS {
        description "On-duration value 21/32 ms.";
        value 21;
      }
      enum ONDURATIONTIMER_22SUBMS {
        description "On-duration value 22/32 ms.";
        value 22;
      }
      enum ONDURATIONTIMER_23SUBMS {
        description "On-duration value 23/32 ms.";
        value 23;
      }
      enum ONDURATIONTIMER_24SUBMS {
        description "On-duration value 24/32 ms.";
        value 24;
      }
      enum ONDURATIONTIMER_25SUBMS {
        description "On-duration value 25/32 ms.";
        value 25;
      }
      enum ONDURATIONTIMER_26SUBMS {
        description "On-duration value 26/32 ms.";
        value 26;
      }
      enum ONDURATIONTIMER_27SUBMS {
        description "On-duration value 27/32 ms.";
        value 27;
      }
      enum ONDURATIONTIMER_28SUBMS {
        description "On-duration value 28/32 ms.";
        value 28;
      }
      enum ONDURATIONTIMER_29SUBMS {
        description "On-duration value 29/32 ms.";
        value 29;
      }
      enum ONDURATIONTIMER_30SUBMS {
        description "On-duration value 30/32 ms.";
        value 30;
      }
      enum ONDURATIONTIMER_31SUBMS {
        description "On-duration value 31/32 ms.";
        value 31;
      }
      enum ONDURATIONTIMER_1MS {
        description "On-duration value 1 ms.";
        value 32;
      }
      enum ONDURATIONTIMER_2MS {
        description "On-duration value 2 ms.";
        value 33;
      }
      enum ONDURATIONTIMER_3MS {
        description "On-duration value 3 ms.";
        value 34;
      }
      enum ONDURATIONTIMER_4MS {
        description "On-duration value 4 ms.";
        value 35;
      }
      enum ONDURATIONTIMER_5MS {
        description "On-duration value 5 ms.";
        value 36;
      }
      enum ONDURATIONTIMER_6MS {
        description "On-duration value 6 ms.";
        value 37;
      }
      enum ONDURATIONTIMER_8MS {
        description "On-duration value 8 ms.";
        value 38;
      }
      enum ONDURATIONTIMER_10MS {
        description "On-duration value 10 ms.";
        value 39;
      }
      enum ONDURATIONTIMER_20MS {
        description "On-duration value 20 ms.";
        value 40;
      }
      enum ONDURATIONTIMER_30MS {
        description "On-duration value 30 ms.";
        value 41;
      }
      enum ONDURATIONTIMER_40MS {
        description "On-duration value 40 ms.";
        value 42;
      }
      enum ONDURATIONTIMER_50MS {
        description "On-duration value 50 ms.";
        value 43;
      }
      enum ONDURATIONTIMER_60MS {
        description "On-duration value 60 ms.";
        value 44;
      }
      enum ONDURATIONTIMER_80MS {
        description "On-duration value 80 ms.";
        value 45;
      }
      enum ONDURATIONTIMER_100MS {
        description "On-duration value 100 ms.";
        value 46;
      }
      enum ONDURATIONTIMER_200MS {
        description "On-duration value 200 ms.";
        value 47;
      }
      enum ONDURATIONTIMER_300MS {
        description "On-duration value 300 ms.";
        value 48;
      }
      enum ONDURATIONTIMER_400MS {
        description "On-duration value 400 ms.";
        value 49;
      }
      enum ONDURATIONTIMER_500MS {
        description "On-duration value 500 ms.";
        value 50;
      }
      enum ONDURATIONTIMER_600MS {
        description "On-duration value 600 ms.";
        value 51;
      }
      enum ONDURATIONTIMER_800MS {
        description "On-duration value 800 ms.";
        value 52;
      }
      enum ONDURATIONTIMER_1000MS {
        description "On-duration value 1000 ms.";
        value 53;
      }
      enum ONDURATIONTIMER_1200MS {
        description "On-duration value 1200 ms.";
        value 54;
      }
      enum ONDURATIONTIMER_1600MS {
        description "On-duration value 1600 ms.";
        value 55;
      }
    }
  }
  typedef enum-DrxLongCycle {
    description "Long Cycle value for DRX.";
    type enumeration {
      enum LONGCYCLE_10MS {
        description "Long cycle value 10 ms.";
        value 1;
      }
      enum LONGCYCLE_20MS {
        description "Long cycle value 20 ms.";
        value 2;
      }
      enum LONGCYCLE_32MS {
        description "Long cycle value 32 ms.";
        value 3;
      }
      enum LONGCYCLE_40MS {
        description "Long cycle value 40 ms.";
        value 4;
      }
      enum LONGCYCLE_60MS {
        description "Long cycle value 60 ms.";
        value 5;
      }
      enum LONGCYCLE_64MS {
        description "Long cycle value 64 ms.";
        value 6;
      }
      enum LONGCYCLE_70MS {
        description "Long cycle value 70 ms.";
        value 7;
      }
      enum LONGCYCLE_80MS {
        description "Long cycle value 80 ms.";
        value 8;
      }
      enum LONGCYCLE_128MS {
        description "Long cycle value 128 ms.";
        value 9;
      }
      enum LONGCYCLE_160MS {
        description "Long cycle value 160 ms.";
        value 10;
      }
      enum LONGCYCLE_256MS {
        description "Long cycle value 256 ms.";
        value 11;
      }
      enum LONGCYCLE_320MS {
        description "Long cycle value 320 ms.";
        value 12;
      }
      enum LONGCYCLE_512MS {
        description "Long cycle value 512 ms.";
        value 13;
      }
      enum LONGCYCLE_640MS {
        description "Long cycle value 640 ms.";
        value 14;
      }
      enum LONGCYCLE_1024MS {
        description "Long cycle value 1024 ms.";
        value 15;
      }
      enum LONGCYCLE_1280MS {
        description "Long cycle value 1280 ms.";
        value 16;
      }
      enum LONGCYCLE_2048MS {
        description "Long cycle value 2048 ms.";
        value 17;
      }
      enum LONGCYCLE_2560MS {
        description "Long cycle value 2560 ms.";
        value 18;
      }
      enum LONGCYCLE_5120MS {
        description "Long cycle value 5120 ms.";
        value 19;
      }
      enum LONGCYCLE_10240MS {
        description "Long cycle value 10240 ms.";
        value 20;
      }
    }
  }
  typedef enum-AilgModType {
    description "Air Interface Load Generator (AILG) modulation type.";
    type enumeration {
      enum AILG_MOD_QPSK {
        description "Modulation type for AILG PDSCH is QPSK.";
        value 0;
      }
      enum AILG_MOD_16QAM {
        description "Modulation type for AILG PDSCH is 16QAM.";
        value 1;
      }
      enum AILG_MOD_64QAM {
        description "Modulation type for AILG PDSCH is 64QAM.";
        value 2;
      }
      enum AILG_MOD_256QAM {
        description "Modulation type for AILG PDSCH is 256QAM.";
        value 3;
      }
    }
  }
  typedef enum-TrsResourceShifting {
    description "Value for configuring trsResourceShifting.";
    type enumeration {
      enum DEACTIVATED {
        description "TRS is not shifted.\n\nAll cells use the same TRS resource position and PDSCH can be multiplexed in TRS symbols.";
        value 0;
      }
      enum ACTIVATED {
        description "TRS resource shifting is activated with no multiplexing of PDSCH in TRS symbols.";
        value 1;
      }
    }
  }
  typedef enum-UlCalibrationStatus {
    description "Describes the current uplink antenna calibration status.";
    type enumeration {
      enum INACTIVE {
        description "Uplink antenna calibration is not activated.";
        value 0;
      }
      enum CONVERGING {
        description "Uplink antenna calibration is converging.";
        value 1;
      }
      enum CALIBRATED {
        description "Uplink antenna calibration is finished with success.";
        value 2;
      }
      enum FAILED {
        description "Uplink antenna calibration has failed.";
        value 3;
      }
    }
  }
  typedef enum-CsiRsActivePortConfig {
    description "Shown the active CSI-RS configuration.\n\nBased on the MOM settings and its HW/SW resources, GNodeB chooses the most appropriate CSI-RS configuration, and shows in the form of list.\nExample: {\"PORT_4\",\"PORT_8\"} means that 4-port CSI-RS and 8-port CSI-RS are transmitted simultaneously.";
    type enumeration {
      enum PORT_2 {
        description "2-port CSI-RS is transmitted.";
        value 0;
      }
      enum PORT_4 {
        description "4-port CSI-RS is transmitted.";
        value 1;
      }
      enum PORT_8 {
        description "8-port CSI-RS is transmitted.";
        value 2;
      }
      enum PORT_16 {
        description "16-port CSI-RS is transmitted.";
        value 3;
      }
      enum PORT_32 {
        description "32-port CSI-RS is transmitted.";
        value 4;
      }
    }
  }
  typedef enum-DlCalibrationStatus {
    description "Describes the current downlink antenna calibration status.";
    type enumeration {
      enum INACTIVE {
        description "Downlink antenna calibration is not activated.";
        value 0;
      }
      enum CONVERGING {
        description "Downlink antenna calibration is converging.";
        value 1;
      }
      enum CALIBRATED {
        description "Downlink antenna calibration is finished with success.";
        value 2;
      }
      enum FAILED {
        description "Downlink antenna calibration has failed.";
        value 3;
      }
    }
  }
  typedef enum-AvailStatus {
    description "The availability status is used to qualify the operational state.\nIt indicates why the operational state has changed its value.";
    type enumeration {
      enum IN_TEST {
        description "The resource is undergoing a test procedure.\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.\nThis routine operation is to place the resource online and make it available for use. The operation may be manual or automatic, or both.\nThe operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.\nThe semantics are defined in CCITT Rec. X.735 | ISO/IEC 10164-6.";
        value 8;
      }
      enum DEPENDENCY_LOCKED {
        description "The administrative state of a resource that this resource depends on is locked.\nAlternatively, the availability status of the other resource is dependency locked.";
        value 9;
      }
      enum DEPENDENCY_FAILED {
        description "The availability status of a resource that this resource depends on is failed or dependency failed.";
        value 10;
      }
      enum DEPENDENCY_SHUTTINGDOWN {
        description "The administrative state of a resource that this resource depends on is shutting down.\nAlternatively, the availability status of the other resource is dependency shutting down.";
        value 11;
      }
      enum DEPENDENCY_RECOVERY {
        description "Resource that this resource depends on is undergoing a recovery procedure.";
        value 12;
      }
      enum DEPENDENCY_HOLDING {
        description "Resource cannot operate because some other resource on which it depends is currently unavailable.\nThe situation is expected to be resolved. Actions to facilitate dependency resolution may be ongoing.";
        value 13;
      }
    }
  }
  typedef enum-UlCalibrationMethod {
    description "Describes which types of uplink antenna calibration are supported and/or used.";
    type enumeration {
      enum NONE {
        description "No antenna calibration method.";
        value 0;
      }
      enum INTERNAL {
        description "Internal antenna calibration method.";
        value 1;
      }
    }
  }
  typedef enum-DlCalibrationMethod {
    description "Describes which types of downlink antenna calibration are supported and/or used.";
    type enumeration {
      enum NONE {
        description "No antenna calibration method.";
        value 0;
      }
      enum INTERNAL {
        description "Internal antenna calibration method.";
        value 1;
      }
    }
  }
  typedef enum-CsiRsControl4Ports {
    description "Value for configuration of 4-port CSI-RS.";
    type enumeration {
      enum OFF {
        description "4-port CSI-RS is disabled.";
        value 0;
      }
      enum TWO_ONE {
        description "4-port CSI-RS enabled.\n\nPMI feedback based on Type 1 single panel codebook (N1=2 N2=1).";
        value 1;
      }
    }
  }
  typedef enum-LinkActive {
    description "Whether F1-C link to gNodeB-CU-CP is configured with cells and used for traffic.";
    type enumeration {
      enum NOT_ACTIVE {
        description "F1-C link is currently not used for traffic.";
        status current {
          yexte:preliminary;
        }
        value 0;
      }
      enum ACTIVE {
        description "F1-C link is currently used for traffic.";
        status current {
          yexte:preliminary;
        }
        value 1;
      }
    }
  }
  typedef enum-StartPrbStrategy {
    description "Mitigate interference strategy that chooses way to allocate PRBs to UEs.";
    type enumeration {
      enum START_LOWER_EDGE {
        description "Mitigate interference strategy that chooses way of allocating PRBs to UEs.\n\nFrom lower frequency band edge, START_LOWER_EDGE is chosen.";
        value 0;
      }
      enum START_HIGHER_EDGE {
        description "Mitigate interference strategy that chooses way of allocating PRBs to UEs.\n\nFrom higher frequency band edge, START_HIGHER_EDGE is chosen.";
        value 1;
      }
      enum RANDOM_START_LOWER_OR_HIGHER {
        description "Mitigate interference strategy that chooses way of allocating PRBs to UEs.\n\nBoth from lower and higher frequency band edges by random for each slot, RANDOM_START_LOWER_OR_HIGHER is chosen.";
        value 2;
      }
      enum RANDOM_START_WITHIN_BAND {
        description "Mitigate interference strategy that chooses way of allocating PRBs to UEs.\n\nFrom random starting point for each slot for interference spreading over the whole band, RANDOM_START_WITHIN_BAND is chosen.";
        value 3;
      }
    }
  }
  typedef enum-TxDirection {
    description "Transmission direction.";
    type enumeration {
      enum DL_AND_UL {
        description "Supports both DL and UL.";
        value 0;
      }
      enum DL {
        description "Supports DL only.";
        value 1;
      }
    }
  }
  typedef enum-CsiRsResourceShifting {
    description "Value for csiRsResourceShifting.";
    type enumeration {
      enum DEACTIVATED {
        description "CSI-RS shifting is not activated.\n\nAll cells use the same CSI-RS resource position.";
        value 0;
      }
      enum ACTIVATED_AUTOMATIC {
        description "Intra-slot CSI-RS resource shifting is activated.\n\nShift is automatically assigned by gNodeB.";
        value 1;
      }
    }
  }
  typedef enum-TddUlDlPatternType {
    description "Defines TDD pattern in terms of downlink, uplink, and special slots.\n\nSlots are indicated with D, S, and U for downlink, special, and uplink slots, respectively.\nFor example, a pattern given as DDSU starts with two downlink slots followed by a special slot and finally a single uplink slot.";
    type enumeration {
      enum TDD_ULDL_PATTERN_00 {
        description "UL/DL pattern is DDSU.";
        value 0;
      }
      enum TDD_ULDL_PATTERN_01 {
        description "UL/DL pattern is DDDSUUDDDD.\n\nCorresponds to LTE UL/DL configuration 2 for SCS 30 kHz.";
        value 1;
      }
      enum TDD_ULDL_PATTERN_02 {
        description "UL/DL pattern is DDDSU.";
        value 2;
      }
      enum TDD_ULDL_PATTERN_03 {
        description "UL/DL pattern is DDDSUDDSUU.";
        value 3;
      }
      enum TDD_ULDL_PATTERN_04 {
        description "UL/DL pattern is DDDDDDDSUU.\n\nCorresponds to LTE UL/DL configuration 2 with frame start offset for SCS 30 kHz.";
        value 4;
      }
    }
  }
  typedef enum-TxPowerState {
    description "DL output power state.";
    type enumeration {
      enum INVALID {
        description "DL output power state is not available.";
        value 0;
      }
      enum STABLE {
        description "DL output power is stable.";
        value 1;
      }
      enum CHANGING {
        description "DL output power changes to reach txPowerRatio.";
        value 2;
      }
    }
  }
  typedef ddt-GNBDU_NRCellDU_ssbPeriodicity {
    type int32 {
      range "5..5 | 10..10 | 20..20 | 40..40 | 80..80 | 160..160";
    }
  }
  typedef ddt-GNBDU_Rrc_beamFailureDetectionTimer {
    type int32 {
      range "1..1 | 2..2 | 3..3 | 4..4 | 5..5 | 6..6 | 8..8 | 10..10";
    }
  }
  typedef ddt-GNBDU_DU5qi_tReassemblyDl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-GNBDU_NRSectorCarrier_longitude {
    type int32 {
      range -180000000..180000000;
    }
  }
  typedef ddt-GNBDU_DU5qi_packetDelayBudgetOffset {
    type int32 {
      range 0..1023;
    }
  }
  typedef ddt-GNBDU_SibTypePws_siPeriodicity {
    type int32 {
      range "8..8 | 16..16 | 32..32 | 64..64 | 128..128 | 256..256 | 512..512";
    }
  }
  typedef ddt-GNBDU_NRSectorCarrier_essScPairId {
    type int64 {
      range 1..9223372036854775807;
    }
  }
  typedef ddt-GNBDU_NRCellDU_ulAvailableCrbs {
    type uint32 {
      range 0..272;
    }
  }
  typedef ddt-GNBDU_GNBDUFunction_gNBDUId {
    type int64 {
      range 0..68719476735;
    }
  }
  typedef ddt-GNBDU_PowerBackoff_powerBackoffThresh {
    type int32 {
      range 0..1000;
    }
  }
  typedef ddt-GNBDU_NRSectorCarrier_maxEirpPsdThresh {
    type int32 {
      range 1..1000;
    }
  }
  typedef ddt-GNBDU_NRSectorCarrier_scaledTransmissionPower {
    type int32;
  }
  typedef ddt-GNBDU_CommonBeamforming_digitalTilt {
    type int32 {
      range -900..900;
    }
  }
  typedef ddt-GNBDU_GNBDUFunction_ulBbCapacityMaxLimit {
    type int32 {
      range 0..65535;
    }
  }
  typedef ddt-GNBDU_SignalingRadioBearer_tPollRetransmitUl {
    type int32 {
      range "5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500 | 800..800 | 1000..1000 | 2000..2000 | 4000..4000";
    }
  }
  typedef ddt-GNBDU_NRCellDU_dftSOfdmPuschStartRsrpThresh {
    type int32 {
      range -156..-29;
    }
  }
  typedef ddt-GNBDU_DU5qi_averagingWindow {
    type int32 {
      range 0..4095;
    }
  }
  typedef ddt-NratCommonLibrary_SliceSelectionAssistInfo_sd {
    type int32 {
      range 0..16777215;
    }
  }
  typedef ddt-GNBDU_NRCellDU_bandListManual {
    type int32 {
      range "1..5 | 7..7 | 8..8 | 12..12 | 14..14 | 18..18 | 20..20 | 25..25 | 26..26 | 28..28 | 29..29 | 30..30 | 34..34 | 38..41 | 48..48 | 50..50 | 51..51 | 65..65 | 66..66 | 70..70 | 71..71 | 74..84 | 86..86 | 89..95 | 257..257 | 258..258 | 260..260 | 261..261";
    }
  }
  typedef ddt-GNBDU_NRCellDU_maxNoOfSrsPortsPreferred {
    type int32 {
      range "1..1 | 2..2 | 4..4";
    }
  }
  typedef ddt-GNBDU_NRCellDU_pointAFrequencyUlFdd {
    type int32;
  }
  typedef ddt-GNBDU_NRCellDU_trsPowerBoosting {
    type int32 {
      range 0..6;
    }
  }
  typedef ddt-NratCommonLibrary_SliceSelectionAssistInfo_sst {
    type int32 {
      range 0..255;
    }
  }
  typedef ddt-GNBDU_CsiRsConfig8P_i12Restriction {
    type string {
      length 0..2;
    }
  }
  typedef ddt-GNBDU_GNBDUFunction_dlBbCapacityTarget {
    type int32 {
      range 75..65535;
    }
  }
  typedef ddt-GNBDU_SignalingRadioBearer_tPollRetransmitDl {
    type int32 {
      range "5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500 | 800..800 | 1000..1000 | 2000..2000 | 4000..4000";
    }
  }
  typedef ddt-GNBDU_DU5qi_rlcSNLength {
    type int32 {
      range "6..6 | 12..12 | 18..18";
    }
  }
  typedef ddt-GNBDU_SignalingRadioBearer_ulMaxRetxThreshold {
    type int32 {
      range "1..1 | 2..2 | 3..3 | 4..4 | 6..6 | 8..8 | 16..16 | 32..32";
    }
  }
  typedef ddt-GNBDU_NRCellDU_nRPCI {
    type int32 {
      range 0..1007;
    }
  }
  typedef ddt-GNBDU_NRCellDU_pZeroNomPucch {
    type int32 {
      range -202..24;
    }
  }
  typedef ddt-GNBDU_Paging_defaultPagingCycle {
    type int32 {
      range "32..32 | 64..64 | 128..128 | 256..256";
    }
  }
  typedef ddt-GNBDU_InterMeLink_linkLatency15minHWM {
    type int32;
  }
  typedef ddt-GNBDU_NRSectorCarrier_txPowerRatio {
    type int32 {
      range 10..100;
    }
  }
  typedef ddt-GNBDU_Rrc_n311 {
    type int32 {
      range "1..1 | 2..2 | 3..3 | 4..4 | 5..5 | 6..6 | 8..8 | 10..10";
    }
  }
  typedef ddt-GNBDU_DU5qi_packetDelayBudget {
    type int32 {
      range 0..1023;
    }
  }
  typedef ddt-GNBDU_PriorityDomainMapping_priorityLevelsList {
    type uint32 {
      range 1..127;
    }
  }
  typedef ddt-GNBDU_Rrc_n310 {
    type int32 {
      range "1..1 | 2..2 | 3..3 | 4..4 | 6..6 | 8..8 | 10..10 | 20..20";
    }
  }
  typedef ddt-GNBDU_NRSectorCarrier_altitude {
    type int32 {
      range -32768..32767;
    }
  }
  typedef ddt-GNBDU_CsiRsConfig32P_i11Restriction {
    type string {
      length 0..8;
    }
  }
  typedef ddt-GNBDU_NRCellDU_endcDlNrQualHyst {
    type int32 {
      range 0..60;
    }
  }
  typedef ddt-GNBDU_QosPriorityMapping_defaultDomain {
    type uint32 {
      range 48..48;
    }
  }
  typedef ddt-GNBDU_NRCellDU_qQualMinOffset {
    type int32 {
      range 1..8;
    }
  }
  typedef ddt-GNBDU_GNBDUFunction_gNBIdLength {
    type int32 {
      range 22..32;
    }
  }
  typedef ddt-GNBDU_NRCellDU_pMax {
    type int32 {
      range -30..26;
    }
  }
  typedef ddt-GNBDU_NRSectorCarrier_noOfRxAntennas {
    type int32 {
      range "0..0 | 1..1 | 2..2 | 4..4 | 8..8";
    }
  }
  typedef ddt-GNBDU_NRSectorCarrier_frequencyDL {
    type int32;
  }
  typedef ddt-GNBDU_NRSectorCarrier_frequencyUL {
    type int32;
  }
  typedef ddt-GNBDU_NRCoverage_radius {
    type int32 {
      range 1..100000;
    }
  }
  typedef ddt-GNBDU_CsiRsConfig8P_i11Restriction {
    type string {
      length 0..4;
    }
  }
  typedef ddt-GNBDU_NRCellDU_pZeroUePuschOffset256Qam {
    type int32 {
      range 0..15;
    }
  }
  typedef ddt-UserLabel {
    description "User-defined label, maximum 128 characters including spaces.";
    type string {
      length 1..128;
    }
  }
  typedef ddt-GNBDU_GNBDUFunction_ulBbCapacityNet {
    type int32 {
      range 0..65535;
    }
  }
  typedef ddt-GNBDU_NRCoverage_openingAngle {
    type int32 {
      range 0..3599;
    }
  }
  typedef ddt-GNBDU_NRCellDU_endcUlNrLowQualThresh {
    type int32 {
      range -40..145;
    }
  }
  typedef ddt-GNBDU_NRSectorCarrier_configuredMaxTxPower {
    type int32 {
      range 0..10000000;
    }
  }
  typedef ddt-GNBDU_NRSectorCarrier_latitude {
    type int32 {
      range -90000000..90000000;
    }
  }
  typedef ddt-GNBDU_CsiRsConfig4P_i11Restriction {
    type string {
      length 0..2;
    }
  }
  typedef ddt-GNBDU_DU5qi_profile5qi {
    type int32 {
      range 0..255;
    }
  }
  typedef ddt-GNBDU_NRCellDU_trsPeriodicity {
    type int32 {
      range "10..10 | 20..20 | 40..40 | 80..80";
    }
  }
  typedef ddt-GNBDU_NRCellDU_fakeInt8SingleRange {
    type int8 {
      range 1..100;
    }
  }
  typedef ddt-GNBDU_NRCellDU_fakeInt8MultiRange {
    type int8 {
     range "-10..-10 | 10..10 | 50..50 | 100..100";
    }
  }

  typedef ddt-GNBDU_NRCellDU_fakeUInt8MultiRange {
      type uint8 {
       range "10..10 | 50..50 | 100..100";
      }
    }

  typedef ddt-GNBDU_NRCellDU_fakeInt16SingleRange {
    type int16 {
     range -500..1000;
    }
  }
  typedef ddt-GNBDU_NRCellDU_fakeInt16MultiRange {
    type int16 {
     range "-100..-100 | 100..100 | 500..500 | 1000..1000";
    }
  }
  typedef ddt-GNBDU_NRCellDU_fakeUInt16SingleRange {
     type uint16 {
      range 1..1000;
     }
  }
  typedef ddt-GNBDU_NRCellDU_fakeUInt16MultiRange {
     type uint16 {
       range "1..1 | 100..100 | 500..500 | 1000..1000";
     }
  }
  typedef ddt-GNBDU_NRCellDU_fakeInt64MultiRange {
    type int64 {
     range "-100000000..-100000000 | 100000000..100000000 | 500000000..500000000 | 100000000000..100000000000";
    }
  }
  typedef ddt-GNBDU_NRCellDU_fakeUInt64SingleRange {
    type uint64 {
      range "100..100000000000";
    }
  }
  typedef ddt-GNBDU_NRCellDU_fakeUInt64MultiRange {
     type uint64 {
      range "100000000..100000000 | 500000000..500000000 | 100000000000..100000000000";
     }
  }
  typedef ddt-GNBDU_NRCellDU_fakeDecimal64SingleRange {
    type decimal64 {
     range -9.5..10.5;
    }
  }
  typedef ddt-GNBDU_NRCellDU_fakeDecimal64MultiRange {
      type decimal64 {
       range "-9.5..-9.5 | 10.5..10.5 | 18446744073709551616000000000000000.09999999999999999999999..18446744073709551616000000000000000.1";
      }
    }

  typedef ddt-GNBDU_NRCellDU_cellLocalId {
    type int32 {
      range 0..16383;
    }
  }
  typedef ddt-GNBDU_InterMeLink_linkLatency24hrsHWM {
    type int32;
  }
  typedef ddt-GNBDU_NRCellDU_siWindowLength {
    type int32 {
      range "5..5 | 10..10 | 20..20 | 40..40 | 80..80 | 160..160 | 320..320 | 640..640 | 1280..1280";
    }
  }
  typedef ddt-GNBDU_GNBDUFunction_gNBId {
    type int64 {
      range 0..4294967295;
    }
  }
  typedef ddt-GNBDU_Beam_ssbPhysicalIndex {
    type int32 {
      range 0..63;
    }
  }
  typedef ddt-GNBDU_NRSectorCarrier_bSChannelBwDL {
    type int32 {
      range "5..5 | 10..10 | 15..15 | 20..20 | 30..30 | 40..40 | 50..50 | 60..60 | 70..70 | 80..80 | 90..90 | 100..100";
    }
  }
  typedef ddt-NratCommonLibrary_PLMNId_mcc {
    type string {
      length 3..3;
    }
  }
  typedef ddt-GNBDU_GNBDUFunction_pwsEtwsPrimaryInd {
    type int32 {
      range 3..16;
    }
  }
  typedef ddt-GNBDU_RpUserPlaneLink_remoteEndPoint {
    type string {
      length 2..39;
    }
  }
  typedef ddt-GNBDU_NRCellDU_pointAFrequencyTdd {
    type int32 {
      range 0..100000000;
    }
  }
  typedef ddt-GNBDU_NRCellDU_ssbDuration {
    type int32 {
      range 1..5;
    }
  }
  typedef ddt-GNBDU_NRCellDU_qQualMin {
    type int32 {
      range -43..-12;
    }
  }
  typedef ddt-GNBDU_NRCellDU_ssbOffset {
    type int32 {
      range 0..159;
    }
  }
  typedef ddt-GNBDU_InterMeLink_linkLatency1minAvg {
    type int32;
  }
  typedef ddt-GNBDU_GNBDUFunction_dlBbCapacityNet {
    type int32 {
      range 0..65535;
    }
  }
  typedef ddt-GNBDU_DU5qi_tReassemblyUl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-GNBDU_NRCellDU_qRxLevMinOffset {
    type int32 {
      range 2..16;
    }
  }
  typedef ddt-GNBDU_NRSectorCarrier_bSChannelBwUL {
    type int32 {
      range "5..5 | 10..10 | 15..15 | 20..20 | 30..30 | 40..40 | 50..50 | 60..60 | 70..70 | 80..80 | 90..90 | 100..100";
    }
  }
  typedef ddt-GNBDU_DataRadioBearer_dlPollPdu {
    type int32 {
      range "4..4 | 8..8 | 16..16 | 32..32 | 64..64 | 128..128 | 256..256 | 512..512 | 1024..1024 | 2048..2048 | 4096..4096 | 6144..6144 | 8192..8192 | 12288..12288 | 16384..16384 | 20480..20480 | 24576..24576 | 28672..28672 | 32768..32768 | 40960..40960 | 49152..49152 | 57344..57344 | 65536..65536";
    }
  }
  typedef ddt-GNBDU_NRSectorCarrier_noOfTxAntennas {
    type int32 {
      range "0..0 | 1..1 | 2..2 | 4..4 | 8..8 | 16..16";
    }
  }
  typedef ddt-GNBDU_NRCellDU_bandList {
    type int32 {
      range 1..1024;
    }
  }
  typedef ddt-GNBDU_NRCellDU_ailgDlPrbLoadLevel {
    type uint32 {
      range 0..100;
    }
  }
  typedef ddt-GNBDU_NRCellDU_ssbPowerBoost {
    type int32 {
      range 0..12;
    }
  }
  typedef ddt-GNBDU_RedundantGNodeB_gNBIdLength {
    type int32 {
      range 22..32;
    }
  }
  typedef ddt-GNBDU_DataRadioBearer_ulPollPdu {
    type int32 {
      range "4..4 | 8..8 | 16..16 | 32..32 | 64..64 | 128..128 | 256..256 | 512..512 | 1024..1024 | 2048..2048 | 4096..4096 | 6144..6144 | 8192..8192 | 12288..12288 | 16384..16384 | 20480..20480 | 24576..24576 | 28672..28672 | 32768..32768 | 40960..40960 | 49152..49152 | 57344..57344 | 65536..65536";
    }
  }
  typedef ddt-GNBDU_NRCellDU_pointAArfcnTdd {
    type int32 {
      range 0..3279165;
    }
  }
  typedef ddt-GNBDU_GNBDUFunction_dlBbCapacityMaxLimit {
    type int32 {
      range 0..65535;
    }
  }
  typedef ddt-GNBDU_NRCellDU_rachPreambleTransMax {
    type int32 {
      range "3..3 | 4..4 | 5..5 | 6..6 | 7..7 | 8..8 | 10..10 | 20..20 | 50..50 | 100..100 | 200..200";
    }
  }
  typedef ddt-GNBDU_NRCellDU_ssbFrequency {
    type int32 {
      range 0..3279165;
    }
  }
  typedef ddt-GNBDU_NRSectorCarrier_arfcnDL {
    type int32 {
      range 0..3279165;
    }
  }
  typedef ddt-GNBDU_SignalingRadioBearer_dlMaxRetxThreshold {
    type int32 {
      range "1..1 | 2..2 | 3..3 | 4..4 | 6..6 | 8..8 | 16..16 | 32..32";
    }
  }
  typedef ddt-GNBDU_NRCellDU_ulMaxMuMimoLayers {
    type int32 {
      range "0..0 | 2..2 | 4..4 | 6..6 | 8..8";
    }
  }
  typedef ddt-GNBDU_NRCellDU_rachRootSequence {
    type int32 {
      range 0..837;
    }
  }
  typedef ddt-GNBDU_SignalingRadioBearer_tReassemblyUl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-GNBDU_DataRadioBearer_tPollRetransmitUl {
    type int32 {
      range "5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500 | 800..800 | 1000..1000 | 2000..2000 | 4000..4000";
    }
  }
  typedef ddt-GNBDU_NRSectorCarrier_arfcnUL {
    type int32 {
      range 0..3279165;
    }
  }
  typedef ddt-GNBDU_NRCellDU_configuredEpsTAC {
    type int32 {
      range 0..65535;
    }
  }
  typedef ddt-GNBDU_AdditionalPLMNInfo_nRTAC {
    type int32 {
      range 0..16777215;
    }
  }
  typedef ddt-GNBDU_NRCellDU_subCarrierSpacing {
    type int32 {
      range "15..15 | 30..30 | 60..60 | 120..120";
    }
  }
  typedef ddt-GNBDU_NRCellDU_endcUlNrQualHyst {
    type int32 {
      range 1..60;
    }
  }
  typedef ddt-GNBDU_NRCellDU_srsPeriodicity {
    type int32 {
      range "5..5 | 10..10 | 20..20 | 40..40 | 80..80";
    }
  }
  typedef ddt-GNBDU_SignalingRadioBearer_tReassemblyDl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-GNBDU_DU5qi_logicalChannelGroupId {
    type int32 {
      range 1..7;
    }
  }
  typedef ddt-GNBDU_NRCellDU_pointAFrequencyDlFdd {
    type int32;
  }
  typedef ddt-GNBDU_PriorityDomainMapping_priorityDomain {
    type int32 {
      range 1..64;
    }
  }
  typedef ddt-GNBDU_NRCellDU_nCGI {
    type int64 {
      range 0..1152921504606846975;
    }
  }
  typedef ddt-GNBDU_DataRadioBearer_tPollRetransmitDl {
    type int32 {
      range "5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500 | 800..800 | 1000..1000 | 2000..2000 | 4000..4000";
    }
  }
  typedef ddt-GNBDU_TermPointToGNBCUCP_ipv6Address {
    type string {
      length 2..39;
    }
  }
  typedef ddt-GNBDU_NRCellDU_typeISinglePanelRiRestriction {
    type uint8 {
      range 1..15;
    }
  }
  typedef ddt-GNBDU_CommonBeamforming_digitalPan {
    type int32 {
      range -900..900;
    }
  }
  typedef ddt-GNBDU_TermPointToGNBCUCP_ipv4Address {
    type string {
      length 7..15;
    }
  }
  typedef ddt-GNBDU_SchedulingProfile_relativePriority {
    type int32 {
      range "1..1 | 2..2 | 4..4 | 8..8 | 16..16 | 32..32 | 64..64 | 128..128 | 256..256";
    }
  }
  typedef ddt-GNBDU_CsiRsConfig32P_i12Restriction {
    type string {
      length 0..4;
    }
  }
  typedef ddt-GNBDU_Rrc_beamFailureInstanceMaxCount {
    type int32 {
      range "1..1 | 2..2 | 3..3 | 4..4 | 5..5 | 6..6 | 8..8 | 10..10";
    }
  }
  typedef ddt-GNBDU_PowerBackoff_powerBackoffAvgTime {
    type int32 {
      range 30..1800;
    }
  }
  typedef ddt-GNBDU_DU5qi_maxDataBurstVolume {
    type int32 {
      range 0..4095;
    }
  }
  typedef ddt-GNBDU_CsiRsConfig2P_aRestriction {
    type string {
      length 0..2;
    }
  }
  typedef ddt-GNBDU_NRCellDU_qRxLevMin {
    type int32 {
      range -140..-44;
    }
  }
  typedef ddt-GNBDU_ResourcePartition_resourcePartitionName {
    type string {
      length 1..255;
    }
  }
  typedef ddt-GNBDU_SibType_siPeriodicity {
    type int32 {
      range "8..8 | 16..16 | 32..32 | 64..64 | 128..128 | 256..256 | 512..512";
    }
  }
  typedef ddt-GNBDU_NRCellDU_ailgPdcchLoadLevel {
    type uint32 {
      range 0..100;
    }
  }
  typedef ddt-GNBDU_NRCellDU_dlStartCrb {
    type uint32 {
      range 0..272;
    }
  }
  typedef ddt-GNBDU_RedundantGNodeB_switchbackTimer {
    type int32 {
      range 0..65535;
    }
  }
  typedef ddt-GNBDU_NRCellDU_ssbSubCarrierSpacing {
    type int32 {
      range "15..15 | 30..30 | 120..120 | 240..240";
    }
  }
  typedef ddt-GNBDU_DataRadioBearer_dlMaxRetxThreshold {
    type int32 {
      range "1..1 | 2..2 | 3..3 | 4..4 | 6..6 | 8..8 | 16..16 | 32..32";
    }
  }
  typedef ddt-GNBDU_CsiRsConfig16P_i11Restriction {
    type string {
      length 0..8;
    }
  }
  typedef ddt-GNBDU_QciProfileEndcConfig_tReassemblyDl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-NratCommonLibrary_PLMNId_mnc {
    type string {
      length 2..3;
    }
  }
  typedef ddt-GNBDU_NRCellDU_ulStartCrb {
    type uint32 {
      range 0..272;
    }
  }
  typedef ddt-GNBDU_Rrc_t301 {
    type int32 {
      range "100..100 | 200..200 | 300..300 | 400..400 | 600..600 | 1000..1000 | 1500..1500 | 2000..2000";
    }
  }
  typedef ddt-GNBDU_Rrc_t300 {
    type int32 {
      range "100..100 | 200..200 | 300..300 | 400..400 | 600..600 | 1000..1000 | 1500..1500 | 2000..2000";
    }
  }
  typedef ddt-GNBDU_NRCellDU_dlAvailableCrbs {
    type uint32 {
      range 0..272;
    }
  }
  typedef ddt-GNBDU_TermPointToGNBCUCP_gNBCUName {
    type string {
      length 1..150;
    }
  }
  typedef ddt-GNBDU_DataRadioBearer_tStatusProhibitDl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500 | 800..800 | 1000..1000 | 1200..1200 | 1600..1600 | 2000..2000 | 2400..2400";
    }
  }
  typedef ddt-GNBDU_DU5qi_priorityLevel {
    type int32 {
      range 1..127;
    }
  }
  typedef ddt-GNBDU_RedundantGNodeB_gNBId {
    type int64 {
      range 0..4294967295;
    }
  }
  typedef ddt-GNBDU_NRCellDU_dlMaxMuMimoLayers {
    type int32 {
      range "0..0 | 2..2 | 4..4 | 6..6 | 8..8 | 10..10 | 12..12 | 14..14 | 16..16";
    }
  }
  typedef ddt-GNBDU_CustomComBfwWideBeam_antennaNo {
    type int32 {
      range 0..63;
    }
  }
  typedef ddt-GNBDU_ExtGNBDUPartnerFunction_gNBDUId {
    type int64 {
      range 0..68719476735;
    }
  }
  typedef ddt-GNBDU_NRCoverage_bearing {
    type int32 {
      range 0..3599;
    }
  }
  typedef ddt-GNBDU_QciProfileEndcConfig_tReassemblyUl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 110..110 | 120..120 | 130..130 | 140..140 | 150..150 | 160..160 | 170..170 | 180..180 | 190..190 | 200..200";
    }
  }
  typedef ddt-GNBDU_NRPolygonCorner_longitude {
    type int32 {
      range -180000000..180000000;
    }
  }
  typedef ddt-GNBDU_DataRadioBearer_tStatusProhibitUl {
    type int32 {
      range "0..0 | 5..5 | 10..10 | 15..15 | 20..20 | 25..25 | 30..30 | 35..35 | 40..40 | 45..45 | 50..50 | 55..55 | 60..60 | 65..65 | 70..70 | 75..75 | 80..80 | 85..85 | 90..90 | 95..95 | 100..100 | 105..105 | 110..110 | 115..115 | 120..120 | 125..125 | 130..130 | 135..135 | 140..140 | 145..145 | 150..150 | 155..155 | 160..160 | 165..165 | 170..170 | 175..175 | 180..180 | 185..185 | 190..190 | 195..195 | 200..200 | 205..205 | 210..210 | 215..215 | 220..220 | 225..225 | 230..230 | 235..235 | 240..240 | 245..245 | 250..250 | 300..300 | 350..350 | 400..400 | 450..450 | 500..500 | 800..800 | 1000..1000 | 1200..1200 | 1600..1600 | 2000..2000 | 2400..2400";
    }
  }
  typedef ddt-GNBDU_NRSectorCarrier_maxTransmissionPower {
    type int32;
  }
  typedef ddt-GNBDU_Rrc_t304 {
    type int32 {
      range "50..50 | 100..100 | 150..150 | 200..200 | 500..500 | 1000..1000 | 2000..2000 | 10000..10000";
    }
  }
  typedef ddt-GNBDU_ExtGNBDUPartnerFunction_gNBIdLength {
    type int32 {
      range 22..32;
    }
  }
  typedef ddt-GNBDU_GNBDUFunction_gNBDUName {
    type string {
      length 1..150;
    }
  }
  typedef ddt-GNBDU_NRPolygonCorner_latitude {
    type int32 {
      range -90000000..90000000;
    }
  }
  typedef ddt-GNBDU_Rrc_t310 {
    type int32 {
      range "0..0 | 50..50 | 100..100 | 200..200 | 500..500 | 1000..1000 | 2000..2000 | 4000..4000 | 6000..6000";
    }
  }
  typedef ddt-GNBDU_DU5qi_dscp {
    type int32 {
      range 0..63;
    }
  }
  typedef ddt-GNBDU_Rrc_t311 {
    type int32 {
      range "1000..1000 | 3000..3000 | 5000..5000 | 10000..10000 | 15000..15000 | 20000..20000 | 30000..30000";
    }
  }
  typedef ddt-GNBDU_NRCellDU_nRTAC {
    type int32 {
      range 0..16777215;
    }
  }
  typedef ddt-GNBDU_CsiRsConfig16P_i12Restriction {
    type string {
      length 0..2;
    }
  }
  typedef ddt-GNBDU_NRCellDU_csiRsPeriodicity {
    type int32 {
      range "10..10 | 20..20 | 40..40 | 80..80 | 160..160 | 320..320 | 640..640";
    }
  }
  typedef ddt-GNBDU_NRCellDU_essMbsfnSubframeConfig {
    type uint32 {
      range "9440512..9440512 | 9441024..9441024 | 12584960..12584960";
    }
  }
  typedef ddt-GNBDU_DataRadioBearer_ulMaxRetxThreshold {
    type int32 {
      range "1..1 | 2..2 | 3..3 | 4..4 | 6..6 | 8..8 | 16..16 | 32..32";
    }
  }
  typedef ddt-GNBDU_NRCellDU_pZeroNomSrs {
    type int32 {
      range -202..24;
    }
  }
  typedef ddt-GNBDU_RpUserPlaneLink_localEndPoint {
    type string {
      length 2..39;
    }
  }
  typedef ddt-GNBDU_NRCellDU_rachPreambleRecTargetPower {
    type int32 {
      range -202..-60;
    }
  }
  typedef ddt-GNBDU_Paging_nS {
    type int32 {
      range "1..1 | 2..2 | 4..4";
    }
  }
  typedef ddt-GNBDU_ExtGNBDUPartnerFunction_gNBId {
    type int64 {
      range 0..4294967295;
    }
  }
  typedef ddt-GNBDU_CustomComBfwWideBeam_phase {
    type int32 {
      range 0..359;
    }
  }
  typedef ddt-GNBDU_NRCellDU_cellRange {
    type int32 {
      range 1..100000;
    }
  }
  typedef ddt-GNBDU_CustomComBfwWideBeam_amplitude {
    type int32 {
      range 0..100;
    }
  }
  typedef ddt-GNBDU_NRCellDU_pZeroNomPuschGrant {
    type int32 {
      range -202..24;
    }
  }
  typedef ddt-GNBDU_NRSectorCarrier_txPowerChangeRate {
    type int32 {
      range 1..10;
    }
  }
  typedef ddt-GNBDU_NRCellDU_endcDlNrLowQualThresh {
    type int32 {
      range -40..40;
    }
  }
  typedef ddt-GNBDU_NRSectorCarrier_essScLocalId {
    type int32 {
      range 1..99999;
    }
  }
  grouping struct-NRCoverage {
    description "Transmission point coverage area used for UE positioning.\n\nDefined by bearing, opening angle and radius.";
    leaf openingAngle {
      description "Opening Angle of the Transmission Point area.\nExpressed in deci-degree, 0 means an omnidirectional antenna covering 3600 deci-degree (360 degree).";
      type erienmnrmgnbdu:ddt-GNBDU_NRCoverage_openingAngle;
      mandatory true;
    }
    leaf bearing {
      description "Bearing of the Transmission Point area.\nExpressed in deci-degree clockwise from north.";
      type erienmnrmgnbdu:ddt-GNBDU_NRCoverage_bearing;
      mandatory true;
    }
    leaf radius {
      description "Maximum distance from the transmission point.\nMaximum distance where a connection to a UE can be set up or maintained, or both.";
      type erienmnrmgnbdu:ddt-GNBDU_NRCoverage_radius;
      mandatory true;
    }
  } // end 'grouping struct-NRCoverage'
  grouping struct-NRPolygonCorner {
    description "Corner of Polygon that models transmission point coverage area.";
    leaf latitude {
      description "Latitude of a coverage polygon corner point.\nPositive values are used for north and negative values for south.";
      type erienmnrmgnbdu:ddt-GNBDU_NRPolygonCorner_latitude;
      mandatory true;
    }
    leaf longitude {
      description "Longitude of a coverage polygon corner point.\nPositive values are used for the east and negative values for west.";
      type erienmnrmgnbdu:ddt-GNBDU_NRPolygonCorner_longitude;
      mandatory true;
    }
  } // end 'grouping struct-NRPolygonCorner'
  grouping struct-CsiRsConfig16P {
    description "Container for attributes specific to 16-port CSI-RS configuration.\n\nIncludes attributes related to the port-to-antenna mapping, and codebook-related parameters including subset restrictions.";
    leaf i11Restriction {
      description "Codebook subset restriction applicable to i11 PMI component for 16-port CSI feedback.\nValue of bit at index i11 can be set to 0 = disabled or to 1 for all other options. Least significant bit has index i11 = 0. Expressed as a hexadecimal string.";
      yexte:dependencies "If csiRsConfig16P/csiRsControl16Ports is set to EIGHT_ONE_N1AZ or EIGHT_ONE_N1EL then value of csiRsConfig16P/i11Restriction must be a hexadecimal string of eight digits.\nIf csiRsConfig16P/csiRsControl16Ports is set to FOUR_TWO_N1AZ or FOUR_TWO_N1EL, then value of csiRsConfig16P/i11Restriction must be a hexadecimal string of four digits.\nIf csiRsConfig16P/csiRsControl16Ports is set to OFF, then value of csiRsConfig16P/i11Restriction must be an empty string.";
      type erienmnrmgnbdu:ddt-GNBDU_CsiRsConfig16P_i11Restriction;
      default "";
    }
    leaf i12Restriction {
      description "Codebook subset restriction applicable to i12 PMI component for 16-port CSI feedback.\nValue of bit at index i12 can be set to 0 = disabled or to 1 for all other options. Least significant bit has index i12 = 0. Expressed as a hexadecimal string.";
      yexte:dependencies "If csiRsConfig16P/csiRsControl16Ports is set to EIGHT_ONE_N1AZ, EIGHT_ONE_N1EL, or OFF, then value of csiRsConfig16P/i12Restriction must be an empty string.\nIf csiRsControl16Ports is set to FOUR_TWO_N1AZ or FOUR_TWO_N1EL, then value of csiRsConfig16P/i12Restriction must be a hexadecimal string of two digits.";
      type erienmnrmgnbdu:ddt-GNBDU_CsiRsConfig16P_i12Restriction;
      default "";
    }
    leaf csiRsControl16Ports {
      description "Emission of 16-port CSI-RS and selected associated CSI feedback settings.\nHas an impact on port-to-antenna mapping for CSI-RS.\nApplies only to cells based on radios with at least 16 transmit branches. Otherwise, ignored.";
      yexte:dependencies "If secondaryCellOnly is false, csiRsControl16Ports can be set to a value other than OFF only if csiRsControl8Ports is also set to a value other than OFF and csiRsControl32Ports is set to OFF.";
      type erienmnrmgnbdu:enum-CsiRsControl16Ports;
      default OFF;
    }
  } // end 'grouping struct-CsiRsConfig16P'
  grouping struct-PLMNId {
    description "PLMN Identity consisting of Mobile Country Code (MCC) and Mobile Network Code (MNC).";
    leaf mnc {
      description "The Mobile Network Code (MNC) identifies home PLMN of mobile subscription.\nMNC consists of two or three decimal digits. For example, MNC of 001 is not same as MNC of 01.\nAs default value, use 01.\nAllowed values: [0-9][0-9][0-9]|[0-9][0-9]";
      type erienmnrmgnbdu:ddt-NratCommonLibrary_PLMNId_mnc;
      mandatory true;
    }
    leaf mcc {
      description "The Mobile Country Code (MCC) identifies uniquely domicile country of mobile subscriber.\nMCC consists of three decimal digits. The first digit of MCC identifies geographic region. (Values 1 and 8 in the first digit are not allowed.)\nAs default value, use 001.\nAllowed values: [02345679][0-9][0-9]";
      type erienmnrmgnbdu:ddt-NratCommonLibrary_PLMNId_mcc;
      mandatory true;
    }
  } // end 'grouping struct-PLMNId'
  grouping struct-UlCalibrationDataRO {
    description "Uplink antenna calibration information.";
    leaf ulCalibrationStatus {
      description "Describes current uplink antenna calibration status.";
      yexte:dependencies "If sequence ulCalibrationSupportedMethods is empty, value of ulCalibrationStatus is 0 (INACTIVE).";
      type erienmnrmgnbdu:enum-UlCalibrationStatus;
      mandatory true;
    }
    leaf-list ulCalibrationSupportedMethods {
      min-elements 0;
      max-elements 2;
      description "Describes which type of uplink antenna calibration is supported.\nAn empty list means there is no support.";
      type erienmnrmgnbdu:enum-UlCalibrationMethod;
    }
    leaf ulCalibrationActiveMethod {
      description "Describes which uplink antenna calibration method is active (if any).";
      yexte:dependencies "If sequence ulCalibrationSupportedMethods is empty, value of ulCalibrationActiveMethod is 0 (NONE).";
      type erienmnrmgnbdu:enum-UlCalibrationMethod;
      mandatory true;
    }
  } // end 'grouping struct-UlCalibrationDataRO'
  grouping struct-DlCalibrationDataRO {
    description "Downlink antenna calibration information.";
    leaf-list dlCalibrationSupportedMethods {
      min-elements 0;
      max-elements 2;
      description "Describes which type of downlink antenna calibration is supported.\nAn empty list means there is no support.";
      type erienmnrmgnbdu:enum-DlCalibrationMethod;
    }
    leaf dlCalibrationStatus {
      description "Describes current downlink antenna calibration status.";
      yexte:dependencies "If sequence dlCalibrationSupportedMethods is empty, value of dlCalibrationStatus is 0 (INACTIVE).";
      type erienmnrmgnbdu:enum-DlCalibrationStatus;
      mandatory true;
    }
    leaf dlCalibrationActiveMethod {
      description "Describes which downlink antenna calibration method is active (if any).";
      yexte:dependencies "If sequence dlCalibrationSupportedMethods is empty, value of dlCalibrationActiveMethod is 0 (NONE).";
      type erienmnrmgnbdu:enum-DlCalibrationMethod;
      mandatory true;
    }
  } // end 'grouping struct-DlCalibrationDataRO'
  grouping struct-CustomComBfwWideBeam {
    description "Amplitude and phase for each antenna for custom beamforming weights of downlink common channels.";
    leaf phase {
      description "Phase for an antenna for custom beamforming weights of downlink common channels.";
      type erienmnrmgnbdu:ddt-GNBDU_CustomComBfwWideBeam_phase;
      mandatory true;
    }
    leaf amplitude {
      description "Amplitude for an antenna for custom beamforming weights of downlink common channels.";
      type erienmnrmgnbdu:ddt-GNBDU_CustomComBfwWideBeam_amplitude;
      mandatory true;
    }
    leaf antennaNo {
      description "Antenna port number.";
      yexte:dependencies "Must be unique among all structs in the sequence attribute.";
      type erienmnrmgnbdu:ddt-GNBDU_CustomComBfwWideBeam_antennaNo;
      mandatory true;
    }
  } // end 'grouping struct-CustomComBfwWideBeam'
  grouping struct-CsiRsConfig2P {
    description "Container for attributes specific to 2-port CSI-RS configuration.\n\nAttributes related to port-to-antenna mapping and codebook-related parameters including subset restrictions.";
    leaf aRestriction {
      description "Codebook subset restriction applicable to bit sequence a for 2-port CSI feedback.\nValue of bit at the bit sequence a can be set to 0 = disabled or to 1 for all other options. Expressed as a hexadecimal string.";
      yexte:dependencies "If CsiRsConfig2P::csiRsControl2Ports is set to ON, then value of CsiRsConfig2P::aRestriction must be a hexadecimal string of two digits.\nIf CsiRsConfig2P::csiRsControl2Ports is set to OFF, then value of CsiRsConfig2P::aRestriction must be an empty string.";
      type erienmnrmgnbdu:ddt-GNBDU_CsiRsConfig2P_aRestriction;
      default 3F;
    }
    leaf csiRsControl2Ports {
      description "Emission of 2-port CSI-RS and selected associated CSI feedback settings.\nHas impact on port-to-antenna mapping for CSI-RS.\nApplies only to cells based on radios with two transmit branches. Otherwise, ignored.";
      yexte:dependencies "If CsiRsConfig2P::csiRsControl2Ports is set to ON, then value of CsiRsConfig2P::aRestriction must be a hexadecimal string of two digits.\nIf CsiRsConfig2P::csiRsControl2Ports is set to OFF, then value of CsiRsConfig2P::aRestriction must be an empty string.";
      type erienmnrmgnbdu:enum-CsiRsControl2Ports;
      default ON;
    }
  } // end 'grouping struct-CsiRsConfig2P'
  grouping struct-SibTypePws {
    description "Information for SI message acquisition.";
    leaf siPeriodicity {
      description "Periodicity of the SI-message in radio frames.\n1 radio frame = 10 ms.";
      type erienmnrmgnbdu:ddt-GNBDU_SibTypePws_siPeriodicity;
      default 16;
    }
    leaf siBroadcastStatus {
      description "Broadcast status of a SI-message.";
      type erienmnrmgnbdu:enum-SiBroadcastStatus;
      default BROADCASTING;
    }
  } // end 'grouping struct-SibTypePws'
  grouping struct-CsiRsConfig32P {
    description "Container for attributes specific to 32-port CSI-RS configuration.\n\nIncludes attributes related to the port-to-antenna mapping, and codebook-related parameters including subset restrictions.";
    leaf i11Restriction {
      description "Codebook subset restriction applicable to i11 PMI component for 32-port CSI feedback.\nValue of bit at index i11 can be set to 0 = disabled or to 1 for all other options. Least significant bit has index i11 = 0. Expressed as a hexadecimal string.";
      yexte:dependencies "If csiRsConfig32P/csiRsControl32Ports is set to EIGHT_TWO_N1AZ or EIGHT_TWO_N1EL, then value of csiRsConfig32P/i11Restriction must be a hexadecimal string of eight digits.\nIf csiRsConfig32P/csiRsControl32Ports is set to FOUR_FOUR, then value of csiRsConfig32P/i11Restriction must be a hexadecimal string of four digits.\nIf csiRsConfig32P/csiRsControl32Ports is set to OFF, then value of csiRsConfig32P/i11Restriction must be an empty string.";
      type erienmnrmgnbdu:ddt-GNBDU_CsiRsConfig32P_i11Restriction;
      default "";
    }
    leaf i12Restriction {
      description "Codebook subset restriction applicable to i12 PMI component for 32-port CSI feedback.\nValue of bit at index i12 can be set to 0 = disabled or to 1 for all other options. Least significant bit has index i12 = 0. Expressed as a hexadecimal string.";
      yexte:dependencies "If csiRsConfig32P/csiRsControl32Ports is set to EIGHT_TWO_N1AZ or EIGHT_TWO_N1EL, then value of csiRsConfig32P/i12Restriction must be a hexadecimal string of two digits.\nIf csiRsConfig32P/csiRsControl32Ports is set to FOUR_FOUR, then value of csiRsConfig32P/i12Restriction must be a hexadecimal string of four digits.\nIf csiRsConfig32P/csiRsControl32Ports is set to OFF, then value of csiRsConfig32P/i12Restriction must be an empty string.";
      type erienmnrmgnbdu:ddt-GNBDU_CsiRsConfig32P_i12Restriction;
      default "";
    }
    leaf csiRsControl32Ports {
      description "Emission of 32-port CSI-RS and selected associated CSI feedback settings.\nHas an impact on port-to-antenna mapping for CSI-RS.\nApplies only to cells based on radios with at least 32 transmit branches. Otherwise, ignored.";
      yexte:dependencies "If secondaryCellOnly is false, csiRsControl32Ports can be set to a value other than OFF only if csiRsControl8Ports is also set to a value other than OFF and csiRsControl16Ports is set to OFF.";
      type erienmnrmgnbdu:enum-CsiRsControl32Ports;
      default OFF;
    }
  } // end 'grouping struct-CsiRsConfig32P'
  grouping struct-CsiRsConfig4P {
    description "Container for attributes specific to 4-port CSI-RS configuration.\n\nAttributes related to port-to-antenna mapping and codebook-related parameters including subset restrictions.";
    leaf csiRsControl4Ports {
      description "Emission of 4-port CSI-RS and selected associated CSI feedback settings.\nHas impact on port-to-antenna mapping for CSI-RS.\nApplies only to cells based on radios with four transmit branches. Otherwise, ignored.";
      yexte:dependencies "If CsiRsConfig4P::csiRsControl4Ports is set to TWO_ONE, then value of CsiRsConfig4P::i11Restriction must be a hexadecimal string of two digits.\nIf CsiRsConfig4P::csiRsControl4Ports is set to OFF, then value of CsiRsConfig4P::i11Restriction must be an empty string.";
      type erienmnrmgnbdu:enum-CsiRsControl4Ports;
      default TWO_ONE;
    }
    leaf i11Restriction {
      description "Codebook subset restriction applicable to i11 PMI component for 4-port CSI feedback.\nValue of bit at index i11 can be 0 = disabled or 1 = all other options. Least significant bit has index i11 = 0. Expressed as hexadecimal string.";
      yexte:dependencies "If CsiRsConfig4P::csiRsControl4Ports is set to TWO_ONE, then value of CsiRsConfig4P::i11Restriction must be a hexadecimal string of two digits.\nIf CsiRsConfig4P::csiRsControl4Ports is set to OFF, then value of CsiRsConfig4P::i11Restriction must be an empty string.";
      type erienmnrmgnbdu:ddt-GNBDU_CsiRsConfig4P_i11Restriction;
      default FF;
    }
  } // end 'grouping struct-CsiRsConfig4P'
  grouping struct-SibType {
    description "Information for SI message acquisition.";
    leaf siPeriodicity {
      description "Periodicity of the SI-message in radio frames.\n1 radio frame = 10 ms.";
      type erienmnrmgnbdu:ddt-GNBDU_SibType_siPeriodicity;
      default 64;
    }
    leaf siBroadcastStatus {
      description "Broadcast status of a SI-message.";
      type erienmnrmgnbdu:enum-SiBroadcastStatus;
      default BROADCASTING;
    }
  } // end 'grouping struct-SibType'
  grouping struct-SliceSelectionAssistInfo {
    description "Single Network Slice Selection Assistance Information (S-NSSAI).";
    leaf sd {
      description "Slice Differentiator (SD).\nIf it is not associated with SST, SD value can be set to 16777215.";
      type erienmnrmgnbdu:ddt-NratCommonLibrary_SliceSelectionAssistInfo_sd;
      mandatory true;
    }
    leaf sst {
      description "Slice/Service Type (SST).\nValues 0 to 127 belong to standardized SST range and are defined in 3GPP TS 23.501. Values 128 to 255 belong to operator-specific range.";
      type erienmnrmgnbdu:ddt-NratCommonLibrary_SliceSelectionAssistInfo_sst;
      mandatory true;
    }
  } // end 'grouping struct-SliceSelectionAssistInfo'
  grouping struct-CsiRsConfig8P {
    description "Container for attributes specific to 8-port CSI-RS configuration.\n\nIncludes attributes related to the port-to-antenna mapping, and codebook-related parameters including subset restrictions.";
    leaf csiRsControl8Ports {
      description "Emission of 8-port CSI-RS and selected associated CSI feedback settings.\nHas an impact on port-to-antenna mapping for CSI-RS.\nApplies only to cells based on radios with at least eight transmit branches. Otherwise, ignored.";
      yexte:dependencies "If secondaryCellOnly is false, csiRsControl8Ports has to be set to a value other than OFF in cells based on radios with at least 8 transmit branches.";
      type erienmnrmgnbdu:enum-CsiRsControl8Ports;
      default FOUR_ONE_N1AZ;
    }
    leaf i11Restriction {
      description "Codebook subset restriction applicable to i11 PMI component for 8-port CSI feedback.\nValue of bit at index i11 can be set to 0 = disabled or to 1 for all other options. Least significant bit has index i11 = 0. Expressed as a hexadecimal string.";
      yexte:dependencies "If csiRsConfig8P/csiRsControl8Ports is set to FOUR_ONE_N1AZ or FOUR_ONE_N1EL, then value of csiRsConfig8P/i11Restriction must be a hexadecimal string of four digits.\nIf csiRsConfig8P/i11Restriction is set to TWO_TWO, then value of csiRsConfig8P/i11Restriction must be a hexadecimal string of two digits.\nIf csiRsConfig8P/csiRsControl8Ports is set to OFF, then value of csiRsConfig8P/i11Restriction must be an empty string.";
      type erienmnrmgnbdu:ddt-GNBDU_CsiRsConfig8P_i11Restriction;
      default FFFF;
    }
    leaf i12Restriction {
      description "Codebook subset restriction applicable to i12 PMI component for 8-port CSI feedback.\nValue of bit at index i12 can be set to 0 = disabled or to 1 for all other options. Least significant bit has index i12 = 0. Expressed as a hexadecimal string.";
      yexte:dependencies "If csiRsConfig8P/csiRsControl8Ports is set to FOUR_ONE_N1AZ, FOUR_ONE_N1EL, or OFF, then value of csiRsConfig8P/i12Restriction must be an empty string.\nIf csiRsConfig8P/csiRsControl8Ports is set to TWO_TWO, then value of csiRsConfig8P/i12Restriction must be a hexadecimal string of two digits.";
      type erienmnrmgnbdu:ddt-GNBDU_CsiRsConfig8P_i12Restriction;
      default "";
    }
  } // end 'grouping struct-CsiRsConfig8P'
  grouping moc-LocalIpEndpoint-keys {
    description "Key(s) for MOC LocalIpEndpoint";
    leaf id {
      erienmyext:no-notification;
      description "The value component of the RDN.";
      mandatory true;
      yexte:ecim-name localIpEndpointId;
      type string;
    }
  } // end 'grouping moc-LocalIpEndpoint-keys'
  grouping moc-LocalIpEndpoint {
    description "Local transport network endpoint for user plane interface.";
    leaf-list addressRef {
      min-elements 1;
      max-elements 2;
      description "Reference to AddressIPv4 or AddressIPv6 MO instance.\nMust be unique among LocalIpEndpoint MO instances under EndpointResource. Dual stack is not supported, only one IP address can be referenced.";
      yexte:takes-effect "Node restart";
      erienmyext:enm-type MOREF;
      type string;
    }
    leaf-list interfaceList {
      min-elements 1;
      max-elements 2;
      description "List of user plane interfaces that use the referenced AddressIPv4 or AddressIPv6.\nAllowed value: F1.\nInterface must be unique across LocalIpEndpoints under EndpointResource.";
      yexte:takes-effect "Node restart";
      type erienmnrmgnbdu:enum-InterfaceName;
    }
  } // end 'grouping moc-LocalIpEndpoint'
  grouping moc-RadioBearerTable-keys {
    description "Key(s) for MOC RadioBearerTable";
    leaf id {
      erienmyext:no-notification;
      description "The value component of the RDN.";
      mandatory true;
      yexte:ecim-name radioBearerTableId;
      type string;
    }
  } // end 'grouping moc-RadioBearerTable-keys'
  grouping moc-RadioBearerTable {
    description "Container for radio bearer configurations.\n\nThe RDN of this MO is RadioBearerTable=1.";
  } // end 'grouping moc-RadioBearerTable'
  grouping moc-RedundantGNodeB-keys {
    description "Key(s) for MOC RedundantGNodeB";
    leaf id {
      status current {
        yexte:preliminary;
      }
      erienmyext:no-notification;
      description "The value component of the RDN.";
      mandatory true;
      yexte:ecim-name redundantGNodeBId;
      type string;
    }
  } // end 'grouping moc-RedundantGNodeB-keys'
  grouping moc-RedundantGNodeB {
    description "Represents redundant gNodeB-DU function.\n\nUsed when more than one gNodeB-CU-CP needs to be defined.";
    leaf activeF1Link {
      status current {
        yexte:preliminary;
      }
      config false;
      description "Active F1-C link used for traffic towards gNodeB-CU-CP.";
      notife:notifiable-state-data true;
      type erienmnrmgnbdu:enum-LinkActive;
    }
    leaf switchbackTimer {
      status current {
        yexte:preliminary;
      }
      description "Switchback time to primary F1-C link.\nIf empty, no switchback to primary link is initiated.\nIf set to any value between 0 and 65535, switchback is initiated to primary link after the number of seconds set as value.";
      yexte:disturbances "Changing this attribute can cause loss of traffic.";
      type erienmnrmgnbdu:ddt-GNBDU_RedundantGNodeB_switchbackTimer;
      default 0;
    }
    leaf gNBId {
      status current {
        yexte:preliminary;
      }
      description "Identity of redundant gNodeB within a PLMN.";
      mandatory true;
      yexte:takes-effect "Node restart";
      yexte:dependencies "The gNBId must be equal or less than 2^gNBIdLength - 1.";
      type erienmnrmgnbdu:ddt-GNBDU_RedundantGNodeB_gNBId;
    }
    leaf gNBIdLength {
      status current {
        yexte:preliminary;
      }
      description "Length of gNBId bit string representation.";
      yexte:dependencies "The gNBId must be equal or less than 2^gNBIdLength - 1.";
      type erienmnrmgnbdu:ddt-GNBDU_RedundantGNodeB_gNBIdLength;
      default 22;
    }
  } // end 'grouping moc-RedundantGNodeB'
  grouping moc-Rrc-keys {
    description "Key(s) for MOC Rrc";
    leaf id {
      erienmyext:no-notification;
      description "The value component of the RDN.";
      mandatory true;
      yexte:ecim-name rrcId;
      type string;
    }
  } // end 'grouping moc-Rrc-keys'
  grouping moc-Rrc {
    description "Manageable RRC protocol characteristics.\n\nThe RDN of this MO is Rrc=1.\n";
    leaf t301 {
      description "Timer t301.\nUE timer to supervise response to RRC Connection Reestablishment Request during radio connection re-establishment procedure.\nUE returns to idle mode and optionally starts to reconnect over NAS when timer expires.\nProvided to UE by SIB1.";
      yexte:takes-effect "Next cell unlock";
      type erienmnrmgnbdu:ddt-GNBDU_Rrc_t301;
      default 400;
    }
    leaf n310 {
      description "Maximum number of consecutive out of sync indications received from lower layers.\nProvided to UE by SIB1.\nFor EN-DC, provided to UE by SCG radio configuration.";
      yexte:takes-effect "Next cell unlock";
      type erienmnrmgnbdu:ddt-GNBDU_Rrc_n310;
      default 20;
    }
    leaf t304 {
      description "Timer t304.\nWaiting time for successful completion of random access.\nFor EN-DC, provided to UE by SCG radio configuration.";
      yexte:takes-effect "New connection";
      type erienmnrmgnbdu:ddt-GNBDU_Rrc_t304;
      default 1000;
    }
    leaf n311 {
      description "Maximum number of consecutive in-sync indications received from lower layers.\nProvided to UE by SIB1.\nFor EN-DC, provided to UE by SCG radio configuration.";
      yexte:takes-effect "Next cell unlock";
      type erienmnrmgnbdu:ddt-GNBDU_Rrc_n311;
      default 1;
    }
    leaf beamFailureInstanceMaxCount {
      status obsolete {
        yexte:status-information "Since 20.Q4. Planned to be removed.";
      }
      description "Number of beam failure events after which UE triggers beam failure recovery.\nValue corresponds to number of beam failure instances.";
      yexte:takes-effect "Next cell unlock";
      type erienmnrmgnbdu:ddt-GNBDU_Rrc_beamFailureInstanceMaxCount;
      default 10;
    }
    leaf t300 {
      description "UE timer to supervise response to RRC Connection Request.\nProvided to UE by SIB1.";
      yexte:takes-effect "Next cell unlock";
      type erienmnrmgnbdu:ddt-GNBDU_Rrc_t300;
      default 1000;
    }
    leaf t311 {
      description "Timer t311.\nUE timer triggered at radio link failure. UE tries to re-establish radio connection with one of following options:\n- Performing RRC Connection Reestablishment.\n- Finding a suitable cell on another RAT.\nUE returns to idle mode and optionally starts to reconnect over NAS when timer expires.\nProvided to the UE by SIB1.";
      yexte:takes-effect "Next cell unlock";
      type erienmnrmgnbdu:ddt-GNBDU_Rrc_t311;
      default 3000;
    }
    leaf t310 {
      description "Timer t310.\nWaiting time for radio link failure.\nProvided to UE by SIB1. Values 4000 and 6000 are not supported in SIB1.\nFor EN-DC, provided to UE by SCG radio configuration. All values are relevant for EN-DC.";
      yexte:takes-effect "Next cell unlock";
      type erienmnrmgnbdu:ddt-GNBDU_Rrc_t310;
      default 2000;
    }
    leaf beamFailureDetectionTimer {
      status obsolete {
        yexte:status-information "Since 20.Q4. Planned to be removed.";
      }
      description "Timer for beam failure detection.\nValue in number of Qout,LR reporting periods of beam failure detection reference signal.";
      yexte:takes-effect "Next cell unlock";
      type erienmnrmgnbdu:ddt-GNBDU_Rrc_beamFailureDetectionTimer;
      default 1;
    }
  } // end 'grouping moc-Rrc'
  grouping moc-DUSliceQosInfo-keys {
    description "Key(s) for MOC DUSliceQosInfo";
    leaf id {
      status obsolete {
        yexte:status-information "Since 20.Q2. Deprecated: Since 19.Q4. Planned to be removed.";
      }
      erienmyext:no-notification;
      description "The value component of the RDN.";
      mandatory true;
      yexte:ecim-name dUSliceQosInfoId;
      type string;
    }
  } // end 'grouping moc-DUSliceQosInfo-keys'
  grouping moc-DUSliceQosInfo {
    description "DU Slice to 5QI table mapping information.";
    leaf-list reservedBy {
      min-elements 0;
      status obsolete {
        yexte:status-information "Since 20.Q2. Deprecated: Since 19.Q4. Planned to be removed.";
      }
      config false;
      description "Contains a list of MO instances that reserve this MO instance.";
      notife:notifiable-state-data true;
      erienmyext:enm-type MOREF;
      type string;
    }
    container pLMNId {
      description "PLMN identifier.";
      status obsolete {
        yexte:status-information "Since 20.Q2. Deprecated: Since 19.Q4. Planned to be removed.";
      }
      erienmyext:enm-type STRUCT;
      uses erienmnrmgnbdu:struct-PLMNId;
    } // end 'container pLMNId'
    leaf dU5qiTableRef {
      status obsolete {
        yexte:status-information "Since 20.Q2. Deprecated: Since 19.Q4. Planned to be removed.";
      }
      description "Reference to an instance of DU5qiTable MO.";
      yexte:takes-effect "New connection";
      erienmyext:enm-type MOREF;
      type string;
    }
    container sNSSAI {
      description "Single Network Slice Selection Assistance Information (S-NSSAI).";
      status obsolete {
        yexte:status-information "Since 20.Q2. Deprecated: Since 19.Q4. Planned to be removed.";
      }
      erienmyext:enm-type STRUCT;
      uses erienmnrmgnbdu:struct-SliceSelectionAssistInfo;
    } // end 'container sNSSAI'
  } // end 'grouping moc-DUSliceQosInfo'
  grouping moc-LogicalChannelGroup-keys {
    description "Key(s) for MOC LogicalChannelGroup";
    leaf id {
      status obsolete {
        yexte:status-information "Since 20.Q2. Planned to be removed.";
      }
      erienmyext:no-notification;
      description "The value component of the RDN.";
      mandatory true;
      yexte:ecim-name logicalChannelGroupId;
      type string;
    }
  } // end 'grouping moc-LogicalChannelGroup-keys'
  grouping moc-LogicalChannelGroup {
    description "QoS configuration related to Logical Channel group.";
    leaf userLabel {
      status obsolete {
        yexte:status-information "Since 20.Q2. Planned to be removed.";
      }
      description "Label for free use.";
      type erienmnrmgnbdu:ddt-UserLabel;
    }
    leaf-list reservedBy {
      min-elements 0;
      status obsolete {
        yexte:status-information "Since 20.Q2. Planned to be removed.";
      }
      config false;
      description "Contains a list of MO instances that reserve this MO instance.";
      notife:notifiable-state-data true;
      erienmyext:enm-type MOREF;
      type string;
    }
  } // end 'grouping moc-LogicalChannelGroup'
  grouping moc-DataRadioBearer-keys {
    description "Key(s) for MOC DataRadioBearer";
    leaf id {
      erienmyext:no-notification;
      description "The value component of the RDN.";
      mandatory true;
      yexte:ecim-name dataRadioBearerId;
      type string;
    }
  } // end 'grouping moc-DataRadioBearer-keys'
  grouping moc-DataRadioBearer {
    description "Data radio bearer configuration.\n\nThe RDN of this MO is DataRadioBearer=1.";
    leaf dlPollPdu {
      description "Number of AM RLC PDUs before polling for a status report in GNodeB.";
      yexte:takes-effect "New connection";
      type erienmnrmgnbdu:ddt-GNBDU_DataRadioBearer_dlPollPdu;
      default 32;
    }
    leaf tStatusProhibitDl {
      description "Timer for the receiving side of AM RLC.\nPrevents transmission of a new status PDU in UE.";
      yexte:takes-effect "New connection";
      type erienmnrmgnbdu:ddt-GNBDU_DataRadioBearer_tStatusProhibitDl;
      default 10;
    }
    leaf tStatusProhibitUl {
      description "Timer for the receiving side of AM RLC.\nPrevents transmission of a new status PDU in GNodeB.";
      yexte:takes-effect "New connection";
      type erienmnrmgnbdu:ddt-GNBDU_DataRadioBearer_tStatusProhibitUl;
      default 10;
    }
    leaf tPollRetransmitUl {
      description "Timer for the UE to supervise the poll for STATUS PDU.\nAM RLC UL transmitter waits for RLC STATUS feedback after sending a poll for STATUS before retransmitting the poll.";
      yexte:takes-effect "New connection";
      type erienmnrmgnbdu:ddt-GNBDU_DataRadioBearer_tPollRetransmitUl;
      default 40;
    }
    leaf dlMaxRetxThreshold {
      description "Maximum number of AM RLC DL retransmissions.\nWhen this value is reached, AM RLC DL retransmission is stopped and RRC is notified.";
      yexte:takes-effect "New connection";
      type erienmnrmgnbdu:ddt-GNBDU_DataRadioBearer_dlMaxRetxThreshold;
      default 16;
    }
    leaf tPollRetransmitDl {
      description "Timer supervising the poll for STATUS PDU.\nAM RLC DL transmitter to wait for RLC STATUS feedback after sending a poll for STATUS before retransmitting the poll.";
      yexte:takes-effect "New connection";
      type erienmnrmgnbdu:ddt-GNBDU_DataRadioBearer_tPollRetransmitDl;
      default 40;
    }
    leaf ulMaxRetxThreshold {
      description "Maximum number of AM RLC UL retransmissions.\nWhen this value is reached, AM RLC UL retransmission is stopped and RRC is notified.";
      yexte:takes-effect "New connection";
      type erienmnrmgnbdu:ddt-GNBDU_DataRadioBearer_ulMaxRetxThreshold;
      default 32;
    }
    leaf ulPollPdu {
      description "Number of AM RLC PDUs before polling for a status report in UE.";
      yexte:takes-effect "New connection";
      type erienmnrmgnbdu:ddt-GNBDU_DataRadioBearer_ulPollPdu;
      default 16;
    }
  } // end 'grouping moc-DataRadioBearer'
  grouping moc-Beam-keys {
    description "Key(s) for MOC Beam";
    leaf id {
      erienmyext:no-notification;
      description "The value component of the RDN.";
      mandatory true;
      yexte:ecim-name beamId;
      type string;
    }
  } // end 'grouping moc-Beam-keys'
  grouping moc-Beam {
    description "SSB beam used by NRSectorCarrier.\n\nCreated by the system when NRCellDU::administrativeState is changed to UNLOCKED.\n\nThe RDN of this MO is Beam=[ssbPhysicalIndex].";
    leaf ssbPhysicalIndex {
      erienmyext:no-notification;
      config false;
      description "Physical SSB index, represents the number of wide beams.";
      type erienmnrmgnbdu:ddt-GNBDU_Beam_ssbPhysicalIndex;
    }
  } // end 'grouping moc-Beam'
  grouping moc-ResourcePartitions-keys {
    description "Key(s) for MOC ResourcePartitions";
    leaf id {
      erienmyext:no-notification;
      description "The value component of the RDN.";
      mandatory true;
      yexte:ecim-name resourcePartitionsId;
      type string;
    }
  } // end 'grouping moc-ResourcePartitions-keys'
  grouping moc-ResourcePartitions {
    description "Set of resource partitions.";
  } // end 'grouping moc-ResourcePartitions'
  grouping moc-CommonBeamforming-keys {
    description "Key(s) for MOC CommonBeamforming";
    leaf id {
      erienmyext:no-notification;
      description "The value component of the RDN.";
      mandatory true;
      yexte:ecim-name commonBeamformingId;
      type string;
    }
  } // end 'grouping moc-CommonBeamforming-keys'
  grouping moc-CommonBeamforming {
    description "Contains configuration parameters related to common beamforming.\n\nCreated automatically when NRCellDU::administrativeState is changed to UNLOCKED.\nCan also be created manually.\n\nThe RDN of this MO is CommonBeamforming=1 when created automatically.";
    leaf digitalPan {
      description "Digitally controlled pan through beamforming.\nOnly takes effect if radio equipment supports AAS functionality. Positive value gives clockwise pan and negative value gives counterclockwise pan. If set to empty, usedDigitalPan shows the digital pan in use.\nSelect a value supported by installed radio equipment. Refer to CPI for installed radio equipment.";
      yexte:takes-effect "Next NRSectorCarrier Unlock";
      type erienmnrmgnbdu:ddt-GNBDU_CommonBeamforming_digitalPan;
    }
    list customComBfwWideBeam {
      min-elements 0;
      max-elements 64;
      key auto-generated-struct-key;
      leaf auto-generated-struct-key {
        type uint16;
        description "This leaf has been injected to allow for struct instances in a sequence to be ordered.";
        mandatory true;
      }
      description "Custom beamforming weights of downlink common channels.\n\nOnly takes effect if radio equipment supports AAS functionality. At least one amplitude must be non-zero for custom beamforming weights to take effect.";
      erienmyext:enm-type STRUCT;
      uses erienmnrmgnbdu:struct-CustomComBfwWideBeam;
    } // end 'list customComBfwWideBeam'
    leaf coverageShape {
      description "Coverage shape of a sector carrier.\nIf set to PRODUCT_DEFAULT, usedCoverageShape shows coverage shape in use.\nThe coverageShape can be overridden by the system in certain mixed mode scenarios, and usedCoverageShape reflects selected coverage shape.\nFor downlink, takes effect if any of the following is true:\n- customComBfwWideBeam is empty\n- amplitude of customComBfwWideBeam is set to all zeros\nOnly takes effect if radio equipment supports AAS functionality.\nSelect a value supported by installed radio equipment. Refer to CPI for installed radio equipment.";
      yexte:takes-effect "Next NRSectorCarrier Unlock";
      type erienmnrmgnbdu:enum-CoverageShape;
      default PRODUCT_DEFAULT;
    }
    leaf usedCoverageShape {
      config false;
      description "Used coverage shape for sector carrier.\nOnly valid when cell is unlocked.";
      notife:notifiable-state-data true;
      type erienmnrmgnbdu:enum-CoverageShape;
    }
    leaf usedDigitalPan {
      config false;
      description "Selected digital pan for sector carrier.\nOnly valid when cell is unlocked.";
      notife:notifiable-state-data true;
      type int32;
    }
    leaf usedDigitalTilt {
      config false;
      description "Selected digital tilt for sector carrier.\nRelative to horizontal plane, adjusted by mechanical tilt.\nIf value of usedCoverageShape is any MACRO and digitalTilt is empty, system uses 30 for all radio types. This means 3 degrees downtilt.\nOnly valid when cell is unlocked.";
      notife:notifiable-state-data true;
      type int32;
    }
    leaf digitalTilt {
      description "Digitally controlled tilt through beamforming.\nRelative to horizontal plane, adjusted by mechanical tilt.\nOnly applicable if radio equipment supports AAS functionality. Positive value gives downwards tilt and negative value gives upwards tilt. Attribute usedDigitalTilt shows digital tilt in use.\nMake sure that selected value is supported by installed radio equipment. For more information, see Antenna Integrated Radio Unit Description of installed radio equipment.\nIf value of usedCoverageShape is any HIGHRISE or HOTSPOT, a fixed digital tilt is applied. See Antenna Integrated Radio Unit Description of installed radio equipment.";
      yexte:takes-effect "Next NRSectorCarrier Unlock";
      type erienmnrmgnbdu:ddt-GNBDU_CommonBeamforming_digitalTilt;
    }
    leaf cbfMacroTaperType {
      description "Type of tapering for vertical beam weights.\nIt only takes effect if radio equipment supports AAS functionality and applicable only to Macro coverage shape.";
      yexte:takes-effect "Next NRSectorCarrier Unlock";
      type erienmnrmgnbdu:enum-CbfMacroTaperType;
      default STANDARD;
    }
  } // end 'grouping moc-CommonBeamforming'
  grouping moc-AdditionalPLMNInfo-keys {
    description "Key(s) for MOC AdditionalPLMNInfo";
    leaf id {
      erienmyext:no-notification;
      description "The value component of the RDN.";
      mandatory true;
      yexte:ecim-name additionalPLMNInfoId;
      type string;
    }
  } // end 'grouping moc-AdditionalPLMNInfo-keys'
  grouping moc-AdditionalPLMNInfo {
    description "PLMN-related information that can be additionally served by NR cell.";
    leaf cellReservedForOperator {
      description "Whether cell is reserved for operator use.";
      yexte:takes-effect "Next cell unlock";
      yexte:precondition "Value can only be changed when NRCellDU has administrativeState LOCKED.";
      type erienmnrmgnbdu:enum-CellReservedForOperator;
      default NOT_RESERVED;
    }
    leaf nRTAC {
      description "NR Tracking Area Code (TAC).";
      mandatory true;
      yexte:takes-effect "Next cell unlock";
      yexte:dependencies "Specific pLMNIdList can only be associated with unique nRTAC while different pLMNIdList can be associated with the same nRTAC.\nNRCellDU MO can have no AdditionalPLMNInfo MOs with duplicable nRTAC and pLMNIdList.";
      type erienmnrmgnbdu:ddt-GNBDU_AdditionalPLMNInfo_nRTAC;
    }
    list pLMNIdList {
      min-elements 1;
      max-elements 12;
      key auto-generated-struct-key;
      leaf auto-generated-struct-key {
        type uint16;
        description "This leaf has been injected to allow for struct instances in a sequence to be ordered.";
        mandatory true;
      }
      description "PLMNs that can be served by NR cell.";
      erienmyext:enm-type STRUCT;
      uses erienmnrmgnbdu:struct-PLMNId;
    } // end 'list pLMNIdList'
  } // end 'grouping moc-AdditionalPLMNInfo'
  grouping moc-GNBDUFunction-keys {
    description "Key(s) for MOC GNBDUFunction";
    leaf id {
      erienmyext:no-notification;
      description "The value component of the RDN.";
      mandatory true;
      yexte:ecim-name gNBDUFunctionId;
      type string;
    }
  } // end 'grouping moc-GNBDUFunction-keys'
  grouping moc-GNBDUFunction {
    description "Represents gNodeB-DU function.\n\nCannot be deleted if there are NRSectorCarriers configured.";
    leaf userLabel {
      description "Label for free use.";
      type erienmnrmgnbdu:ddt-UserLabel;
    }
    leaf caVlanPortRef {
      description "Reference to an instance of VlanPort MO that can be used to set up InterMeLinks.\nUsed as default when no value is specified for ExtGNBDUPartnerFunction::caVlanPortRef.";
      yexte:takes-effect "Node restart";
      erienmyext:enm-type MOREF;
      type string;
    }
    leaf pwsServiceState {
      status obsolete {
        yexte:status-information "Since 20.Q3. Planned to be removed.";
      }
      config false;
      description "Value true if PWS broadcast is scheduled.";
      notife:notifiable-state-data true;
      type boolean;
    }
    leaf release {
      config false;
      description "The product release of the ManagedFunction.";
      notife:notifiable-state-data true;
      type string;
    }
    leaf activeF1Link {
      status current {
        yexte:preliminary;
      }
      config false;
      description "Active F1-C link used for traffic towards gNodeB-CU-CP.";
      notife:notifiable-state-data true;
      type erienmnrmgnbdu:enum-LinkActive;
    }
    leaf endpointResDepHEnabled {
      description "Whether endpoint resource deprecation handling is enabled.\nIf true, updating deprecated attributes rpUpIpAddress and f1SctpEndPointRef also updates the IP addresses configured with following MO classes:\n- EndPointResource\n- LocalSctpEndpoint\n- LocalIpEndpoint.\nIf false, updating the deprecated attributes does not update following MO classes:\n- EndPointResource\n- LocalSctpEndpoint\n- LocalIpEndpoint.\nNode always uses the IP addresses configured with following MO classes:\n- EndPointResource\n- LocalSctpEndpoint\n- LocalIpEndpoint.\nUpdating these MO classes never updates the deprecated attributes. Deprecated attributes cannot express all configurations.\nDisabling deprecation handling protects MO classes EndPointResource, LocalSctpEndpoint and LocalIpEndpoint from modification from older management system versions where only the deprecated attributes are visible.";
      type boolean;
      default true;
    }
    leaf endpointResourceRef {
      description "Reference to EndpointResource MO instance.\nResourcePartitionMember MO can also refer to EndpointResource MO instances only valid for specific PLMN or NSSAI. If ResourcePartitionMember::endpointResourceRef is empty, this reference is used.";
      yexte:takes-effect "Node restart";
      erienmyext:enm-type MOREF;
      type string;
    }
    leaf dlBbCapacityNet {
      config false;
      description "Granted DL baseband capacity.\nAvailable capacity of corresponding Baseband HWAC property for all enabled Baseband HW.";
      notife:notifiable-state-data true;
      type erienmnrmgnbdu:ddt-GNBDU_GNBDUFunction_dlBbCapacityNet;
    }
    leaf gNBDUName {
      description "Distributed Unit (DU) name.";
      yexte:takes-effect "New connection";
      type erienmnrmgnbdu:ddt-GNBDU_GNBDUFunction_gNBDUName;
    }
    leaf f1SctpEndPointRef {
      status deprecated {
        yexte:status-information "Since 20.Q3. Replaced by LocalSctpEndpoint::sctpEndpointRef. Planned to be removed.";
      }
      description "Reference to SctpEndpoint MO for F1 control connections.";
      yexte:takes-effect "Node restart";
      erienmyext:enm-type MOREF;
      type string;
    }
    leaf dlBbCapacityMaxLimit {
      config false;
      description "Maximum DL baseband capacity available on unlocked Baseband hardware.\nMaximum limit of DL capacity that can be granted by baseband HWAC. This level sets the limit at emergency unlock.";
      notife:notifiable-state-data true;
      type erienmnrmgnbdu:ddt-GNBDU_GNBDUFunction_dlBbCapacityMaxLimit;
    }
    leaf pwsEtwsPrimaryInd {
      description "Number of consecutive defaultPagingCycles during which ETWS primary notification is broadcast.";
      yexte:takes-effect "Next F1 Application Protocol (F1AP) WRITE-REPLACE WARNING REQUEST message. Does not affect ongoing PWS broadcast.";
      type erienmnrmgnbdu:ddt-GNBDU_GNBDUFunction_pwsEtwsPrimaryInd;
      default 8;
    }
    leaf ulBbCapacityNet {
      config false;
      description "Granted UL baseband capacity.\nAvailable capacity of corresponding Baseband HWAC property for all enabled Baseband HW.";
      notife:notifiable-state-data true;
      type erienmnrmgnbdu:ddt-GNBDU_GNBDUFunction_ulBbCapacityNet;
    }
    container dUpLMNId {
      description "PLMN identifier used as part of PM Events data.\n\nShows the first entry of pLMNIdList on NRCellDU MOs.";
      status current {
        yexte:preliminary;
      }
      erienmyext:enm-type STRUCT;
      uses erienmnrmgnbdu:struct-PLMNId;
    } // end 'container dUpLMNId'
    leaf dlBbCapacityTarget {
      description "Targeted amount of Baseband HWAC throughput capacity for DL to be allocated to NR.\nThe setting impacts installation and distribution of Hardware Utilization Packages (HUPs) on the node.\nIn LTE+NR mixed mode Baseband configuration, ENodeBFunction::dlBbCapacityTarget must also be considered:\n- If dlBbCapacityTarget value is greater than or equal to 75 for just one RAT, system attempts to allocate the targeted value to that RAT. Available excess capacity is allocated to the other RAT.\n- If dlBbCapacityTarget value is greater than or equal to 75 on both RATs, fulfillment of both targets is attempted with priority to NR. Until targets are met, HUPs are distributed proportionally. After targets are met, HUPs are distributed equally.\n- If dlBbCapacityTarget value is undefined on both RATs (set to empty on NR and set to -1 on LTE), Baseband HWAC throughput capacity for DL is allocated by system as equal as installed HUPs allow, with priority to NR.\nGranted Baseband DL capacity is shown by GNBDUFunction::dlBbCapacityNet attribute.\nGranted Baseband UL capacity is half of granted DL capacity and is shown by GNBDUFunction::ulBbCapacityNet attribute.\nInformation on installed Baseband HWACs and HUPs can be found in CapacityUsage::hupInfo.";
      yexte:disturbances "Changing this parameter in LTE+NR mixed mode configuration can impact throughput limit on NR and LTE and can cause traffic degradation.";
      type erienmnrmgnbdu:ddt-GNBDU_GNBDUFunction_dlBbCapacityTarget;
    }
    leaf gNBDUId {
      description "Unique identifier for the DU within a gNodeB.";
      mandatory true;
      yexte:takes-effect "Node restart";
      type erienmnrmgnbdu:ddt-GNBDU_GNBDUFunction_gNBDUId;
    }
    leaf gNBId {
      description "Identity of gNodeB within a PLMN.";
      mandatory true;
      yexte:takes-effect "Node restart";
      yexte:dependencies "gNBId =< (2^gNBIdLength)-1";
      type erienmnrmgnbdu:ddt-GNBDU_GNBDUFunction_gNBId;
    }
    leaf gNBIdLength {
      description "Length of gNBId bit string representation.\nIf gNBId bit representation exceeds 22 bits, gNBIdLength value must be at least minimum bit length that can accommodate gNBId.\ngNBId =< (2^gNBIdLength)-1";
      yexte:takes-effect "Node restart";
      type erienmnrmgnbdu:ddt-GNBDU_GNBDUFunction_gNBIdLength;
      default 22;
    }
    leaf ulBbCapacityMaxLimit {
      config false;
      description "Maximum UL baseband capacity available on unlocked Baseband hardware.\nMaximum limit of UL capacity that can be granted by baseband HWAC. This level sets the limit at emergency unlock.";
      notife:notifiable-state-data true;
      type erienmnrmgnbdu:ddt-GNBDU_GNBDUFunction_ulBbCapacityMaxLimit;
    }
    leaf rpUpIpAddressRef {
      status deprecated {
        yexte:status-information "Since 20.Q3. Replaced by LocalIpEndpoint::addressRef. Planned to be removed.";
      }
      description "Reference to the IP address for intra RAN user plane connections.\nReference to an AddressIPv4 or AddressIPv6 instance.";
      yexte:takes-effect "Node restart";
      erienmyext:enm-type MOREF;
      type string;
    }
  } // end 'grouping moc-GNBDUFunction'
  grouping moc-LocalSctpEndpoint-keys {
    description "Key(s) for MOC LocalSctpEndpoint";
    leaf id {
      erienmyext:no-notification;
      description "The value component of the RDN.";
      mandatory true;
      yexte:ecim-name localSctpEndpointId;
      type string;
    }
  } // end 'grouping moc-LocalSctpEndpoint-keys'
  grouping moc-LocalSctpEndpoint {
    description "Local transport network endpoint for control plane interface.";
    leaf sctpEndpointRef {
      description "Reference to SctpEndpoint MO instance.\nMust be unique among LocalSctpEndpoint MO instances under EndpointResource.";
      mandatory true;
      yexte:takes-effect "Node restart";
      yexte:dependencies "If sctpEndpointRef is the same for LocalSctpEndpoint MO instances, interfaceUsed must be the same.";
      erienmyext:enm-type MOREF;
      type string;
    }
    leaf interfaceUsed {
      description "Control plane interface that uses the referenced SctpEndpoint.\nAllowed value: F1.\nInterface must be unique across LocalSctpEndpoints under EndpointResource.";
      mandatory true;
      yexte:takes-effect "Node restart";
      yexte:dependencies "Must be the same for LocalSctpEndpoint MO instances, if sctpEndpointRef is the same.";
      type erienmnrmgnbdu:enum-InterfaceName;
    }
  } // end 'grouping moc-LocalSctpEndpoint'
  grouping moc-ResourcePartition-keys {
    description "Key(s) for MOC ResourcePartition";
    leaf id {
      erienmyext:no-notification;
      description "The value component of the RDN.";
      mandatory true;
      yexte:ecim-name resourcePartitionId;
      type string;
    }
  } // end 'grouping moc-ResourcePartition-keys'
  grouping moc-ResourcePartition {
    description "Combination of attributes specifying in which resource partition a UE is included.";
    leaf-list reservedBy {
      min-elements 0;
      config false;
      description "Contains a list of MO instances that reserve this MO instance.\nCurrently not used.";
      notife:notifiable-state-data true;
      erienmyext:enm-type MOREF;
      type string;
    }
    leaf related5qiTableRef {
      description "Reference to DU5qiTable MO instance.";
      yexte:takes-effect "New connection";
      yexte:dependencies "If non-empty, ResourcePartitionMember::endpointResourceRef must be empty.";
      erienmyext:enm-type MOREF;
      type string;
    }
    leaf resourcePartitionName {
      description "Name of a resource partition.";
      type erienmnrmgnbdu:ddt-GNBDU_ResourcePartition_resourcePartitionName;
    }
  } // end 'grouping moc-ResourcePartition'
  grouping moc-EndpointResource-keys {
    description "Key(s) for MOC EndpointResource";
    leaf id {
      erienmyext:no-notification;
      description "The value component of the RDN.";
      mandatory true;
      yexte:ecim-name endpointResourceId;
      type string;
    }
  } // end 'grouping moc-EndpointResource-keys'
  grouping moc-EndpointResource {
    description "Transport network endpoints for RAN interfaces.\n\nConfiguration is valid for an entity that refers to an instance of this MO.";
    leaf userLabel {
      description "Label for free use.";
      type erienmnrmgnbdu:ddt-UserLabel;
    }
    leaf-list reservedBy {
      min-elements 0;
      config false;
      description "Contains a list of MO instances that reserve this MO instance.";
      notife:notifiable-state-data true;
      erienmyext:enm-type MOREF;
      type string;
    }
  } // end 'grouping moc-EndpointResource'
  grouping moc-NRSynchronization-keys {
    description "Key(s) for MOC NRSynchronization";
    leaf id {
      erienmyext:no-notification;
      description "The value component of the RDN.";
      mandatory true;
      yexte:ecim-name nRSynchronizationId;
      type string;
    }
  } // end 'grouping moc-NRSynchronization-keys'
  grouping moc-NRSynchronization {
    description "Top class for synchronization within NR.\n\nThe RDN of this MO is NRSynchronization=1.";
  } // end 'grouping moc-NRSynchronization'
  grouping moc-DUResourcePartition-keys {
    description "Key(s) for MOC DUResourcePartition";
    leaf id {
      status obsolete {
        yexte:status-information "Since 20.Q2. Deprecated: Since 19.Q4. Planned to be removed.";
      }
      erienmyext:no-notification;
      description "The value component of the RDN.";
      mandatory true;
      yexte:ecim-name dUResourcePartitionId;
      type string;
    }
  } // end 'grouping moc-DUResourcePartition-keys'
  grouping moc-DUResourcePartition {
    description "Combination of attributes specifying in which resource partition a UE is included.";
    leaf-list mappedSliceList {
      min-elements 0;
      max-elements 36;
      status obsolete {
        yexte:status-information "Since 20.Q2. Deprecated: Since 19.Q4. Planned to be removed.";
      }
      description "List of mapped slices to 5QI table.";
      yexte:takes-effect "New connection";
      erienmyext:enm-type MOREF;
      type string;
    }
  } // end 'grouping moc-DUResourcePartition'
  grouping moc-PowerBackoff-keys {
    description "Key(s) for MOC PowerBackoff";
    leaf id {
      erienmyext:no-notification;
      description "The value component of the RDN.";
      mandatory true;
      yexte:ecim-name powerBackoffId;
      type string;
    }
  } // end 'grouping moc-PowerBackoff-keys'
  grouping moc-PowerBackoff {
    description "Configuration parameters related to EMF Exposure Power Back-off.\n\nThe feature intends to reduce radio safety distance in massive MIMO products.";
    leaf powerBackoffThresh {
      yexte:restricted;
      description "Average transmitted power upper threshold for duration of powerBackoffAvgTime.\nIn percentage of configuredMaxTxPower.";
      mandatory true;
      yexte:takes-effect "Next NRSectorCarrier Unlock";
      yexte:dependencies "Only used when powerBackoffEnabled is set to true.";
      type erienmnrmgnbdu:ddt-GNBDU_PowerBackoff_powerBackoffThresh;
    }
    leaf powerBackoffEnabled {
      yexte:restricted;
      description "Enables EMF Exposure Power Back-off.\nThe feature reduces EMF safety distance in massive MIMO AAS systems. Creating this MO can result in throughput loss.";
      mandatory true;
      yexte:takes-effect "Next NRSectorCarrier Unlock";
      type boolean;
    }
    leaf powerBackoffAvgTime {
      yexte:restricted;
      description "Power averaging time for EMF Exposure Power Back-off.";
      mandatory true;
      yexte:takes-effect "Next NRSectorCarrier Unlock";
      yexte:dependencies "Only used when powerBackoffEnabled is set to true.";
      type erienmnrmgnbdu:ddt-GNBDU_PowerBackoff_powerBackoffAvgTime;
    }
  } // end 'grouping moc-PowerBackoff'
  grouping moc-DU5qiTable-keys {
    description "Key(s) for MOC DU5qiTable";
    leaf id {
      erienmyext:no-notification;
      description "The value component of the RDN.";
      mandatory true;
      yexte:ecim-name dU5qiTableId;
      type string;
    }
  } // end 'grouping moc-DU5qiTable-keys'
  grouping moc-DU5qiTable {
    description "Mapping from 5G QoS Identifier to parameters that have impact on QoS.";
    leaf default5qiTable {
      description "Indicates that the DU5qiTable instance is a default 5QI table.\nThe default 5QI table will be used when no DU5qiTable has been configured for a resource partition.";
      yexte:takes-effect "New connection";
      yexte:dependencies "Only one DU5qiTable instance can have the attribute default5qiTable set to TRUE.";
      type boolean;
      default false;
    }
    leaf-list reservedBy {
      min-elements 0;
      config false;
      description "Contains a list of MO instances that reserve this MO instance.";
      notife:notifiable-state-data true;
      erienmyext:enm-type MOREF;
      type string;
    }
    leaf resourcePartitionRef {
      status obsolete {
        yexte:status-information "Since 20.Q2. Deprecated: Since 20.Q1. Planned to be removed.";
      }
      description "Reference to an instance of ResourcePartition MO.";
      yexte:takes-effect "New connection";
      erienmyext:enm-type MOREF;
      type string;
    }
  } // end 'grouping moc-DU5qiTable'
  grouping moc-TermPointToGNBCUCP-keys {
    description "Key(s) for MOC TermPointToGNBCUCP";
    leaf id {
      erienmyext:no-notification;
      description "The value component of the RDN.";
      mandatory true;
      yexte:ecim-name termPointToGNBCUCPId;
      type string;
    }
  } // end 'grouping moc-TermPointToGNBCUCP-keys'
  grouping moc-TermPointToGNBCUCP {
    description "Models an F1-C link to a gNodeB-CU-CP.";
    leaf usedIpAddress {
      config false;
      description "Destination address used for initialization of underlying SCTP association.\nContains address of latest successful F1-C setup.\nIP address can be an IPv4 or an IPv6 address.";
      notife:notifiable-state-data true;
      type string;
    }
    leaf ipv6Address {
      description "IPv6 address of gNodeB-CU-CP.\nFormat is eight fields, separated by colons.\nEach field consists of four hexadecimal characters. Value of each field is in range 0-FFFF.\nLeading zeroes can be omitted in a field, and multiple groups of 16 bits of zeroes can be compressed to ::.\nThe :: can appear only once in an address.";
      yexte:takes-effect "Next MO unlock";
      type erienmnrmgnbdu:ddt-GNBDU_TermPointToGNBCUCP_ipv6Address;
      default ::;
    }
    leaf administrativeState {
      description "The administrative state.\nCan be set to LOCKED only if there is no NRCellDU with administrativeState UNLOCKED in the GNBDUFunction.";
      yexte:disturbances "Changing this attribute to LOCKED causes loss of traffic.";
      type erienmnrmgnbdu:enum-AdmState;
      default LOCKED;
    }
    leaf ipv4Address {
      description "IPv4 address of the gNodeB-CU-CP.\nThe input format is four fields of digits, separated by dots. Each field may consist of three digits. The value of each field is in the range 0-255.";
      yexte:takes-effect "Next MO unlock";
      type erienmnrmgnbdu:ddt-GNBDU_TermPointToGNBCUCP_ipv4Address;
      default 0.0.0.0;
    }
    leaf-list availabilityStatus {
      min-elements 0;
      config false;
      description "The availability status.\nIt contains details about operational state.";
      notife:notifiable-state-data true;
      type erienmnrmgnbdu:enum-AvailStatus;
    }
    leaf operationalState {
      config false;
      description "The operational state.";
      notife:notifiable-state-data true;
      type erienmnrmgnbdu:enum-OperState;
    }
    leaf gNBCUName {
      config false;
      description "Central Unit (CU) name.";
      notife:notifiable-state-data true;
      type erienmnrmgnbdu:ddt-GNBDU_TermPointToGNBCUCP_gNBCUName;
    }
  } // end 'grouping moc-TermPointToGNBCUCP'
  grouping moc-QciProfileEndcConfig-keys {
    description "Key(s) for MOC QciProfileEndcConfig";
    leaf id {
      status deprecated {
        yexte:status-information "Since 20.Q3. Replaced by DU5qi. Planned to be removed.";
      }
      erienmyext:no-notification;
      description "The value component of the RDN.";
      mandatory true;
      yexte:ecim-name qciProfileEndcConfigId;
      type string;
    }
  } // end 'grouping moc-QciProfileEndcConfig-keys'
  grouping moc-QciProfileEndcConfig {
    description "Route from QCIs to parameters that impacts QoS for Data Radio Bearers.\n\nENDC stands for E-UTRAN NR Dual Connectivity.\n\nThe RDN of this MO is QciProfileEndcConfig=1.";
    leaf tReassemblyUl {
      status deprecated {
        yexte:status-information "Since 20.Q3. Replaced by DU5qi::tReassemblyUl. Planned to be removed.";
      }
      description "Timer for receiving side of AM RLC and receiving UM RLC.\nDetects loss of RLC PDUs at lower layers.";
      yexte:takes-effect "New connection";
      type erienmnrmgnbdu:ddt-GNBDU_QciProfileEndcConfig_tReassemblyUl;
      default 20;
    }
    leaf tReassemblyDl {
      status deprecated {
        yexte:status-information "Since 20.Q3. Replaced by DU5qi::tReassemblyDl. Planned to be removed.";
      }
      description "Timer for the UE used by the receiving side of AM RLC and receiving UM RLC.\nDetects loss of RLC PDUs at lower layers.";
      yexte:takes-effect "New connection";
      type erienmnrmgnbdu:ddt-GNBDU_QciProfileEndcConfig_tReassemblyDl;
      default 20;
    }
  } // end 'grouping moc-QciProfileEndcConfig'
  grouping moc-NRCellDU-keys {
    description "Key(s) for MOC NRCellDU";
    leaf id {
      erienmyext:no-notification;
      description "The value component of the RDN.";
      mandatory true;
      yexte:ecim-name nRCellDUId;
      type string;
    }
  } // end 'grouping moc-NRCellDU-keys'
  grouping moc-NRCellDU {
    description "NR Cell representation in gNodeB-DU.\n\nPrecondition: The MO must be locked before deletion.";
    leaf typeISinglePanelRiRestriction {
      description "Bit mask that indicates UE-specific rank restriction for codebook of Type1 single panel.\nOnly applicable for Low-Band or Mid-Band cells.\nFollowing values can be applied:\n- Bitmap b00001111, no rank restriction, value 15.\n- Bitmap b00000001, rank restricted to 1, UE can only report rank 1, value 1.\n- Bitmap b00000010, rank restricted to 2, value is 2.\n- Bitmap b00000100, rank restricted to 3, value is 4.\n- Bitmap b00001000, rank restricted to 4, value is 8.\n- Bitmap b00000011, rank restricted to 1, or 2, value is 3.\n- Bitmap b00000101, rank restricted to 1, or 3, value is 5.\n- Bitmap b00001001, rank restricted to 1, or 4, value is 9.\n- Bitmap b00000110, rank restricted to 2, or 3, value is 6.\n- Bitmap b00001010, rank restricted to 2, or 4, value is 10.\n- Bitmap b00001100, rank restricted to 3, or 4, value is 12.\n- Bitmap b00000111, rank restricted to 1, 2, or 3, value is 7.\n- Bitmap b00001011, rank restricted to 1, 2, or 4, value is 11.\n- Bitmap b00001101, rank restricted to 1, 3, or 4, value is 13.\n- Bitmap b00001110, rank restricted to 2, 3, or 4, value is 14.";
      yexte:disturbances "Changing this attribute can cause loss of traffic.";
      yexte:takes-effect "New connection";
      type erienmnrmgnbdu:ddt-GNBDU_NRCellDU_typeISinglePanelRiRestriction;
      default 15;
    }
    leaf nCGI {
      status obsolete {
        yexte:status-information "Since 20.Q2. Deprecated: Since 20.Q1. Planned to be removed.";
      }
      config false;
      description "NR Cell Global Identity.";
      notife:notifiable-state-data true;
      type erienmnrmgnbdu:ddt-GNBDU_NRCellDU_nCGI;
    }
    leaf dftSOfdmPuschStartRsrpThresh {
      status current {
        yexte:preliminary;
      }
      description "UE starts on DFT-S-OFDM when reported RSRP is below threshold in attribute value.\nRSRP is reported in 3GPP TS 38.331 CG-ConfigInfo.\nApplicable at Secondary Cell Group Addition for EN-DC FR2.";
      yexte:takes-effect "Next cell unlock";
      type erienmnrmgnbdu:ddt-GNBDU_NRCellDU_dftSOfdmPuschStartRsrpThresh;
      default -156;
    }
    leaf ulAvailableCrbs {
      description "Total amount of Common Resource Blocks (CRBs) available for uplink channels.\nEmpty value means no bandwidth restriction, no blanking in UL.";
      yexte:takes-effect "Next cell unlock";
      yexte:precondition "Value can only be changed if administrativeState is LOCKED.";
      type erienmnrmgnbdu:ddt-GNBDU_NRCellDU_ulAvailableCrbs;
    }
    leaf ailgDlPrbLoadLevel {
      description "Air Interface Load Generator (AILG) load level required for PDSCH.\nLoad level set to 0 means AILG for PDSCH is disabled.";
      yexte:takes-effect "Next cell unlock";
      yexte:precondition "Value can only be changed if administrativeState is LOCKED.";
      type erienmnrmgnbdu:ddt-GNBDU_NRCellDU_ailgDlPrbLoadLevel;
      default 0;
    }
    leaf drxOnDurationTimer {
      description "Number of consecutive slots or subframes at beginning of a DRX cycle.";
      yexte:takes-effect "Next cell unlock";
      yexte:precondition "Value can only be changed if administrativeState is LOCKED.";
      type erienmnrmgnbdu:enum-DrxOnDurationTimer;
      default ONDURATIONTIMER_8MS;
    }
    leaf trsResourceShifting {
      description "Whether TRS resource allocation shifting is activated.";
      yexte:takes-effect "Next cell unlock";
      type erienmnrmgnbdu:enum-TrsResourceShifting;
      default DEACTIVATED;
    }
    leaf ulStartCrb {
      description "Start position of Common Resource Blocks (CRBs) available for uplink channels.";
      yexte:takes-effect "Next cell unlock";
      yexte:precondition "Value can only be changed if administrativeState is LOCKED.";
      type erienmnrmgnbdu:ddt-GNBDU_NRCellDU_ulStartCrb;
      default 0;
    }
    leaf endcDlNrQualHyst {
      description "NR radio quality hysteresis used for SN terminated split bearer.\nQuality needs to be hysteresis more than endcDlNrLowQualThresh to start using NR leg for downlink user data transmission again.\nSINR is used to represent quality.";
      yexte:takes-effect "Next cell unlock";
      yexte:precondition "Value can only be changed if administrativeState is LOCKED.";
      type erienmnrmgnbdu:ddt-GNBDU_NRCellDU_endcDlNrQualHyst;
      default 5;
    }
    leaf fakeInt8NoRange{
      description "Just a fake Int8 with no range injected for testing";
      type int8;
    }
    leaf fakeInt8SingleRange{
          description "Just a fake Int8 with single range injected for testing";
          type erienmnrmgnbdu:ddt-GNBDU_NRCellDU_fakeInt8SingleRange;
    }
    leaf fakeInt8MultiRange{
      description "Just a fake Int8 with multi range injected for testing";
      type erienmnrmgnbdu:ddt-GNBDU_NRCellDU_fakeInt8MultiRange;
    }
    leaf fakeUInt8NoRange{
      description "Just a fake Unsigned Int8 with no range injected for testing";
      type uint8;
    }
    leaf fakeUInt8MultiRange{
          description "Just a fake Unsigned Int8 with multi range injected for testing";
          type erienmnrmgnbdu:ddt-GNBDU_NRCellDU_fakeUInt8MultiRange;
        }
    leaf fakeInt16NoRange{
      description "Just a fake Int16 with no range injected for testing";
      type int16;
    }
    leaf fakeInt16SingleRange{
          description "Just a fake Int16 with single range injected for testing";
          type erienmnrmgnbdu:ddt-GNBDU_NRCellDU_fakeInt16SingleRange;
    }
    leaf fakeInt16MultiRange{
     description "Just a fake Int16 with multi range injected for testing";
     type erienmnrmgnbdu:ddt-GNBDU_NRCellDU_fakeInt16MultiRange;
    }
    leaf fakeUInt16NoRange{
      description "Just a fake Unsigned Int16 with no range injected for testing";
      type uint16;
    }
    leaf fakeUInt16SingleRange{
          description "Just a fake Unsigned Int16 with single range injected for testing";
          type erienmnrmgnbdu:ddt-GNBDU_NRCellDU_fakeUInt16SingleRange;
    }
    leaf fakeUInt16MultiRange{
              description "Just a fake Unsigned Int16 with multi range injected for testing";
              type erienmnrmgnbdu:ddt-GNBDU_NRCellDU_fakeUInt16MultiRange;
    }
    leaf fakeUInt32NoRange{
      description "Just a fake Unsigned Int32 with no range injected for testing";
      type uint32;
    }
     leaf fakeInt64MultiRange{
         description "Just a fake Int64 with multi range injected for testing";
         type erienmnrmgnbdu:ddt-GNBDU_NRCellDU_fakeInt64MultiRange;
        }
    leaf fakeUInt64NoRange{
      description "Just a fake Unsigned Int64 with no range injected for testing";
      type uint64;
    }
    leaf fakeUInt64SingleRange{
      description "Just a fake Unsigned Int64 with single range injected for testing";
      type erienmnrmgnbdu:ddt-GNBDU_NRCellDU_fakeUInt64SingleRange;
    }
    leaf fakeUInt64MultiRange{
          description "Just a fake Unsigned Int64 with multi range injected for testing";
          type erienmnrmgnbdu:ddt-GNBDU_NRCellDU_fakeUInt64MultiRange;
        }
    leaf fakeDecimal64NoRange{
      description "Just a fake decimal64 with no range injected for testing";
      type decimal64;
    }
    leaf fakeDecimal64SingleRange{
      description "Just a fake decimal64 with single range injected for testing";
      type erienmnrmgnbdu:ddt-GNBDU_NRCellDU_fakeDecimal64SingleRange;
    }
    leaf fakeDecimal64MultiRange{
      description "Just a fake decimal64 with multi range injected for testing";
      type erienmnrmgnbdu:ddt-GNBDU_NRCellDU_fakeDecimal64MultiRange;
    }
    leaf serviceState {
      config false;
      description "Current service state.";
      notife:notifiable-state-data true;
      type erienmnrmgnbdu:enum-NRCellServiceState;
    }
    leaf cellBarred {
      description "Whether the NR cell is barred or not.";
      yexte:takes-effect "Next cell unlock";
      yexte:precondition "Value can only be changed if administrativeState is LOCKED.";
      type erienmnrmgnbdu:enum-CellBarred;
      default NOT_BARRED;
    }
    list sNSSAIList {
      min-elements 0;
      max-elements 1024;
      key auto-generated-struct-key;
      leaf auto-generated-struct-key {
        type uint16;
        description "This leaf has been injected to allow for struct instances in a sequence to be ordered.";
        mandatory true;
      }
      description "List of supported network slices.";
      erienmyext:enm-type STRUCT;
      uses erienmnrmgnbdu:struct-SliceSelectionAssistInfo;
    } // end 'list sNSSAIList'
    leaf fddLteCoexistence {
      status obsolete {
        yexte:status-information "Since 20.Q4. Planned to be removed.";
      }
      description "Whether or not NR cell is deployed in an LTE-NR coexistence case.\nApplicable for FDD only.\nIf set to true, the value of N_TA, offset is configured to 0 x T_c to enable UL frame alignment with an LTE FDD network.\nIf set to false, the value of N_TA, offset is configured to 25600 x T_c to optimize NR performance.\nSee 3GPP TS 38.133, 5G; NR; Requirements for support of radio resource management, chapter 7.1.2.";
      yexte:takes-effect "Next cell unlock";
      yexte:precondition "Value can only be changed if administrativeState is LOCKED.";
      type boolean;
      default false;
    }
    leaf drxInactivityTimer {
      description "Duration after PDCCH ocassion in which PDCCH indicates new UL or DL transmission.\nRecommended value for High-Band is INACTIVITYTIMER_8MS.";
      yexte:takes-effect "Next cell unlock";
      yexte:precondition "Value can only be changed if administrativeState is LOCKED.";
      type erienmnrmgnbdu:enum-DrxInactivityTimer;
      default INACTIVITYTIMER_8MS;
    }
    leaf cellReservedForOperator {
      description "Whether the cell is reserved for operator use or not.";
      yexte:takes-effect "Next cell unlock";
      yexte:precondition "Value can only be changed if administrativeState is LOCKED.";
      type erienmnrmgnbdu:enum-CellReservedForOperator;
      default NOT_RESERVED;
    }
    leaf ulRobustLaEnabled {
      description "Whether uplink robust link adaptation is enabled.\nOnly applicable if license for Critical IoT is present and the High-Band feature is active.\nMust be false for Low-Band and Mid-Band cells.";
      yexte:takes-effect "Next cell unlock";
      yexte:precondition "Value can only be changed if administrativeState is LOCKED.";
      type boolean;
      default false;
    }
    leaf drxEnable {
      description "Whether DRX function in cell is enabled.";
      yexte:takes-effect "Next cell unlock";
      yexte:precondition "Value can only be changed if administrativeState is LOCKED.";
      type boolean;
      default true;
    }
    leaf dlRobustLaEnabled {
      description "Whether downlink robust link adaptation is enabled.\nOnly applicable if license for Critical IoT is present and the High-Band feature is active.\nMust be false for Low-Band and Mid-Band cells.";
      yexte:takes-effect "Next cell unlock";
      yexte:precondition "Value can only be changed if administrativeState is LOCKED.";
      type boolean;
      default false;
    }
    leaf pointAArfcnTdd {
      config false;
      description "Common reference point for resource block grid within a cell.\nPointA value given by center frequency of resource element 0 in cell resource block 0 and indicated on a raster as NR-ARFCN.\nComputed from NRSectorCarrier::arfcnDL on cell unlock.";
      notife:notifiable-state-data true;
      type erienmnrmgnbdu:ddt-GNBDU_NRCellDU_pointAArfcnTdd;
    }
    leaf nrLteCoexistence {
      description "Whether NR cell is deployed in an LTE-NR coexistence.\nIf set to true when using TDD, tddUlDlPattern settings are validated with respect to alignment to LTE TDD. Value of N_TA, offset is configured to 39936 x T_c to enable UL frame alignment with an LTE TDD network.\nIf set to true when using FDD, value of N_TA, offset is configured to 0 x T_c to enable UL frame alignment with an LTE FDD network.\nIf set to false, value of N_TA, offset is configured to 25600 x T_c to optimize NR performance.\nSee 3GPP TS 38.133, 5G; NR; Requirements for support of radio resource management, chapter 7.1.2.";
      yexte:takes-effect "Next cell unlock";
      yexte:precondition "Value can only be changed if administrativeState is LOCKED.";
      yexte:dependencies "Can be true if the following apply:\n- tddUlDlPattern is TDD_ULDL_PATTERN_01 and tddSpecialSlotPattern is TDD_SPECIAL_SLOT_PATTERN_01, TDD_SPECIAL_SLOT_PATTERN_03, TDD_SPECIAL_SLOT_PATTERN_04, or TDD_SPECIAL_SLOT_PATTERN_05.\n- tddUlDlPattern is TDD_ULDL_PATTERN_04 and tddSpecialSlotPattern is TDD_SPECIAL_SLOT_PATTERN_03.\nMust be false otherwise.";
      type boolean;
      default false;
    }
    leaf pdschAilgEnabled {
      status obsolete {
        yexte:status-information "Since 20.Q2. Deprecated: Since 19.Q4. Planned to be removed.";
      }
      description "Whether Air Interface Load Generator (AILG) is enabled for PDSCH.";
      yexte:takes-effect "Next cell unlock";
      yexte:precondition "Value can only be changed if administrativeState is LOCKED.";
      type boolean;
      default false;
    }
    leaf pZeroNomPuschGrant {
      description "Power control parameter P0 Nominal for PUSCH transmissions with grant.";
      yexte:takes-effect "New connection";
      type erienmnrmgnbdu:ddt-GNBDU_NRCellDU_pZeroNomPuschGrant;
      default -100;
    }
    leaf operationalState {
      config false;
      description "The operational state.";
      notife:notifiable-state-data true;
      type erienmnrmgnbdu:enum-OperState;
    }
    leaf pwsBroadcastOngoing {
      config false;
      description "Whether PWS broadcast is scheduled.";
      notife:notifiable-state-data true;
      type boolean;
    }
    leaf endcUlNrLowQualThresh {
      description "NR radio quality level threshold used for SN Terminated split bearer.\nBelow this threshold the NR leg will not be used for uplink user data transmission.\nSINR is used to represent quality.";
      yexte:takes-effect "Next cell unlock";
      yexte:precondition "Value can only be changed if administrativeState is LOCKED.";
      type erienmnrmgnbdu:ddt-GNBDU_NRCellDU_endcUlNrLowQualThresh;
      default 17;
    }
    leaf tddLteCoexistence {
      status deprecated {
        yexte:status-information "Since 20.Q4. Replaced by nrLteCoexistence. Planned to be removed.";
      }
      description "Whether or not NR cell is deployed in an LTE-NR coexistence.\nApplicable for TDD only.\nIf set to true, tddUlDlPattern settings are validated with respect to alignment to LTE TDD. Value of N_TA, offset is configured to 39936 x T_c to enable UL frame alignment with an LTE TDD network.\nIf set to false, settings of tddUlDlPattern are not assumed to align to an LTE TDD pattern. Value of N_TA, offset is configured to 25600 x T_c to optimize NR performance.\nSee 3GPP TS 38.133, 5G; NR; Requirements for support of radio resource management, chapter 7.1.2.";
      yexte:takes-effect "Next cell unlock";
      yexte:precondition "Value can only be changed if administrativeState is LOCKED.";
      yexte:dependencies "Can be true if the following apply:\n- tddUlDlPattern is TDD_ULDL_PATTERN_01 and tddSpecialSlotPattern is TDD_SPECIAL_SLOT_PATTERN_01, TDD_SPECIAL_SLOT_PATTERN_03, TDD_SPECIAL_SLOT_PATTERN_04, or TDD_SPECIAL_SLOT_PATTERN_05.\n- tddUlDlPattern is TDD_ULDL_PATTERN_04 and tddSpecialSlotPattern is TDD_SPECIAL_SLOT_PATTERN_03.\nMust be false otherwise.";
      type boolean;
      default false;
    }
    leaf dlAvailableCrbs {
      description "Total amount of Common Resource Blocks (CRBs) available for downlink channels.\nEmpty value means no bandwidth restriction, no blanking in DL.";
      yexte:takes-effect "Next cell unlock";
      yexte:precondition "Value can only be changed if administrativeState is LOCKED.";
      type erienmnrmgnbdu:ddt-GNBDU_NRCellDU_dlAvailableCrbs;
    }
    leaf tddUlDlPattern {
      description "TDD uplink-downlink pattern configuration.\nDefines downlink, uplink, and special slot pattern for NR TDD.";
      yexte:takes-effect "Next cell unlock";
      yexte:precondition "Value can only be changed if administrativeState is LOCKED.";
      yexte:dependencies "For TDD_ULDL_PATTERN_00, the following options apply:\n - tddSpecialSlotPattern must be TDD_SPECIAL_SLOT_PATTERN_00, TDD_SPECIAL_SLOT_PATTERN_01, or TDD_SPECIAL_SLOT_PATTERN_02.\n - nrLteCoexistence must be false.\n - advancedDlSuMimoEnabled must be false.\nFor TDD_ULDL_PATTERN_01, tddSpecialSlotPattern must be one of the following options:\n- TDD_SPECIAL_SLOT_PATTERN_01\n- TDD_SPECIAL_SLOT_PATTERN_03\n- TDD_SPECIAL_SLOT_PATTERN_04\n- TDD_SPECIAL_SLOT_PATTERN_05\nFor TDD_ULDL_PATTERN_02, the following options apply:\n - tddSpecialSlotPattern must be TDD_SPECIAL_SLOT_PATTERN_00, TDD_SPECIAL_SLOT_PATTERN_01, or TDD_SPECIAL_SLOT_PATTERN_02.\n - nrLteCoexistence must be false.\nFor TDD_ULDL_PATTERN_03, the following options apply:\n - tddSpecialSlotPattern must be TDD_SPECIAL_SLOT_PATTERN_00, TDD_SPECIAL_SLOT_PATTERN_01, or TDD_SPECIAL_SLOT_PATTERN_02.\n - nrLteCoexistence must be false.\nFor TDD_ULDL_PATTERN_04, tddSpecialSlotPattern must be TDD_SPECIAL_SLOT_PATTERN_03.";
      type erienmnrmgnbdu:enum-TddUlDlPatternType;
      default TDD_ULDL_PATTERN_00;
    }
    leaf rachPreambleTransMax {
      description "Maximum number of random access preamble transmissions performed before declaring a failure.";
      yexte:takes-effect "Next cell unlock";
      yexte:precondition "Value can only be changed if administrativeState is LOCKED.";
      type erienmnrmgnbdu:ddt-GNBDU_NRCellDU_rachPreambleTransMax;
      default 10;
    }
    container csiRsConfig4P {
      description "4-port CSI and associated port to antenna mapping settings.";
      erienmyext:enm-type STRUCT;
      uses erienmnrmgnbdu:struct-CsiRsConfig4P;
    } // end 'container csiRsConfig4P'
    leaf ssbFrequencyAutoSelected {
      config false;
      description "Automatically selected SSB frequency (NR-ARFCN).\nCalculated at cell unlock if ssbFrequency is set to 0. ssbFrequencyAutoSelected is empty while ssbFrequency > 0.";
      notife:notifiable-state-data true;
      type int32;
    }
    leaf ssbGscn {
      config false;
      description "GSCN of SSB.\nSSB location on synchronization raster (required for primary cell in stand-alone gNodeB). If empty, SSB is not placed on synchronization raster.";
      notife:notifiable-state-data true;
      type int32;
    }
    leaf fixWideBeamsForPeriodicSr {
      status current {
        yexte:preliminary;
      }
      description "Number of fixed wide beams for periodic SR in PRACH slot according to SSB relation.\nOnly applicable for High-Band cells.\nFor Low-Band and Mid-Band, value must be FIX_WB_FOR_PERIODIC_SR_NONE.\nAttribute is for 12 wide beam configuration and is scaled automatically for 24 wide beam support.";
      yexte:takes-effect "Next cell unlock";
      yexte:precondition "Value can only be changed if the administrativeState is LOCKED.";
      yexte:dependencies "For High-Band cells, must be set to FIX_WB_FOR_PERIODIC_SR_NONE if cellRange is less than or equal to 1100 m.";
      type erienmnrmgnbdu:enum-FixWideBeamsForPeriodicSrType;
      default FIX_WB_FOR_PERIODIC_SR_NONE;
    }
    leaf pdschStartPrbStrategy {
      description "Mitigate interference strategy that chooses one of following ways to allocate PRBs to UEs for DL.\n- From lower frequency band edge, START_LOWER_EDGE.\n- From higher frequency band edge, START_HIGHER_EDGE.\n- Both from lower and higher frequency band edges by random for each slot, RANDOM_START_LOWER_OR_HIGHER.\n- Random starting point for each slot for interference spreading over the whole band, RANDOM_START_WITHIN_BAND.";
      yexte:takes-effect "Next cell unlock";
      yexte:precondition "Value can only be changed if administrativeState is LOCKED.";
      type erienmnrmgnbdu:enum-StartPrbStrategy;
      default RANDOM_START_WITHIN_BAND;
    }
    leaf endcDlNrLowQualThresh {
      description "NR radio quality level threshold used for SN terminated split bearer.\nBelow this threshold the NR leg is not used for downlink user data transmission.\nSINR is used to represent quality. Value -16 correspond to zero throughput, and lower values have no further impact.";
      yexte:takes-effect "Next cell unlock";
      yexte:precondition "Value can only be changed if administrativeState is LOCKED.";
      type erienmnrmgnbdu:ddt-GNBDU_NRCellDU_endcDlNrLowQualThresh;
      default 5;
    }
    leaf nCI {
      config false;
      description "NR Cell Identity.";
      notife:notifiable-state-data true;
      type int64;
    }
    leaf pointAFrequencyTdd {
      config false;
      description "Frequency representation of the NR-ARFCN used by pointAArfcnTDD.";
      notife:notifiable-state-data true;
      type erienmnrmgnbdu:ddt-GNBDU_NRCellDU_pointAFrequencyTdd;
    }
    leaf bfrEnabled {
      description "Whether Beam Failure Recovery is enabled.";
      yexte:takes-effect "Next cell unlock";
      yexte:precondition "Value can only be changed if administrativeState is LOCKED.";
      type boolean;
      default true;
    }
    leaf dlStartCrb {
      description "Start position of Common Resource Blocks (CRBs) available for downlink channels.";
      yexte:takes-effect "Next cell unlock";
      yexte:precondition "Value can only be changed if administrativeState is LOCKED.";
      type erienmnrmgnbdu:ddt-GNBDU_NRCellDU_dlStartCrb;
      default 0;
    }
    leaf csiReportFormat {
      description "Whether aperiodic CSI reports include subband or wideband feedback.";
      yexte:takes-effect "Next cell unlock";
      yexte:precondition "Value can only be changed if administrativeState is LOCKED.";
      type erienmnrmgnbdu:enum-CsiReportFormat;
      default CQI_WB_PMI_WB;
    }
    leaf rachPreambleRecTargetPower {
      description "Target random access preamble power level at network receiver side.";
      yexte:takes-effect "Next cell unlock";
      yexte:precondition "Value can only be changed if administrativeState is LOCKED.";
      type erienmnrmgnbdu:ddt-GNBDU_NRCellDU_rachPreambleRecTargetPower;
      default -110;
    }
    container sibType2 {
      description "Information needed for acquisition of System Information Block 2.";
      erienmyext:enm-type STRUCT;
      uses erienmnrmgnbdu:struct-SibType;
    } // end 'container sibType2'
    leaf trsPeriodicity {
      description "Periodicity of Channel State Information-Reference Signal (CSI-RS) used for tracking purpose.";
      yexte:takes-effect "Next cell unlock";
      yexte:precondition "Value can only be changed if administrativeState is LOCKED.";
      yexte:dependencies "Must be 40 if cell uses NRSectorCarrier with essScPairId configured.";
      type erienmnrmgnbdu:ddt-GNBDU_NRCellDU_trsPeriodicity;
      default 20;
    }
    leaf csiRsShiftingSecondary {
      description "Whether secondary CSI-RS resource allocation shifting is activated.";
      yexte:takes-effect "Next cell unlock";
      type erienmnrmgnbdu:enum-CsiRsResourceShifting;
      default DEACTIVATED;
    }
    leaf maxNoOfSrsPortsPreferred {
      status current {
        yexte:preliminary;
      }
      description "Maximum number of SRS ports that is preferred in SRS configuration for each UE.\nIf the value of this parameter cannot be assigned to a UE due to its reported capabilities, the number of SRS ports assigned will be based on the capabilities reported by the UE.";
      yexte:takes-effect "New connection";
      type erienmnrmgnbdu:ddt-GNBDU_NRCellDU_maxNoOfSrsPortsPreferred;
      default 4;
    }
    leaf ulMaxMuMimoLayers {
      description "Maximum number of coscheduled uplink MU-MIMO layers at cell level.\nUplink MU-MIMO is disabled when value is 0.\nOnly used if Control Channel Beamforming is present and active.\nValue must be 0 for Low-Band and High-Band cells.\nFor Mid-Band cells, values 0, 2 and 4 are allowed.";
      yexte:takes-effect "Next cell unlock";
      yexte:precondition "Value can only be changed if administrativeState is LOCKED.";
      type erienmnrmgnbdu:ddt-GNBDU_NRCellDU_ulMaxMuMimoLayers;
      default 0;
    }
    leaf nRTAC {
      description "NR Tracking Area Code (TAC).";
      mandatory true;
      yexte:takes-effect "Next cell unlock";
      yexte:precondition "Value can only be changed if administrativeState is LOCKED.";
      yexte:dependencies "Specific pLMNIdList can only be associated with unique nRTAC while different pLMNIdList can be associated with the same nRTAC.\nNRCellDU MO can have no AdditionalPLMNInfo MOs with duplicable nRTAC and pLMNIdList.";
      type erienmnrmgnbdu:ddt-GNBDU_NRCellDU_nRTAC;
    }
    container sibType4 {
      description "Information needed for acquisition of System Information Block 4.";
      erienmyext:enm-type STRUCT;
      uses erienmnrmgnbdu:struct-SibType;
    } // end 'container sibType4'
    container sibType5 {
      description "Information needed for acquisition of System Information Block 5.";
      erienmyext:enm-type STRUCT;
      uses erienmnrmgnbdu:struct-SibType;
    } // end 'container sibType5'
    leaf ul256QamEnabled {
      description "Whether 256-QAM support in UL is enabled.\nOnly applicable for Low-Band and Mid-Band cells.\nFor High-Band cells, value must be false.\nOnly applicable if license for 256QamUlLowMidBand is present and the feature is active.";
      yexte:takes-effect "New connection";
      type boolean;
      default false;
    }
    leaf pointAFrequencyUlFdd {
      config false;
      description "Frequency representation of the NR-ARFCN used by pointAArfcnUlFdd.";
      notife:notifiable-state-data true;
      type erienmnrmgnbdu:ddt-GNBDU_NRCellDU_pointAFrequencyUlFdd;
    }
    leaf dftSOfdmPuschEnabled {
      description "Whether DFT-S-OFDM waveform support for PUSCH is enabled.";
      yexte:takes-effect "Next cell unlock";
      yexte:precondition "Value can only be changed if administrativeState is LOCKED.";
      type boolean;
      default false;
    }
    container csiRsConfig32P {
      description "Settings related to 32-port CSI and associated port to antenna mapping.";
      erienmyext:enm-type STRUCT;
      uses erienmnrmgnbdu:struct-CsiRsConfig32P;
    } // end 'container csiRsConfig32P'
    container csiRsConfig16P {
      description "Settings related to 16-port CSI and associated port to antenna mapping.";
      erienmyext:enm-type STRUCT;
      uses erienmnrmgnbdu:struct-CsiRsConfig16P;
    } // end 'container csiRsConfig16P'
    leaf drxLongCycle {
      description "Duration of one complete DRX cycle.\nRecommended value for High-Band is LONGCYCLE_80MS.";
      yexte:takes-effect "Next cell unlock";
      yexte:precondition "Value can only be changed if administrativeState is LOCKED.";
      type erienmnrmgnbdu:enum-DrxLongCycle;
      default LONGCYCLE_80MS;
    }
    container sibType6 {
      description "Information needed for acquisition of System Information Block 6 (SIB6).\n\nContains PWS warning message for ETWS primary notification.";
      erienmyext:enm-type STRUCT;
      uses erienmnrmgnbdu:struct-SibTypePws;
    } // end 'container sibType6'
    container sibType7 {
      description "Information needed for acquisition of System Information Block 7 (SIB7).\n\nContains PWS warning message for ETWS secondary notification.";
      erienmyext:enm-type STRUCT;
      uses erienmnrmgnbdu:struct-SibType;
    } // end 'container sibType7'
    leaf dl256QamEnabled {
      description "Enables 256 QAM support in DL.\nNot applicable in High-Band cells.";
      yexte:takes-effect "New connection";
      yexte:precondition "Value can only be changed if administrativeState is LOCKED.";
      type boolean;
      default true;
    }
    container sibType8 {
      description "Information needed for acquisition of System Information Block 8 (SIB8).\n\nContains PWS warning message for Wireless Emergency Alerts (WEA), also known as CMAS.";
      erienmyext:enm-type STRUCT;
      uses erienmnrmgnbdu:struct-SibType;
    } // end 'container sibType8'
    leaf pointAArfcnUlFdd {
      config false;
      description "Common reference point for the resource block grid of the UL carrier FDD cell.\nPointA value given by center frequency of resource element 0 in cell resource block 0 and indicated on a raster as NR-ARFCN.\nComputed from NRSectorCarrier::arfcnUL on cell unlock.";
      notife:notifiable-state-data true;
      type int32;
    }
    leaf endcUlNrQualHyst {
      description "NR radio quality hysteresis used for SN Terminated split bearer.\nQuality need to be hysteresis better than endcUlNrLowQualThresh to start using the NR leg for uplink user data transmission again.\nSINR is used to represent quality.";
      yexte:takes-effect "Next cell unlock";
      yexte:precondition "Value can only be changed if administrativeState is LOCKED.";
      type erienmnrmgnbdu:ddt-GNBDU_NRCellDU_endcUlNrQualHyst;
      default 6;
    }
    leaf pZeroNomSrs {
      status current {
        yexte:preliminary;
      }
      description "Power control parameter P0 nominal for SRS transmissions.";
      yexte:takes-effect "Next cell unlock";
      type erienmnrmgnbdu:ddt-GNBDU_NRCellDU_pZeroNomSrs;
      default -110;
    }
    leaf qRxLevMinOffset {
      description "Offset applied to signaled Qrxlevmin.\nIf the attribute is set to empty, the value is not broadcast in SIB1, and the UE applies the default value of 0 dB for Qrxlevminoffset in 3GPP TS 38.304.";
      yexte:takes-effect "New connection";
      type erienmnrmgnbdu:ddt-GNBDU_NRCellDU_qRxLevMinOffset;
    }
    leaf cellLocalId {
      description "Used together with gNodeB identifier to identify NR cell in PLMN.\nMust be unique in gNodeB.\nUsed together with gNBId to form NCI.";
      mandatory true;
      yexte:takes-effect "Node restart";
      yexte:precondition "Value can only be changed if administrativeState is LOCKED.";
      yexte:dependencies "cellLocalId < 2^(36 - gNBIdLength)";
      type erienmnrmgnbdu:ddt-GNBDU_NRCellDU_cellLocalId;
    }
    container csiRsConfig2P {
      description "2-port CSI and associated port to antenna mapping settings.";
      erienmyext:enm-type STRUCT;
      uses erienmnrmgnbdu:struct-CsiRsConfig2P;
    } // end 'container csiRsConfig2P'
    leaf ssbSubCarrierSpacing {
      description "Sub-carrier spacing of the SSB.";
      yexte:takes-effect "Next cell unlock";
      yexte:precondition "Value can only be changed if administrativeState is LOCKED.";
      yexte:dependencies "Must be equal to subCarrierSpacing.";
      type erienmnrmgnbdu:ddt-GNBDU_NRCellDU_ssbSubCarrierSpacing;
      default 120;
    }
    leaf cellRange {
      description "Maximum signal path distance from BS where connection to UE can be set up and maintained.\nIf empty, system configures 1100 m for High-Band cells and 1600 m for Low-Band or Mid-Band cells.\nFor High-Band cells, maximum value of 4000 m is supported.\nValue greater than 15000 m when rachPreambleFormat is RACH_PREAMBLE_FORMAT_00 (F0) can cause random access performance degradation and interference to other channels.";
      yexte:takes-effect "Next cell unlock";
      yexte:precondition "Value can only be changed if administrativeState is LOCKED.";
      yexte:dependencies "For Low-Band, cellRange must be less than or equal to 10000 m if rachPreambleFormat is set to RACH_PREAMBLE_FORMAT_01 (B4).\nFor Mid-Band, cellRange must be less than or equal to 5000 m if rachPreambleFormat is set to RACH_PREAMBLE_FORMAT_01 (B4).\nFor High-Band cells, if value is greater than 1100 m:\n- rachPreambleFormat must be set to RACH_PREAMBLE_FORMAT_04 (C2).\n- license for Extended Propagation Delay Support High-Band must be present and the feature be active. Otherwise cell cannot be unlocked and there is alarm.";
      type erienmnrmgnbdu:ddt-GNBDU_NRCellDU_cellRange;
    }
    leaf essMbsfnSubframeConfig {
      description "MBSFN subframe configuration for eNodeB using four frames.\nESS NSA:\n110000 000000 100000 000000 (decimal 12584960).\nESS SA:\n100100 000000 110100 000000 (decimal 9440512) or\n100100 000000 111100 000000 (decimal 9441024).";
      yexte:takes-effect "Next cell unlock";
      type erienmnrmgnbdu:ddt-GNBDU_NRCellDU_essMbsfnSubframeConfig;
      default 9440512;
    }
    leaf ssbOffset {
      description "Offset of SSB transmission window.\nCorresponds to the SSB time domain position.\nFor ESS Low-Band, values 0 and 1 are allowed.\nOtherwise, value 0 is allowed.\n1 subframe = 1 ms.";
      yexte:takes-effect "Next cell unlock";
      yexte:precondition "Value can only be changed if administrativeState is LOCKED.";
      yexte:dependencies "Must be less than ssbPeriodicity.";
      type erienmnrmgnbdu:ddt-GNBDU_NRCellDU_ssbOffset;
      default 0;
    }
    leaf administrativeState {
      description "The administrative state.";
      yexte:disturbances "Changing this attribute to LOCKED causes loss of traffic.";
      yexte:dependencies "Attribute nRSectorCarrierRef must be set for administrativeState to change to UNLOCKED.";
      type erienmnrmgnbdu:enum-AdmState;
      default LOCKED;
    }
    leaf ssbFrequency {
      description "Frequency (NR-ARFCN) of the SSB transmission.\nThe frequency identifies the position of resource element RE=#0 (subcarrier #0) of resource block RB#10 of the SS block. The frequency must be positioned on the NR global frequency raster, as defined in 3GPP TS 38.101, and within bSChannelBwDL.\nIf set to 0, the system selects an SSB frequency, which is presented in ssbFrequencyAutoSelected.";
      yexte:takes-effect "Next cell unlock";
      yexte:precondition "Value can only be changed if administrativeState is LOCKED.";
      yexte:dependencies "For cells below 3 GHz, difference between NR-ARFCN value set for arfcnDL on NRSectorCarrier and for ssbFrequency must be zero or one of the following:\n- multiple of 3 for subCarrierSpacing 15 kHz, that is, (arfcnDL - ssbFrequency) mod 3 = 0\n- multiple of 6 for subCarrierSpacing 30 kHz, that is, (arfcnDL - ssbFrequency) mod 6 = 0.\nFor cells above 3 GHz, difference between NR-ARFCN value set for arfcnDL on NRSectorCarrier and for ssbFrequency must be zero or a multiple of two, that is, (arfcnDL - ssbFrequency) mod 2 = 0.";
      type erienmnrmgnbdu:ddt-GNBDU_NRCellDU_ssbFrequency;
      default 0;
    }
    leaf csiRsShiftingPrimary {
      description "Whether primary CSI-RS resource allocation shifting is activated.";
      yexte:takes-effect "Next cell unlock";
      type erienmnrmgnbdu:enum-CsiRsResourceShifting;
      default DEACTIVATED;
    }
    leaf endcUlLegSwitchEnabled {
      description "Whether EN-DC uplink leg switching is enabled.";
      yexte:takes-effect "Next cell unlock";
      yexte:precondition "Value can only be changed if administrativeState is LOCKED.";
      type boolean;
      default false;
    }
    leaf-list bandListManual {
      min-elements 0;
      max-elements 32;
      description "Configured list of bands to be used by the cell.\nIf present, this list will be used instead of bandList.\nBands specified in bandListManual must be intersection of possible bands for given cell configuration.\nPossible bands are displayed in bandList.\nIf bandList contains bands 77 and 78, bandListManual should contain either 77, 78 or 77 and 78.\nIf a band specified in bandListManual does not match cell configuration, cell will fail to unlock.";
      yexte:takes-effect "Next cell unlock";
      yexte:precondition "Value can only be changed if administrativeState is LOCKED.";
      type erienmnrmgnbdu:ddt-GNBDU_NRCellDU_bandListManual;
    }
    leaf siWindowLength {
      description "Length of SI scheduling window in slots.";
      yexte:takes-effect "Next cell unlock";
      yexte:precondition "Value can only be changed if administrativeState is LOCKED.";
      type erienmnrmgnbdu:ddt-GNBDU_NRCellDU_siWindowLength;
      default 20;
    }
    leaf-list nRSectorCarrierRef {
      min-elements 0;
      max-elements 2;
      description "Reference to an NRSectorCarrier MO.\nList of references is limited to maximum one reference.";
      yexte:takes-effect "Next MO unlock";
      yexte:precondition "Value can only be changed if administrativeState is LOCKED.";
      yexte:dependencies "Must be unique if configured, that is, two cells cannot reserve the same NRSectorCarrier.";
      erienmyext:enm-type MOREF;
      type string;
    }
    leaf pZeroNomPucch {
      description "Power control parameter P0 Nominal for PUCCH transmissions.";
      yexte:disturbances "Changing this attribute can cause loss of traffic.";
      yexte:takes-effect "New connection";
      type erienmnrmgnbdu:ddt-GNBDU_NRCellDU_pZeroNomPucch;
      default -114;
    }
    leaf rachPreambleFormat {
      description "RACH preamble format.\nIf empty, the system configures:\nFor Low-Band and Mid-Band, RACH_PREAMBLE_FORMAT_01 (B4)\nFor High-Band, RACH_PREAMBLE_FORMAT_03 (A3).\nFor Low-Band cells, RACH_PREAMBLE_FORMAT_00 (F0), RACH_PREAMBLE_FORMAT_01 (B4) and RACH_PREAMBLE_FORMAT_02 (F1) are allowed.\nFor Mid-Band cells, RACH_PREAMBLE_FORMAT_00 (F0) and RACH_PREAMBLE_FORMAT_01 (B4) are allowed.\nFor High-Band cells, RACH_PREAMBLE_FORMAT_03 (A3) and RACH_PREAMBLE_FORMAT_04 (C2) are allowed.\nValue RACH_PREAMBLE_FORMAT_01 (B4) is allowed for backward compatibility. The system applies RACH_PREAMBLE_FORMAT_03 (A3).";
      yexte:takes-effect "Next cell unlock";
      yexte:precondition "Value can only be changed if administrativeState is LOCKED.";
      yexte:dependencies "For Low-Band cells:\n- Must be set to RACH_PREAMBLE_FORMAT_00 (F0) or RACH_PREAMBLE_FORMAT_02 (F1) if cellRange is greater than 10000 m.\nFor Mid-Band cells:\n- Must be set to RACH_PREAMBLE_FORMAT_00 (F0) if cellRange is greater than 5000 m.\n- Must be set to RACH_PREAMBLE_FORMAT_01 (B4) if tddULDLPattern is set to TDD_ULDL_PATTERN_00 or TDD_ULDL_PATTERN_02.\nFor High-Band cells:\n- Must be set to RACH_PREAMBLE_FORMAT_04 (C2) if cellRange is greater than 1100 m.\n- For High-Band cells with RACH_PREAMBLE_FORMAT_04 (C2), license for Extended Propagation Delay Support High-Band must be present and the feature be active. Otherwise cell cannot be unlocked and there is alarm.";
      type erienmnrmgnbdu:enum-RachPreambleFormatType;
    }
    leaf nRPCI {
      description "The Physical Cell Identity (PCI) of the NR cell.";
      mandatory true;
      yexte:takes-effect "Next cell unlock";
      yexte:precondition "Value can only be changed if administrativeState is LOCKED.";
      type erienmnrmgnbdu:ddt-GNBDU_NRCellDU_nRPCI;
    }
    leaf ailgModType {
      description "PDSCH Air Interface Load Generator (AILG) modulation type.";
      yexte:takes-effect "Next cell unlock";
      yexte:precondition "Value can only be changed if administrativeState is LOCKED.";
      type erienmnrmgnbdu:enum-AilgModType;
      default AILG_MOD_QPSK;
    }
    leaf dlMaxMuMimoLayers {
      description "Maximum number of coscheduled downlink MU-MIMO layers at cell level.\nDownlink MU-MIMO is disabled when value is 0.\nOnly used if Downlink Multi-User MIMO Mid-Band is present and active.\nValue must be 0 for Low-Band and High-Band cells.";
      yexte:takes-effect "Next cell unlock";
      yexte:precondition "Value can only be changed if administrativeState is LOCKED.";
      yexte:dependencies "dlMaxMuMimoLayers can be greater than 0 if subCarrierSpacing is 30 (Mid-Band cell) and one of the following applies:\n- csiRsConfig32P,csiRsControl32Ports is EIGHT_TWO_N1AZ or FOUR_FOUR.\n- csiRsConfig16P,csiRsControl16Ports is EIGHT_ONE_N1AZ.";
      type erienmnrmgnbdu:ddt-GNBDU_NRCellDU_dlMaxMuMimoLayers;
      default 0;
    }
    leaf qQualMinOffset {
      description "Offset applied to signaled Qqualmin.\nIf the attribute is set to empty, the value is not broadcast in SIB1, and the UE applies the default value of 0 dB for Qqualminoffset in 3GPP TS 38.304.";
      yexte:takes-effect "Next cell unlock";
      yexte:precondition "Value can only be changed if administrativeState is LOCKED.";
      type erienmnrmgnbdu:ddt-GNBDU_NRCellDU_qQualMinOffset;
    }
    leaf secondaryCellOnly {
      description "Defines if cell prevents camping of UE instances on cell.";
      yexte:takes-effect "Next cell unlock";
      yexte:precondition "Value can only be changed if administrativeState is LOCKED.";
      yexte:dependencies "Can only be changed from default value when using Low-Band or Mid-Band.";
      type boolean;
      default true;
    }
    leaf-list bandList {
      min-elements 0;
      max-elements 32;
      config false;
      description "List of all NR bands the cells belongs to.\nCalculated by the system at cell unlock.\nIf bandListManual is configured, it will be used instead of bandList.";
      notife:notifiable-state-data true;
      type erienmnrmgnbdu:ddt-GNBDU_NRCellDU_bandList;
    }
    list pLMNIdList {
      min-elements 1;
      max-elements 12;
      key auto-generated-struct-key;
      leaf auto-generated-struct-key {
        type uint16;
        description "This leaf has been injected to allow for struct instances in a sequence to be ordered.";
        mandatory true;
      }
      description "PLMNs that can be served by NR cell.";
      erienmyext:enm-type STRUCT;
      uses erienmnrmgnbdu:struct-PLMNId;
    } // end 'list pLMNIdList'
    leaf puschStartPrbStrategy {
      description "Mitigate interference strategy that chooses one of following ways to allocate PRBs to UEs for UL.\n- From lower frequency band edge, START_LOWER_EDGE.\n- From higher frequency band edge, START_HIGHER_EDGE.\n- Both from lower and higher frequency band edges by random for each slot, RANDOM_START_LOWER_OR_HIGHER.\n- Random starting point for each slot for interference spreading over the whole band, RANDOM_START_WITHIN_BAND.";
      yexte:takes-effect "Next cell unlock";
      yexte:precondition "Value can only be changed if administrativeState is LOCKED.";
      type erienmnrmgnbdu:enum-StartPrbStrategy;
      default RANDOM_START_WITHIN_BAND;
    }
    leaf ssbDuration {
      description "Duration of SSB transmission.\n1 subframe = 1 ms.\nFor Low-Band cells, values 1 and 2 are allowed.\nFor Mid-Band, value 1 is allowed.\nFor High-Band, values 1, 3, and 4 are allowed.";
      yexte:takes-effect "Next cell unlock";
      yexte:precondition "Value can only be changed if administrativeState is LOCKED.";
      yexte:dependencies "For ESS Low-Band, if ssbOffset is 1, ssbDuration must be 1.";
      type erienmnrmgnbdu:ddt-GNBDU_NRCellDU_ssbDuration;
      default 1;
    }
    leaf-list nRSectorCarrier {
      min-elements 0;
      max-elements 2;
      status deprecated {
        yexte:status-information "Since 19.Q4. Replaced by nRSectorCarrierRef. Planned to be removed.";
      }
      description "Reference to an NRSectorCarrier MO.";
      yexte:takes-effect "Next cell unlock";
      yexte:precondition "Value can only be changed if administrativeState is LOCKED.";
      erienmyext:enm-type MOREF;
      type string;
    }
    leaf qQualMin {
      description "Minimum required quality level RSRQ in cell.\nIf set to empty, value is not broadcast in SIB1.";
      yexte:takes-effect "Next cell unlock";
      yexte:precondition "Value can only be changed if administrativeState is LOCKED.";
      type erienmnrmgnbdu:ddt-GNBDU_NRCellDU_qQualMin;
    }
    leaf advancedDlSuMimoEnabled {
      status current {
        yexte:preliminary;
      }
      description "Whether Advanced Downlink Single-User MIMO Mid-Band feature is enabled in cell.\nMaximum three cells with the functionality enabled are supported for each DU.";
      yexte:takes-effect "Next cell unlock";
      yexte:dependencies "If advancedDlSuMimoEnabled is true, tddUlDlPattern must have a different value than TDD_ULDL_PATTERN_00.\nIf advancedDlSuMimoEnabled is true, subCarrierSpacing must be 30.\nIf advancedDlSuMimoEnabled is true, tddSpecialSlotPattern must have a different value than TDD_SPECIAL_SLOT_PATTERN_00.";
      type boolean;
      default false;
    }
    leaf subCarrierSpacing {
      description "Sub-carrier spacing for common elements at cell level.";
      yexte:takes-effect "Next cell unlock";
      yexte:precondition "Value can only be changed if administrativeState is LOCKED.";
      yexte:dependencies "Must be 15 for Low-Band cells, 30 for Mid-Band cells, and 120 for High-Band cells.\nMust be 15 if cell uses NRSectorCarrier with essScPairId configured.\nMust be 30 if advancedDlSuMimoEnabled is true.";
      type erienmnrmgnbdu:ddt-GNBDU_NRCellDU_subCarrierSpacing;
      default 120;
    }
    leaf userLabel {
      description "Label for free use.";
      type erienmnrmgnbdu:ddt-UserLabel;
    }
    leaf maxUeSpeed {
      description "Expected maximum speed of moving UE.\nIf set to empty, the system configures a value depending on the cell configuration.\n- For High-Band, value is UP_TO_10KMPH.\n- For Low-Band or Mid-Band, value is UP_TO_100KMPH.\nFor High-Band, allowed values are UP_TO_10KMPH, UP_TO_50KMPH, UP_TO_100KMPH, or empty.\nFor Mid-Band and Low-Band, allowed values are UP_TO_100KMPH, UP_TO_200KMPH, UP_TO_350KMPH, UP_TO_500KMPH, or empty.\nValues UP_TO_200KMPH, UP_TO_350KMPH and UP_TO_500KMPH are only applicable if license for highSpeedUeLowMidband is present and the feature is active.";
      yexte:takes-effect "Next cell unlock";
      yexte:precondition "Value can only be changed if administrativeState is LOCKED.";
      yexte:dependencies "Values UP_TO_200KMPH, UP_TO_350KMPH and UP_TO_500KMPH can only be set if ul256qamEnabled is false.";
      type erienmnrmgnbdu:enum-MaxUeSpeed;
    }
    leaf tddSpecialSlotPattern {
      description "TDD special slot pattern.\nDefines the downlink, guard, and uplink symbols of special slot or slots.";
      yexte:takes-effect "Next cell unlock";
      yexte:precondition "Value can only be changed if administrativeState is LOCKED.";
      yexte:dependencies "For TDD_SPECIAL_SLOT_PATTERN_00, the following options apply:\n- tddUlDlPattern must be TDD_ULDL_PATTERN_00, TDD_ULDL_PATTERN_02, or TDD_ULDL_PATTERN_03.\n- advancedDlSuMimoEnabled must be false.\nFor TDD_SPECIAL_SLOT_PATTERN_01, the following options apply:\n- tddUlDlPattern must be TDD_ULDL_PATTERN_00, TDD_ULDL_PATTERN_01, TDD_ULDL_PATTERN_02, or TDD_ULDL_PATTERN_03.\nFor TDD_SPECIAL_SLOT_PATTERN_02, tddUlDlPattern must be TDD_ULDL_PATTERN_00, TDD_ULDL_PATTERN_02, or TDD_ULDL_PATTERN_03.\nFor TDD_SPECIAL_SLOT_PATTERN_03, tddUlDlPattern must be TDD_ULDL_PATTERN_04.\nFor TDD_SPECIAL_SLOT_PATTERN_04, tddUlDlPattern must be TDD_ULDL_PATTERN_01.\nFor TDD_SPECIAL_SLOT_PATTERN_05, tddUlDlPattern must be TDD_ULDL_PATTERN_01.";
      type erienmnrmgnbdu:enum-TddSpecialSlotPatternType;
      default TDD_SPECIAL_SLOT_PATTERN_00;
    }
    container csiRsConfig8P {
      description "Settings related to 8-port CSI and associated port to antenna mapping.";
      erienmyext:enm-type STRUCT;
      uses erienmnrmgnbdu:struct-CsiRsConfig8P;
    } // end 'container csiRsConfig8P'
    leaf cellState {
      config false;
      description "Current cellState.";
      notife:notifiable-state-data true;
      type erienmnrmgnbdu:enum-NRCellState;
    }
    leaf pointAFrequencyDlFdd {
      config false;
      description "Frequency representation of the NR-ARFCN used by pointAArfcnDlFdd.";
      notife:notifiable-state-data true;
      type erienmnrmgnbdu:ddt-GNBDU_NRCellDU_pointAFrequencyDlFdd;
    }
    leaf trsPowerBoosting {
      description "TRS power boosting.\nSelects different power boosting levels for CSI-RS transmission for tracking purposes.\nFor Low-Band and Mid-Band cells, values 0, 3, 4, and 6 are allowed.";
      yexte:takes-effect "Next cell unlock";
      yexte:precondition "Value can only be changed if administrativeState is LOCKED.";
      type erienmnrmgnbdu:ddt-GNBDU_NRCellDU_trsPowerBoosting;
      default 0;
    }
    leaf csiRsPeriodicity {
      description "Periodicity of CSI-RS transmission.";
      yexte:takes-effect "Next cell unlock";
      yexte:precondition "Value can only be changed if administrativeState is LOCKED.";
      yexte:dependencies "Must be 20 if cell uses NRSectorCarrier with essScPairId configured.";
      type erienmnrmgnbdu:ddt-GNBDU_NRCellDU_csiRsPeriodicity;
      default 40;
    }
    leaf endcDlLegSwitchEnabled {
      description "Whether EN-DC downlink leg switching is enabled.\nNot applicable in High-Band cells. EN-DC downlink leg switching is always enabled in High-Band cells.";
      yexte:takes-effect "Next cell unlock";
      type boolean;
      default true;
    }
    leaf serviceStatus {
      status deprecated {
        yexte:status-information "Since 20.Q1. Replaced by serviceState. Planned to be removed.";
      }
      config false;
      description "Current serviceStatus.";
      notife:notifiable-state-data true;
      type erienmnrmgnbdu:enum-NRCellServiceStatus;
    }
    leaf-list availabilityStatus {
      min-elements 0;
      config false;
      description "The availability status.\nIt contains details about operational state.";
      notife:notifiable-state-data true;
      type erienmnrmgnbdu:enum-AvailStatus;
    }
    leaf qRxLevMin {
      description "Required minimum received RSRP level in cell for cell selection or re-selection.";
      yexte:takes-effect "New connection";
      type erienmnrmgnbdu:ddt-GNBDU_NRCellDU_qRxLevMin;
      default -140;
    }
    leaf-list csiRsActivePortConfig {
      min-elements 0;
      max-elements 5;
      config false;
      description "Active CSI-RS resource configuration.\nThe active CSI-RS resource configuration has been determined based on the preferred HW/SW configurations of GNodeB.";
      notife:notifiable-state-data true;
      type erienmnrmgnbdu:enum-CsiRsActivePortConfig;
    }
    leaf pMax {
      description "UE uplink transmission power in the serving cell.\nParameter used to calculate Pcompensation at cell reselection.\nCorresponds to parameter PEMAX in 3GPP TS 38.101.\nThis attribute is broadcast in SIB1.\nThis attribute should be chosen less or equal to 23 dBm.\nIf the attribute is set to empty, value is not broadcast in SIB1 and the UE applies the maximum power according to 3GPP TS 38.101.";
      yexte:takes-effect "Next cell unlock";
      yexte:precondition "Value can only be changed if administrativeState is LOCKED.";
      type erienmnrmgnbdu:ddt-GNBDU_NRCellDU_pMax;
      default 23;
    }
    leaf pointAArfcnDlFdd {
      config false;
      description "Common reference point for the resource block grid of the DL carrier FDD cell.\nPointA value given by center frequency of resource element 0 in cell resource block 0 and indicated on a raster as NR-ARFCN.\nComputed from NRSectorCarrier::arfcnDL on cell unlock.";
      notife:notifiable-state-data true;
      type int32;
    }
    leaf dftSOfdmMsg3Enabled {
      description "Whether DFT-S-OFDM waveform support for Msg3 in the RACH process is enabled or not.\nOnly applicable for Low-Band and Mid-Band cells.";
      yexte:takes-effect "Next cell unlock";
      yexte:precondition "Value can only be changed if administrativeState is LOCKED.";
      type boolean;
      default false;
    }
    leaf ssbPeriodicity {
      description "Periodicity of SSB transmission.\n1 subframe = 1 ms.";
      yexte:takes-effect "Next cell unlock";
      yexte:precondition "Value can only be changed if administrativeState is LOCKED.";
      yexte:dependencies "For Low-Band and Mid-Band cells, ssbPeriodicity must be 10 or 20 ms. For High-Band cells, ssbPeriodicity must be 20 ms.\nMust be 20 ms if cell uses NRSectorCarrier with essScPairId configured.";
      type erienmnrmgnbdu:ddt-GNBDU_NRCellDU_ssbPeriodicity;
      default 20;
    }
    leaf ailgPdcchLoadLevel {
      description "Air Interface Load Generator (AILG) load level required for PDCCH.\nLoad level set to 0 means AILG for PDCCH is disabled.";
      yexte:takes-effect "Next cell unlock";
      yexte:precondition "Value can only be changed if administrativeState is LOCKED.";
      type erienmnrmgnbdu:ddt-GNBDU_NRCellDU_ailgPdcchLoadLevel;
      default 0;
    }
    leaf srsPeriodicity {
      status current {
        yexte:preliminary;
      }
      description "SRS periodicity in slots.";
      yexte:takes-effect "Next cell unlock";
      yexte:dependencies "If srsPeriodicity is 5, tddUlDlPattern must equal TDD_ULDL_PATTERN_02.";
      type erienmnrmgnbdu:ddt-GNBDU_NRCellDU_srsPeriodicity;
      default 40;
    }
    leaf pZeroUePuschOffset256Qam {
      description "Power offset to target-received PUSCH PSD for 256-QAM-capable UEs.\nRelevant when 256-QAM MCS Table 5.1.3.1-2 in 3GPP TS 38.214 is used.\nControls received SINR target.\nOnly applicable if ul256QamEnabled is true.";
      yexte:takes-effect "New connection";
      type erienmnrmgnbdu:ddt-GNBDU_NRCellDU_pZeroUePuschOffset256Qam;
      default 0;
    }
    leaf configuredEpsTAC {
      description "EPS TAC, is not broadcast and differs from 5G System (5GS) TAC.\nIf the attribute is set to empty, value is not sent to connected eNodeB via X2.";
      yexte:takes-effect "Next cell unlock";
      yexte:precondition "Value can only be changed if administrativeState is LOCKED.";
      type erienmnrmgnbdu:ddt-GNBDU_NRCellDU_configuredEpsTAC;
    }
    leaf ssbPowerBoost {
      description "Boost value to be applied to SSB power.\nOnly applicable if license for SSB Power Boost is present and the feature is active.\nFor High-Band cells, value must be less than or equal to 5 for 100 MHz cells and less than or equal to 2 for 50 MHz cells.\nValue must be 0 for Mid-Band and Low-Band cells.";
      yexte:takes-effect "Next cell unlock";
      yexte:precondition "Value can only be changed if administrativeState is LOCKED.";
      type erienmnrmgnbdu:ddt-GNBDU_NRCellDU_ssbPowerBoost;
      default 0;
    }
    leaf pdcchAilgEnabled {
      status obsolete {
        yexte:status-information "Since 20.Q2. Deprecated: Since 19.Q4. Planned to be removed.";
      }
      description "Whether Air Interface Load Generator (AILG) is enabled for PDCCH.";
      yexte:takes-effect "Next cell unlock";
      yexte:precondition "Value can only be changed if administrativeState is LOCKED.";
      type boolean;
      default false;
    }
    leaf rachRootSequence {
      description "First root sequence index for random access preamble generation.";
      yexte:takes-effect "Next cell unlock";
      yexte:precondition "Value can only be changed if administrativeState is LOCKED.";
      yexte:dependencies "rachRootSequence < 138 if rachPreambleFormat is set to RACH_PREAMBLE_FORMAT_01 (B4)";
      type erienmnrmgnbdu:ddt-GNBDU_NRCellDU_rachRootSequence;
      default 1;
    }
  } // end 'grouping moc-NRCellDU'
  grouping moc-Paging-keys {
    description "Key(s) for MOC Paging";
    leaf id {
      erienmyext:no-notification;
      description "The value component of the RDN.";
      mandatory true;
      yexte:ecim-name pagingId;
      type string;
    }
  } // end 'grouping moc-Paging-keys'
  grouping moc-Paging {
    description "Configuration parameters for Paging in the RBS.\n\nThe RDN of this MO is Paging=1.";
    leaf nS {
      description "Number of POs for one PF.\nFor ESS cells, value 4 is not allowed.";
      yexte:takes-effect "After all the cells in the same gNodeB-DU have been locked, and subsequently been unlocked.";
      type erienmnrmgnbdu:ddt-GNBDU_Paging_nS;
      default 1;
    }
    leaf defaultPagingCycle {
      description "Paging cycle T.\nUsed by the RBS and broadcasted in SIB1.";
      yexte:disturbances "If cell lock/unlock is not performed immediately after changing defaultPagingCycle, the number of discarded paging messages increases";
      yexte:takes-effect "After all the cells in the same gNodeB-DU have been locked, and subsequently been unlocked.";
      type erienmnrmgnbdu:ddt-GNBDU_Paging_defaultPagingCycle;
      default 128;
    }
    leaf n {
      description "Number of PFs in the DRX Cycle.\nE.g. one T is every radio frame, half T is every second radio frame, quarter T is every fourth radio frame etc.";
      yexte:takes-effect "After all the cells in the same gNodeB-DU have been locked, and subsequently been unlocked.";
      type erienmnrmgnbdu:enum-NValue;
      default T;
    }
  } // end 'grouping moc-Paging'
  grouping moc-QosPriorityMapping-keys {
    description "Key(s) for MOC QosPriorityMapping";
    leaf id {
      erienmyext:no-notification;
      description "The value component of the RDN.";
      mandatory true;
      yexte:ecim-name qosPriorityMappingId;
      type string;
    }
  } // end 'grouping moc-QosPriorityMapping-keys'
  grouping moc-QosPriorityMapping {
    description "Mapping from 5G QoS priorities to parameters that have impact on QoS.";
    leaf defaultDomain {
      erienmyext:no-notification;
      config false;
      description "Default Priority Domain.\nThe default Priority Domain is used for all unmapped Priority Levels.\nIf set to empty, value 48 will be used.";
      yexte:takes-effect "New connection";
      type erienmnrmgnbdu:ddt-GNBDU_QosPriorityMapping_defaultDomain;
    }
  } // end 'grouping moc-QosPriorityMapping'
  grouping moc-NRSectorCarrier-keys {
    description "Key(s) for MOC NRSectorCarrier";
    leaf id {
      erienmyext:no-notification;
      description "The value component of the RDN.";
      mandatory true;
      yexte:ecim-name nRSectorCarrierId;
      type string;
    }
  } // end 'grouping moc-NRSectorCarrier-keys'
  grouping moc-NRSectorCarrier {
    description "Power and frequency use of SectorEquipmentFunction that covers an area.\n\nCannot be deleted once txPowerPersistentLock has been set to true. See description of txPowerPersistentLock.";
    leaf altitude {
      description "Altitude of transmitter antenna position measured in meters.\nPositive value means height, negative value means depth.";
      type erienmnrmgnbdu:ddt-GNBDU_NRSectorCarrier_altitude;
    }
    leaf noOfTxAntennas {
      description "Number of antennas NRSectorCarrier uses for DL transmission.\nIf NRSectorCarrier MO instances have different number of TX antennas in node, attribute must be set to the number of TX antennas that this NRSectorCarrier uses.\nIf set to 0, and optional features enabling use of TX antennas are deactivated, NRSectorCarrier uses one TX branch.\nIf set to 0, and optional features enabling use of TX antennas are activated, NRSectorCarrier uses maximum number of TX antennas defined by operable features.\nSet to 0 for sectors equipped with AAS-capable radio units. System decides optimal number of transmit branches to use.\nFor Low-Band cells, value must be less than or equal to 4.\nFor Mid-Band cells, value must be less than or equal to 8.\nFor High-Band cells, value must be less than or equal to 2.";
      yexte:precondition "Value can only be changed if administrativeState is LOCKED.";
      type erienmnrmgnbdu:ddt-GNBDU_NRSectorCarrier_noOfTxAntennas;
      default 0;
    }
    leaf sectorEquipmentFunctionRef {
      description "Reference to a SectorEquipmentFunction MO.\nMust not be empty.";
      yexte:takes-effect "Next MO unlock";
      yexte:precondition "Value can only be changed if administrativeState is LOCKED.";
      erienmyext:enm-type MOREF;
      type string;
    }
    leaf arfcnUL {
      description "NR Absolute Radio Frequency Channel Number (NR-ARFCN) for uplink.\nIf arfcnUL is less than 600000, arfcnUL must be a multiple of 20, except for band n41 cells, where arfcnUL must be multiple of 6.\nOnly even values if between 600000 and 2016666.\nOnly odd values supported if above 2016667.";
      mandatory true;
      yexte:takes-effect "Next MO unlock";
      yexte:precondition "Value can only be changed if administrativeState is LOCKED.";
      type erienmnrmgnbdu:ddt-GNBDU_NRSectorCarrier_arfcnUL;
    }
    leaf latitude {
      description "Latitude of transmitter antenna position.\nPositive value means north, negative value means south.";
      type erienmnrmgnbdu:ddt-GNBDU_NRSectorCarrier_latitude;
    }
    leaf noOfUsedTxAntennas {
      config false;
      description "Number of used TX antennas.\nMaximum number is determined by noOfTxAntennas.\nEmpty means undefined.";
      notife:notifiable-state-data true;
      type int32;
    }
    leaf essScLocalId {
      description "The gNodeB internal ID attribute for SectorCarrier within Ericsson Shared Spectrum.\nMust be unique and non-zero in gNodeB for ESS NRSectorCarriers.";
      yexte:takes-effect "Next MO unlock";
      yexte:precondition "Value can only be changed if administrativeState is LOCKED.";
      type erienmnrmgnbdu:ddt-GNBDU_NRSectorCarrier_essScLocalId;
    }
    leaf-list rfBranchTxRef {
      min-elements 0;
      max-elements 16;
      description "References to instances of RfBranch MO.\nThe references are used for deterministic TX Carrier Allocation if noOfTxAntennas is grater than 0.\nIf no reference is specified Carrier allocation is based on the RF Branch MOM list (default behavior).";
      yexte:precondition "Value can only be changed if administrativeState is LOCKED.";
      erienmyext:enm-type MOREF;
      type string;
    }
    leaf maxEirpPsdThresh {
      status current {
        yexte:preliminary;
      }
      description "Maximum EIRP density threshold per MHz required for EIRP restriction.\nOnly applicable for limiting EIRP within maximum EIRP stated by Ericsson product specifications. Only recommended for markets with restrictions on EIRP.\nIf set to empty, EIRP restriction is not employed.";
      yexte:disturbances "Changing this attribute can cause loss of traffic.";
      yexte:takes-effect "Next MO unlock";
      yexte:precondition "Value can only be changed if administrativeState is LOCKED.";
      yexte:dependencies "If non-empty, then txPowerRatio must be 100.";
      type erienmnrmgnbdu:ddt-GNBDU_NRSectorCarrier_maxEirpPsdThresh;
    }
    leaf txPowerPersistentLock {
      description "Whether attribute configuredMaxTxPower is locked.\nWhen true, attribute configuredMaxTxPower cannot be changed and MO cannot be deleted.\nOnce set to true there is no possibility to change the value back to false unless a node re-integration is performed.";
      yexte:precondition "Can only be changed when the value is false and administrativeState is LOCKED.";
      type boolean;
      default false;
    }
    leaf txPowerState {
      erienmyext:no-notification;
      config false;
      description "DL output power state.";
      type erienmnrmgnbdu:enum-TxPowerState;
    }
    leaf administrativeState {
      description "The administrative state.";
      type erienmnrmgnbdu:enum-AdmState;
      default LOCKED;
    }
    leaf arfcnDL {
      description "NR Absolute Radio Frequency Channel Number (NR-ARFCN) for downlink.\nIf arfcnDL is less than 600000, arfcnDL must be a multiple of 20, except for band n41 cells, where arfcnDL must be multiple of 6.\nOnly even values if between 600000 and 2016666.\nOnly odd values supported if above 2016667.";
      mandatory true;
      yexte:takes-effect "Next MO unlock";
      yexte:precondition "Value can only be changed if administrativeState is LOCKED.";
      type erienmnrmgnbdu:ddt-GNBDU_NRSectorCarrier_arfcnDL;
    }
    leaf txPowerChangeRate {
      description "Change rate for DL output power to reach txPowerRatio.\nExample: if txPowerChangeRate is 5, a change of txPowerRatio from 100 to 80 will take 4 seconds.";
      yexte:takes-effect "In an unlocked NRSectorCarrier a change will take effect at the next change of txPowerRatio.";
      type erienmnrmgnbdu:ddt-GNBDU_NRSectorCarrier_txPowerChangeRate;
      default 1;
    }
    leaf-list availabilityStatus {
      min-elements 0;
      config false;
      description "The availability status.\nIt contains details about operationalState.";
      notife:notifiable-state-data true;
      type erienmnrmgnbdu:enum-AvailStatus;
    }
    leaf scaledTransmissionPower {
      config false;
      description "Used power at antenna reference point.\nCovers all downlink channels in all TX branches used simultaneously in NRSectorCarrier.\nRepresents the scaled power based on scaling factor, txPowerRatio, being applied to the allocated power at antenna reference point, maxTransmissionPower.\nValue is set every time txPowerState is set to STABLE.";
      notife:notifiable-state-data true;
      type erienmnrmgnbdu:ddt-GNBDU_NRSectorCarrier_scaledTransmissionPower;
    }
    container ulCalibrationData {
      description "Uplink antenna calibration information.";
      erienmyext:enm-type STRUCT;
      uses erienmnrmgnbdu:struct-UlCalibrationDataRO;
    } // end 'container ulCalibrationData'
    leaf longitude {
      description "Longitude of transmitter antenna position.\nPositive value means east, negative value means west.";
      type erienmnrmgnbdu:ddt-GNBDU_NRSectorCarrier_longitude;
    }
    container coverage {
      description "Transmission point coverage.\n\nDescribed by radius, bearing and opening angle.";
      erienmyext:enm-type STRUCT;
      uses erienmnrmgnbdu:struct-NRCoverage;
    } // end 'container coverage'
    leaf-list rfBranchRxRef {
      min-elements 0;
      max-elements 8;
      description "References to instances of RfBranch MO.\nThe references are used for deterministic RX Carrier Allocation if noOfRxAntennas is grater than 0.\nIf no reference is specified Carrier allocation is based on the RF Branch MOM list (default behavior).";
      yexte:precondition "Value can only be changed if administrativeState is LOCKED.";
      erienmyext:enm-type MOREF;
      type string;
    }
    leaf frequencyDL {
      config false;
      description "RF Reference Frequency of downlink channel.";
      notife:notifiable-state-data true;
      type erienmnrmgnbdu:ddt-GNBDU_NRSectorCarrier_frequencyDL;
    }
    leaf essScPairId {
      description "ID attribute that pairs SectorCarriers from gNodeB and eNodeB in Ericsson Spectrum Sharing (ESS).\nMust be unique within gNodeB and eNodeB.";
      yexte:takes-effect "Next MO unlock";
      yexte:precondition "Value can only be changed if administrativeState is LOCKED.";
      yexte:dependencies "If configured, arfcnDL must be different than arfcnUL, and bsChannelBwDL and bsChannelBwUL must be 10, 15, or 20.";
      type erienmnrmgnbdu:ddt-GNBDU_NRSectorCarrier_essScPairId;
    }
    leaf bSChannelBwUL {
      description "BS Channel bandwidth in MHz for uplink.";
      mandatory true;
      yexte:takes-effect "Next MO unlock";
      yexte:precondition "Value can only be changed if administrativeState is LOCKED.\nValue cannot be changed if reservedBy contains NRCellDU MO with administrativeState UNLOCKED.";
      yexte:dependencies "Must be equal to bsChannelBwDL.\nIf essScPairId is configured, supported values are 10, 15, and 20.";
      type erienmnrmgnbdu:ddt-GNBDU_NRSectorCarrier_bSChannelBwUL;
    }
    leaf radioTransmitPerfMode {
      description "Radio transmit operating mode.\nBetter performance can be achieved in DL according to cell traffic profile when radio is configured to maximum output level.\nGreen modes are power saving modes, which can reduce energy consumption when radio transmits in low power modes.";
      yexte:takes-effect "Next cell unlock";
      type erienmnrmgnbdu:enum-RadioOperatingModeEnhanced;
      default COVERAGE;
    }
    leaf txPowerRatio {
      description "DL output power ratio.\nDefault value is 100%. At unlock of NRSectorCarrier the current value will be set directly. When the value is changed on an unlocked NRSectorCarrier, the TX power changes with rate txPowerChangeRate.";
      yexte:disturbances "Changing this attribute can cause loss of traffic.";
      yexte:takes-effect "If a previous change in txPowerRatio is currently ongoing, the latest change will be started once the previous change has completed. Otherwise the current change will be started immediately.";
      yexte:dependencies "Must be 100 if maxEirpPsdThresh is non-empty.";
      type erienmnrmgnbdu:ddt-GNBDU_NRSectorCarrier_txPowerRatio;
      default 100;
    }
    leaf configuredMaxTxPower {
      description "Maximum output power to be used in an NRSectorCarrier.\nOutput power is evenly distributed over antenna connectors used for TX transmission allocated for NRSectorCarrier.\nFor High-Band and mmWave, EIRP value per cross-polarized beam pair must be used.\nNote: Setting configuredMaxTxPower has an impact on attribute maxTransmissionPower which displays the used output power.";
      yexte:takes-effect "Next MO unlock";
      yexte:precondition "Value can only be changed if administrativeState is LOCKED.";
      type erienmnrmgnbdu:ddt-GNBDU_NRSectorCarrier_configuredMaxTxPower;
      default 20000;
    }
    container dlCalibrationData {
      description "Downlink antenna calibration information.";
      erienmyext:enm-type STRUCT;
      uses erienmnrmgnbdu:struct-DlCalibrationDataRO;
    } // end 'container dlCalibrationData'
    leaf noOfUsedRxAntennas {
      config false;
      description "Number of used RX antennas.\nMaximum number is determined by noOfRxAntennas.\nEmpty means undefined.";
      notife:notifiable-state-data true;
      type int32;
    }
    leaf frequencyUL {
      config false;
      description "RF Reference Frequency of uplink channel.";
      notife:notifiable-state-data true;
      type erienmnrmgnbdu:ddt-GNBDU_NRSectorCarrier_frequencyUL;
    }
    list polygon {
      min-elements 0;
      max-elements 15;
      key auto-generated-struct-key;
      leaf auto-generated-struct-key {
        type uint16;
        description "This leaf has been injected to allow for struct instances in a sequence to be ordered.";
        mandatory true;
      }
      description "Coverage area of transmission point as a polygon used for UE positioning.\n\nEach polygon corner is described by latitude and longitude pair and represented with one position in the sequence. The other configured polygon corners follow in sequence. At least three configured corners required in polygon when function is active. Points must be connected in given order. Last point is connected to first point.";
      erienmyext:enm-type STRUCT;
      uses erienmnrmgnbdu:struct-NRPolygonCorner;
    } // end 'list polygon'
    leaf sectorEquipmentFunction {
      status deprecated {
        yexte:status-information "Since 19.Q4. Replaced by sectorEquipmentFunctionRef. Planned to be removed.";
      }
      description "Reference to a SectorEquipmentFunction MO.";
      yexte:takes-effect "Next MO unlock";
      yexte:precondition "Value can only be changed if administrativeState is LOCKED.";
      erienmyext:enm-type MOREF;
      type string;
    }
    leaf bSChannelBwDL {
      description "BS Channel bandwidth in MHz for downlink.";
      mandatory true;
      yexte:takes-effect "Next MO unlock";
      yexte:precondition "Value can only be changed if administrativeState is LOCKED.\nValue cannot be changed if reservedBy contains NRCellDU MO with administrativeState UNLOCKED.";
      yexte:dependencies "Must be equal to bsChannelBwUL.\nIf essScPairId is configured, supported values are 10, 15, and 20.";
      type erienmnrmgnbdu:ddt-GNBDU_NRSectorCarrier_bSChannelBwDL;
    }
    leaf noOfRxAntennas {
      description "Number of antennas that NRSectorCarrier uses for UL transmission.\nIf NRSectorCarrier MO instances have different number of RX antennas, attribute must be set to the number of RX antennas that this NRSectorCarrier uses.\nIf set to 0, and optional features enabling use of RX antennas are deactivated, NRSectorCarrier uses two RX branches.\nIf set to 0, and optional features enabling use of RX antennas are activated, NRSectorCarrier uses maximum number of RX antennas defined by operable features.\nSet to 0 for sectors equipped with AAS-capable radio units. System decides optimal number of receive branches to use.\nFor Low-Band cells, value must be less than or equal to 4.\nFor Mid-Band cells, value must be less than or equal to 8.\nFor High-Band cells, value must be less than or equal to 2.";
      yexte:precondition "Value can only be changed if administrativeState is LOCKED.";
      type erienmnrmgnbdu:ddt-GNBDU_NRSectorCarrier_noOfRxAntennas;
      default 0;
    }
    leaf-list reservedBy {
      min-elements 0;
      config false;
      description "Contains a list of MO instances that reserve this MO instance.";
      notife:notifiable-state-data true;
      erienmyext:enm-type MOREF;
      type string;
    }
    leaf operationalState {
      config false;
      description "The operational state.";
      notife:notifiable-state-data true;
      type erienmnrmgnbdu:enum-OperState;
    }
    leaf txDirection {
      description "The transmission direction.";
      yexte:takes-effect "Next MO unlock";
      yexte:precondition "Value can only be changed if administrativeState is LOCKED.";
      type erienmnrmgnbdu:enum-TxDirection;
      default DL_AND_UL;
    }
    leaf maxTransmissionPower {
      config false;
      description "Maximum possible power at antenna reference point.\nMeasured for all downlink channels in all TX branches used simultaneously in NRSectorCarrier.";
      notife:notifiable-state-data true;
      type erienmnrmgnbdu:ddt-GNBDU_NRSectorCarrier_maxTransmissionPower;
    }
  } // end 'grouping moc-NRSectorCarrier'
  grouping moc-RpUserPlaneTermination-keys {
    description "Key(s) for MOC RpUserPlaneTermination";
    leaf id {
      erienmyext:no-notification;
      description "The value component of the RDN.";
      mandatory true;
      yexte:ecim-name rpUserPlaneTerminationId;
      type string;
    }
  } // end 'grouping moc-RpUserPlaneTermination-keys'
  grouping moc-RpUserPlaneTermination {
    description "Local termination point of the radio processing user plane interface.\n\nSystem created when the first radio processing user plane link is established.\nSystem deleted when the last radio processing user plane link is released.\n\nThe RDN of this MO is RpUserPlaneTermination=1.";
  } // end 'grouping moc-RpUserPlaneTermination'
  grouping moc-ExtGNBDUPartnerFunction-keys {
    description "Key(s) for MOC ExtGNBDUPartnerFunction";
    leaf id {
      erienmyext:no-notification;
      description "The value component of the RDN.";
      mandatory true;
      yexte:ecim-name extGNBDUPartnerFunctionId;
      type string;
    }
  } // end 'grouping moc-ExtGNBDUPartnerFunction-keys'
  grouping moc-ExtGNBDUPartnerFunction {
    description "Grouping point of ERAN links to a partner gNodeB distributed unit.";
    leaf caVlanPortRef {
      description "Reference to an instance of VlanPort MO used by the InterMeLink.\nOverrides the value of GNBDUFunction::caVlandPortRef.";
      erienmyext:enm-type MOREF;
      type string;
    }
    leaf gNBDUId {
      yexte:restricted;
      description "Unique identifier for the 3GPP distributed unit in a partner gNodeB.";
      mandatory true;
      type erienmnrmgnbdu:ddt-GNBDU_ExtGNBDUPartnerFunction_gNBDUId;
    }
    leaf gNBId {
      yexte:restricted;
      description "Identity of partner gNodeB within a PLMN.";
      mandatory true;
      yexte:takes-effect "Next MO unlock";
      yexte:dependencies "The gNBId must be equal or less than 2^gNBIdLength - 1.";
      type erienmnrmgnbdu:ddt-GNBDU_ExtGNBDUPartnerFunction_gNBId;
    }
    leaf gNBDUName {
      config false;
      description "Distributed unit name.";
      notife:notifiable-state-data true;
      type string;
    }
    leaf gNBIdLength {
      yexte:restricted;
      description "Length of gNBId bit string representation.\nIf gNBId bit representation exceeds 22 bits, gNBIdLength value must be at least minimum bit length that can accommodate gNBId.";
      yexte:dependencies "The gNBId must be equal or less than 2^gNBIdLength - 1.";
      type erienmnrmgnbdu:ddt-GNBDU_ExtGNBDUPartnerFunction_gNBIdLength;
      default 22;
    }
  } // end 'grouping moc-ExtGNBDUPartnerFunction'
  grouping moc-InterMeLink-keys {
    description "Key(s) for MOC InterMeLink";
    leaf id {
      erienmyext:no-notification;
      description "The value component of the RDN.";
      mandatory true;
      yexte:ecim-name interMeLinkId;
      type string;
    }
  } // end 'grouping moc-InterMeLink-keys'
  grouping moc-InterMeLink {
    description "ERAN Link between a local ME and a neighboring ME.\n\nSystem created when an inter ME link is established.\nSystem deleted when an inter ME link is released.\n\nThe RDNs of these MOs are InterMeLink=1 to InterMeLink=9.";
    leaf localEndpointIdentity {
      config false;
      description "Local hardware board that terminates inter-ME link.";
      notife:notifiable-state-data true;
      type string;
    }
    leaf linkLatency15minHWM {
      config false;
      description "Highest latency measured during last completed 15-minute period.";
      notife:notifiable-state-data true;
      type erienmnrmgnbdu:ddt-GNBDU_InterMeLink_linkLatency15minHWM;
    }
    leaf vlanId {
      config false;
      description "VLAN ID in VLAN tag of packets transmitted over Ethernet.";
      notife:notifiable-state-data true;
      type int32;
    }
    leaf remoteEndpointIdentity {
      config false;
      description "Remote hardware board that terminates inter-ME link.";
      notife:notifiable-state-data true;
      type string;
    }
    leaf-list availabilityStatus {
      min-elements 0;
      config false;
      description "The availability status.\nIt contains details about operationalState.";
      notife:notifiable-state-data true;
      type erienmnrmgnbdu:enum-AvailStatus;
    }
    leaf operationalState {
      config false;
      description "The operational state.";
      notife:notifiable-state-data true;
      type erienmnrmgnbdu:enum-OperState;
    }
    leaf linkLatency1minAvg {
      config false;
      description "Average latency measured during last 1-minute period.";
      notife:notifiable-state-data true;
      type erienmnrmgnbdu:ddt-GNBDU_InterMeLink_linkLatency1minAvg;
    }
    leaf linkLatency24hrsHWM {
      config false;
      description "Highest latency measured during last 24 hours.";
      notife:notifiable-state-data true;
      type erienmnrmgnbdu:ddt-GNBDU_InterMeLink_linkLatency24hrsHWM;
    }
  } // end 'grouping moc-InterMeLink'
  grouping moc-SchedulingProfile-keys {
    description "Key(s) for MOC SchedulingProfile";
    leaf id {
      status current {
        yexte:preliminary;
      }
      erienmyext:no-notification;
      description "The value component of the RDN.";
      mandatory true;
      yexte:ecim-name schedulingProfileId;
      type string;
    }
  } // end 'grouping moc-SchedulingProfile-keys'
  grouping moc-SchedulingProfile {
    description "Scheduling profile used for current connection.\n\nIf DU5qi::schedulingProfileRef is non-empty, attributes from referred MO instance are used.\nIf DU5qi::schedulingProfileRef is empty, attribute default values according to MO class definition are used.";
    leaf userLabel {
      status current {
        yexte:preliminary;
      }
      description "Label for free use.";
      type erienmnrmgnbdu:ddt-UserLabel;
    }
    leaf relativePriority {
      status current {
        yexte:preliminary;
      }
      description "Relative priority associated with scheduling profile.";
      yexte:takes-effect "New connection";
      type erienmnrmgnbdu:ddt-GNBDU_SchedulingProfile_relativePriority;
      default 1;
    }
    leaf-list reservedBy {
      min-elements 0;
      status current {
        yexte:preliminary;
      }
      config false;
      description "Contains a list of MO instances that reserve this MO instance.";
      notife:notifiable-state-data true;
      erienmyext:enm-type MOREF;
      type string;
    }
  } // end 'grouping moc-SchedulingProfile'
  grouping moc-SignalingRadioBearer-keys {
    description "Key(s) for MOC SignalingRadioBearer";
    leaf id {
      erienmyext:no-notification;
      description "The value component of the RDN.";
      mandatory true;
      yexte:ecim-name signalingRadioBearerId;
      type string;
    }
  } // end 'grouping moc-SignalingRadioBearer-keys'
  grouping moc-SignalingRadioBearer {
    description "Parameters related to Signaling Radio Bearer.\n\nThe RDN of this MO is SignalingRadioBearer=1.";
    leaf tReassemblyUl {
      description "Timer for receiving side of AM RLC and receiving UM RLC.\nDetects loss of RLC PDUs at lower layers.";
      yexte:takes-effect "New connection";
      type erienmnrmgnbdu:ddt-GNBDU_SignalingRadioBearer_tReassemblyUl;
      default 35;
    }
    leaf tReassemblyDl {
      description "Timer for the UE used by the receiving side of AM RLC and receiving UM RLC.\nDetects loss of RLC PDUs at lower layers.";
      yexte:takes-effect "New connection";
      type erienmnrmgnbdu:ddt-GNBDU_SignalingRadioBearer_tReassemblyDl;
      default 35;
    }
    leaf tPollRetransmitUl {
      description "Timer for the UE to supervise the poll for STATUS PDU.\nAM RLC UL transmitter waits for RLC STATUS feedback after sending a poll for STATUS before retransmitting the poll.";
      yexte:takes-effect "New connection";
      type erienmnrmgnbdu:ddt-GNBDU_SignalingRadioBearer_tPollRetransmitUl;
      default 45;
    }
    leaf dlMaxRetxThreshold {
      description "Maximum number of AM RLC DL retransmissions.\nWhen this value is reached, AM RLC DL retransmission is stopped and RRC is notified.";
      yexte:takes-effect "New connection";
      type erienmnrmgnbdu:ddt-GNBDU_SignalingRadioBearer_dlMaxRetxThreshold;
      default 8;
    }
    leaf tPollRetransmitDl {
      description "Timer supervising the poll for STATUS PDU.\nAM RLC DL transmitter to wait for RLC STATUS feedback after sending a poll for STATUS before retransmitting the poll.";
      yexte:takes-effect "New connection";
      type erienmnrmgnbdu:ddt-GNBDU_SignalingRadioBearer_tPollRetransmitDl;
      default 45;
    }
    leaf ulMaxRetxThreshold {
      description "Maximum number of AM RLC UL retransmissions.\nWhen this value is reached, AM RLC UL retransmission is stopped and RRC is notified.";
      yexte:takes-effect "New connection";
      type erienmnrmgnbdu:ddt-GNBDU_SignalingRadioBearer_ulMaxRetxThreshold;
      default 8;
    }
  } // end 'grouping moc-SignalingRadioBearer'
  grouping moc-UeCC-keys {
    description "Key(s) for MOC UeCC";
    leaf id {
      status current {
        yexte:preliminary;
      }
      erienmyext:no-notification;
      description "The value component of the RDN.";
      mandatory true;
      yexte:ecim-name ueCCId;
      type string;
    }
  } // end 'grouping moc-UeCC-keys'
  grouping moc-UeCC {
    description "Container class for UE Connection Control (UeCC) attributes and UeCC profile classes.\n\nThe RDN of this MO must always be UeCC=1.";
  } // end 'grouping moc-UeCC'
  grouping moc-DU5qi-keys {
    description "Key(s) for MOC DU5qi";
    leaf id {
      erienmyext:no-notification;
      description "The value component of the RDN.";
      mandatory true;
      yexte:ecim-name dU5qiId;
      type string;
    }
  } // end 'grouping moc-DU5qi-keys'
  grouping moc-DU5qi {
    description "QoS configuration corresponding to 3GPP-defined and operator-defined 5QI profiles.\n\nMaximum number of operator-defined profiles is 9.\n\nEach profile can be present once in each table.";
    leaf serviceType {
      status current {
        yexte:preliminary;
      }
      description "Service of flow.";
      yexte:dependencies "VOIP if profile5qi is 1.\nIMS_SIGNALING if profile5qi is 5.\nPTT if profile5qi is 65 or 66.\nMC_SIGNALING if profile5qi is 69.\nUNDEFINED if profile5qi is 2, 3, 4, 6 ,7, 8, 9, 67, 70, 79, 80, 82, 83, 84 or 85.";
      type erienmnrmgnbdu:enum-ServiceType;
      default UNDEFINED;
    }
    leaf userLabel {
      status current {
        yexte:preliminary;
      }
      description "Label for free use.";
      type erienmnrmgnbdu:ddt-UserLabel;
    }
    leaf profile5qi {
      description "5G QoS Identifier unique within a table.\nFor 3GPP-defined 5QIs, 5QI can be 1, 2, 3, 4, 5, 6, 7, 8, 9, 65, 66, 67, 69, 70, 79, 80, 82, 83, 84 or 85.";
      mandatory true;
      yexte:dependencies "Value must be unique in 5qiTable.\nFor 3GPP-defined profiles:\n-profile5qi=1 aqmMode must be MODE2, maxDataBurstVolume must be empty, averagingWindow must be set and serviceType must be VOIP.\n-profile5qi=2 aqmMode must be MODE2, maxDataBurstVolume must be empty, averagingWindow must be set and serviceType must be UNDEFINED.\n-profile5qi=3 aqmMode must be MODE2, maxDataBurstVolume must be empty, averagingWindow must be set and serviceType must be UNDEFINED.\n-profile5qi=4 aqmMode must be MODE2, maxDataBurstVolume must be empty, averagingWindow must be set and serviceType must be UNDEFINED.\n-profile5qi=5 aqmMode must be OFF, maxDataBurstVolume must be empty, averagingWindow must be empty and serviceType must be IMS_SIGNALING.\n-profile5qi=6 aqmMode must be MODE1, maxDataBurstVolume must be empty, averagingWindow must be empty and serviceType must be UNDEFINED.\n-profile5qi=7 aqmMode must be MODE1, maxDataBurstVolume must be empty, averagingWindow must be empty and serviceType must be UNDEFINED.\n-profile5qi=8 aqmMode must be MODE1, maxDataBurstVolume must be empty, averagingWindow must be empty and serviceType must be UNDEFINED.\n-profile5qi=9 aqmMode must be MODE1, maxDataBurstVolume must be empty, averagingWindow must be empty and serviceType must be UNDEFINED.\n-profile5qi=65 aqmMode must be MODE2, maxDataBurstVolume must be empty, averagingWindow must be set and serviceType must be PTT.\n-profile5qi=66 aqmMode must be MODE2, maxDataBurstVolume must be empty, averagingWindow must be set and serviceType must be PTT.\n-profile5qi=67 aqmMode must be MODE2, maxDataBurstVolume must be empty, averagingWindow must be set and serviceType must be UNDEFINED.\n-profile5qi=69 aqmMode must be OFF, maxDataBurstVolume must be empty, averagingWindow must be empty and serviceType must be MC_SIGNALING.\n-profile5qi=70 aqmMode must be MODE1, maxDataBurstVolume must be empty, averagingWindow must be empty and serviceType must be UNDEFINED.\n-profile5qi=79 aqmMode must be MODE1, maxDataBurstVolume must be empty, averagingWindow must be empty and serviceType must be UNDEFINED.\n-profile5qi=80 aqmMode must be MODE1, maxDataBurstVolume must be empty, averagingWindow must be empty and serviceType must be UNDEFINED.\n-profile5qi=82 aqmMode must be MODE2, maxDataBurstVolume must be set, averagingWindow must be set and serviceType must be UNDEFINED.\n-profile5qi=83 aqmMode must be MODE2, maxDataBurstVolume must be set, averagingWindow must be set and serviceType must be UNDEFINED.\n-profile5qi=84 aqmMode must be MODE2, maxDataBurstVolume must be set, averagingWindow must be set and serviceType must be UNDEFINED.\n-profile5qi=85 aqmMode must be MODE2, maxDataBurstVolume must be set, averagingWindow must be set and serviceType must be UNDEFINED.";
      type erienmnrmgnbdu:ddt-GNBDU_DU5qi_profile5qi;
    }
    leaf tReassemblyUl {
      description "UL Radio Link Control (RLC) timer reassembly.\nFollowing values are recommended:\n-35 if profile5qi is 1, 2, 65, 66, 67 or 79.\n-25 if profile5qi is 3, 4, 5, 6, 7, 8, 9, 69, 70 or 84.\n-8 if profile5qi is 80, 82 or 83.\n-4 if profile5qi is 85.";
      type erienmnrmgnbdu:ddt-GNBDU_DU5qi_tReassemblyUl;
      default 25;
    }
    leaf maxDataBurstVolume {
      status current {
        yexte:preliminary;
      }
      description "Maximum data burst volume.\nFollowing values are recommended:\n-255 if profile5qi is 82 or 85.\n-1354 if profile5qi is 83 or 84.";
      yexte:dependencies "Must not be empty if profile5qi is 82, 83, 84 or 85.\nMust be empty if profile5qi is 1, 2, 3, 4, 5, 6, 7, 8, 9, 65, 66, 67, 69, 70, 79 or 80.";
      type erienmnrmgnbdu:ddt-GNBDU_DU5qi_maxDataBurstVolume;
    }
    leaf averagingWindow {
      status current {
        yexte:preliminary;
      }
      description "Averaging Window.\nRecommended value is 2000 if profile5qi is 1, 2, 3, 4, 65, 66, 67, 82, 83, 84 or 85.";
      yexte:dependencies "Must be empty if profile5qi is 5, 6, 7, 8, 9, 69, 70, 79 or 80.\nMust not be empty if profile5qi is 1, 2, 3, 4, 65, 66, 67, 82, 83, 84 or 85.";
      type erienmnrmgnbdu:ddt-GNBDU_DU5qi_averagingWindow;
    }
    leaf packetDelayBudget {
      description "Contribution from gNodeB to PDB for 5QI.\nPacket delays outside gNodeB are excluded, for example, in transport network.\nFollowing values are recommended:\n-80 if profile5qi is 1, 5, 7, 66 or 67.\n-130 if profile5qi is 2.\n-30 if profile5qi is 3 or 79.\n-280 if profile5qi is 4, 6, 8 or 9.\n-65 if profile5qi is 65.\n-50 if profile5qi is 69.\n-190 if profile5qi is 70.\n-8 if profile5qi is 80 or 83.\n-9 if profile5qi is 82.\n-25 if profile5qi is 84.\n-3 if profile5qi is 85.";
      type erienmnrmgnbdu:ddt-GNBDU_DU5qi_packetDelayBudget;
      default 280;
    }
    leaf rlcSNLength {
      description "Radio Link Control (RLC) SN field size.\nFollowing values are recommended:\n-12 if profile5qi is 3, 4, 5, 6, 7, 8, 9, 69 or 70.\n-6 if profile5qi is 1, 2, 65, 66, 67. 79, 80, 82, 83, 84 or 85.";
      yexte:dependencies "Must be set to 6 or 12 if rlcMode is set to UM in the corresponding CUCP5qi profile.\nMust be set to 12 or 18 if rlcMode is set to AM.\nMust be set to a value lower than or equal to the setting of pdcpSNLength in CU-CP MOM.";
      type erienmnrmgnbdu:ddt-GNBDU_DU5qi_rlcSNLength;
      default 18;
    }
    leaf packetDelayBudgetOffset {
      status current {
        yexte:preliminary;
      }
      description "Offset added to PDB.\nFollowing values are recommended:\n-0 if profile5qi is 2, 3, 4, 5, 6, 7, 8, 9, 65, 66, 67, 69, 70, 79, 80, 82, 83, 84 or 85.\n-50 if profile5qi is 1.";
      type erienmnrmgnbdu:ddt-GNBDU_DU5qi_packetDelayBudgetOffset;
      default 0;
    }
    leaf dscp {
      status current {
        yexte:preliminary;
      }
      description "DSCP for 5QI.\nCorresponds to mappings from RAN QoS to transport network QoS.\nFollowing values are recommended:\n46 if profile5qi is 1, 65, 66 or 67.\n36 if profile5qi is 2.\n34 if profile5qi is 3.\n38 if profile5qi is 4.\n40 if profile5qi is 5 or 69.\n26 if profile5qi is 6 or 70.\n10 if profile5qi is 7.\n12 if profile5qi is 8.\n14 if profile5qi is 9.";
      type erienmnrmgnbdu:ddt-GNBDU_DU5qi_dscp;
      default 12;
    }
    leaf tReassemblyDl {
      description "DL Radio Link Control (RLC) timer reassembly.\nFollowing values are recommended:\n-35 if profile5qi is 1, 2, 65, 66, 67 or 79.\n-25 if profile5qi is 3, 4, 5, 6, 7, 8, 9, 69, 70 or 84.\n-8 if profile5qi is 80, 82 or 83.\n-4 if profile5qi is 85.";
      type erienmnrmgnbdu:ddt-GNBDU_DU5qi_tReassemblyDl;
      default 25;
    }
    leaf aqmMode {
      status current {
        yexte:preliminary;
      }
      description "AQM mode.";
      yexte:dependencies "MODE2 for profile5qi is 1, 2, 3, 4, 65, 66, 67, 82, 83, 84 or 85.\nMODE1 for profile5qi is 6, 7, 8, 9, 70, 79 or 80.\nOFF for profile5qi is 5 or 69.";
      type erienmnrmgnbdu:enum-AqmMode;
      default MODE1;
    }
    leaf priorityLevel {
      description "5QI-related priority.\nFollowing values are recommended:\n-20 if profile5qi is 1 or 66.\n-40 if profile5qi is 2.\n-30 if profile5qi is 3.\n-50 if profile5qi is 4.\n-10 if profile5qi is 5.\n-60 if profile5qi is 6.\n-70 if profile5qi is 7.\n-80 if profile5qi is 8.\n-90 if profile5qi is 9.\n-7 if profile5qi is 65.\n-15 if profile5qi is 67.\n-5 if profile5qi is 69.\n-55 if profile5qi is 70.\n-65 if profile5qi is 79.\n-68 if profile5qi is 80.\n-19 if profile5qi is 82.\n-22 if profile5qi is 83.\n-24 if profile5qi is 84.\n-21 if profile5qi is 85.";
      type erienmnrmgnbdu:ddt-GNBDU_DU5qi_priorityLevel;
      default 80;
    }
    leaf logicalChannelGroupRef {
      status obsolete {
        yexte:status-information "Since 20.Q2. Planned to be removed.";
      }
      description "One instance of LogicalChannelGroup.\nAssigns Logical Channel Group to QoS Class Indicator (5QI).";
      erienmyext:enm-type MOREF;
      type string;
    }
    leaf logicalChannelGroupId {
      description "One instance of LogicalChannelGroup.\nAssigns logical channel group to QoS Class Indicator (5QI).\nFollowing values are recommended:\n0 if SRB.\n1 if profile5qi is 1, 2, 65, or 66.\n2 if profile5qi is 3, 4, or 75.\n3 if profile5qi is 5 or 69.\n4 if profile5qi is 70 or 79.\n5 if profile5qi is 6, 7, 8, or 9.\n6 if profile5qi is 80, 82, 83, 84, or 85.\n7 if profile5qi is 67, or operator defined 5QI.";
      yexte:takes-effect "New connection";
      type erienmnrmgnbdu:ddt-GNBDU_DU5qi_logicalChannelGroupId;
      default 5;
    }
    leaf schedulingProfileRef {
      status current {
        yexte:preliminary;
      }
      description "Reference to an instance of SchedulingProfile MO.\nIf reference is non-empty, attributes from referred MO instance are used.\nIf reference is empty, attribute default values according to MO class definition are used.\nReferenced schedulingProfile must be under UeCC MO under same GNBDUFunction as DU5qi.";
      yexte:takes-effect "New connection";
      erienmyext:enm-type MOREF;
      type string;
    }
  } // end 'grouping moc-DU5qi'
  grouping moc-RpUserPlaneLink-keys {
    description "Key(s) for MOC RpUserPlaneLink";
    leaf id {
      erienmyext:no-notification;
      description "The value component of the RDN.";
      mandatory true;
      yexte:ecim-name rpUserPlaneLinkId;
      type string;
    }
  } // end 'grouping moc-RpUserPlaneLink-keys'
  grouping moc-RpUserPlaneLink {
    description "User plane link for the radio processing interface.\n\nSystem created when a radio processing user plane link is established.\nSystem deleted when a radio processing user plane link is released.\n\nThe RDN of this MO is RpUserPlaneLink=[Remote Managed Element Identity].";
    leaf remoteEndPoint {
      config false;
      description "Remote GTP transport address.\nIP address can be an IPv4 or an IPv6 address.";
      notife:notifiable-state-data true;
      type erienmnrmgnbdu:ddt-GNBDU_RpUserPlaneLink_remoteEndPoint;
    }
    leaf localEndPoint {
      config false;
      description "Local GTP transport address.\nIP address can be an IPv4 or an IPv6 address.";
      notife:notifiable-state-data true;
      type erienmnrmgnbdu:ddt-GNBDU_RpUserPlaneLink_localEndPoint;
    }
  } // end 'grouping moc-RpUserPlaneLink'
  grouping moc-PriorityDomainMapping-keys {
    description "Key(s) for MOC PriorityDomainMapping";
    leaf id {
      erienmyext:no-notification;
      description "The value component of the RDN.";
      mandatory true;
      yexte:ecim-name priorityDomainMappingId;
      type string;
    }
  } // end 'grouping moc-PriorityDomainMapping-keys'
  grouping moc-PriorityDomainMapping {
    description "Mapping from 5G QoS priority level to internal parameters that have absolute priority realization.";
    leaf priorityDomain {
      description "Internal representation of absolute priority differentiation.\nA connection using Priority Domain A always has a higher priority than a connection using Priority Domain B if A < B. Multiple PriorityDomainMapping instances cannot have the same priorityDomain value configured.";
      yexte:takes-effect "New connection";
      type erienmnrmgnbdu:ddt-GNBDU_PriorityDomainMapping_priorityDomain;
      default 48;
    }
    leaf-list priorityLevelsList {
      min-elements 0;
      max-elements 127;
      description "List of priority levels to realize using the specified Priority Domain.\nThe same priority level value cannot be configured in multiple priorityLevelsLists.";
      yexte:takes-effect "New connection";
      type erienmnrmgnbdu:ddt-GNBDU_PriorityDomainMapping_priorityLevelsList;
    }
  } // end 'grouping moc-PriorityDomainMapping'
  grouping moc-ResourcePartitionMember-keys {
    description "Key(s) for MOC ResourcePartitionMember";
    leaf id {
      erienmyext:no-notification;
      description "The value component of the RDN.";
      mandatory true;
      yexte:ecim-name resourcePartitionMemberId;
      type string;
    }
  } // end 'grouping moc-ResourcePartitionMember-keys'
  grouping moc-ResourcePartitionMember {
    description "Set of member information of resource partition.";
    list sNSSAIList {
      min-elements 0;
      max-elements 1024;
      key auto-generated-struct-key;
      leaf auto-generated-struct-key {
        type uint16;
        description "This leaf has been injected to allow for struct instances in a sequence to be ordered.";
        mandatory true;
      }
      description "List of Single Network Slice Selection Assistance Information (S-NSSAI).";
      erienmyext:enm-type STRUCT;
      uses erienmnrmgnbdu:struct-SliceSelectionAssistInfo;
    } // end 'list sNSSAIList'
    leaf endpointResourceRef {
      description "Reference to EndpointResource MO instance.\nThe reference setting defines the Transport Network configuration for specific PLMN or NSSAI.\nIf this reference is empty, attribute GNBDUFunction::endpointResourceRef is used.\nCannot refer to EndpointResource MO which has LocalSctpEndpoint::interfaceUsed set to F1. F1 SctpEndpoint can only be referenced from GNBDUFunction::endpointResourceRef.";
      yexte:takes-effect "Node restart";
      yexte:dependencies "Must be empty if ResourcePartition::related5qiTableRef is non-empty.\nIf endpointResourceRef is non-empty, the following dependencies apply:\n- pLMNIdList must be non-empty.\n- Only sNSSAIList or pLMNIdList can have more than one element.\n- If sNSSAIList is empty, PLMNId must be unique among ResourcePartitionMember MOs.\n- If sNSSAIList is non-empty, the combination of PLMNId and SliceSelectionAssistInfo must be unique among ResourcePartitionMember MOs.";
      erienmyext:enm-type MOREF;
      type string;
    }
    list pLMNIdList {
      min-elements 0;
      max-elements 12;
      key auto-generated-struct-key;
      leaf auto-generated-struct-key {
        type uint16;
        description "This leaf has been injected to allow for struct instances in a sequence to be ordered.";
        mandatory true;
      }
      description "List of PLMN identifier.";
      erienmyext:enm-type STRUCT;
      uses erienmnrmgnbdu:struct-PLMNId;
    } // end 'list pLMNIdList'
  } // end 'grouping moc-ResourcePartitionMember'
  grouping moc-DUResourcePartitions-keys {
    description "Key(s) for MOC DUResourcePartitions";
    leaf id {
      status obsolete {
        yexte:status-information "Since 20.Q2. Deprecated: Since 19.Q4. Planned to be removed.";
      }
      erienmyext:no-notification;
      description "The value component of the RDN.";
      mandatory true;
      yexte:ecim-name dUResourcePartitionsId;
      type string;
    }
  } // end 'grouping moc-DUResourcePartitions-keys'
  grouping moc-DUResourcePartitions {
    description "Set of resource partitions.";
  } // end 'grouping moc-DUResourcePartitions'
  augment /erienmnrmcomtop:ManagedElement/erienmnrmgnbdu:GNBDUFunction/erienmnrmgnbdu:EndpointResource {
    list LocalIpEndpoint {
      key id;
      description "Local transport network endpoint for user plane interface.";
      erienmyext:enm-type MOC;
      uses moc-LocalIpEndpoint-keys;
      container attributes {
        description "Attributes for LocalIpEndpoint";
        uses moc-LocalIpEndpoint;
      } // end 'container attributes'
    } // end 'list LocalIpEndpoint'
  }
  augment /erienmnrmcomtop:ManagedElement/erienmnrmgnbdu:GNBDUFunction {
    list RadioBearerTable {
      key id;
      max-elements 1;
      description "Container for radio bearer configurations.\n\nThe RDN of this MO is RadioBearerTable=1.";
      yexte:is-system-created;
      erienmyext:enm-type MOC;
      uses moc-RadioBearerTable-keys;
    } // end 'list RadioBearerTable'
  }
  augment /erienmnrmcomtop:ManagedElement/erienmnrmgnbdu:GNBDUFunction {
    list RedundantGNodeB {
      key id;
      max-elements 1;
      description "Represents redundant gNodeB-DU function.\n\nUsed when more than one gNodeB-CU-CP needs to be defined.";
      status current {
        yexte:preliminary;
      }
      erienmyext:enm-type MOC;
      uses moc-RedundantGNodeB-keys;
      container attributes {
        description "Attributes for RedundantGNodeB";
        uses moc-RedundantGNodeB;
      } // end 'container attributes'
    } // end 'list RedundantGNodeB'
  }
  augment /erienmnrmcomtop:ManagedElement/erienmnrmgnbdu:GNBDUFunction {
    list Rrc {
      key id;
      max-elements 1;
      description "Manageable RRC protocol characteristics.\n\nThe RDN of this MO is Rrc=1.\n";
      yexte:is-system-created;
      erienmyext:enm-type MOC;
      uses moc-Rrc-keys;
      container attributes {
        description "Attributes for Rrc";
        uses moc-Rrc;
      } // end 'container attributes'
    } // end 'list Rrc'
  }
  augment /erienmnrmcomtop:ManagedElement/erienmnrmgnbdu:GNBDUFunction {
    list DUSliceQosInfo {
      key id;
      max-elements 36;
      description "DU Slice to 5QI table mapping information.";
      status obsolete {
        yexte:status-information "Since 20.Q2. Deprecated: Since 19.Q4. Planned to be removed.";
      }
      erienmyext:enm-type MOC;
      uses moc-DUSliceQosInfo-keys;
      container attributes {
        description "Attributes for DUSliceQosInfo";
        uses moc-DUSliceQosInfo;
      } // end 'container attributes'
    } // end 'list DUSliceQosInfo'
  }
  augment /erienmnrmcomtop:ManagedElement/erienmnrmgnbdu:GNBDUFunction/erienmnrmgnbdu:DU5qiTable {
    list LogicalChannelGroup {
      key id;
      max-elements 8;
      description "QoS configuration related to Logical Channel group.";
      status obsolete {
        yexte:status-information "Since 20.Q2. Planned to be removed.";
      }
      erienmyext:enm-type MOC;
      uses moc-LogicalChannelGroup-keys;
      container attributes {
        description "Attributes for LogicalChannelGroup";
        uses moc-LogicalChannelGroup;
      } // end 'container attributes'
    } // end 'list LogicalChannelGroup'
  }
  augment /erienmnrmcomtop:ManagedElement/erienmnrmgnbdu:GNBDUFunction/erienmnrmgnbdu:RadioBearerTable {
    list DataRadioBearer {
      key id;
      max-elements 1;
      description "Data radio bearer configuration.\n\nThe RDN of this MO is DataRadioBearer=1.";
      yexte:is-system-created;
      erienmyext:enm-type MOC;
      uses moc-DataRadioBearer-keys;
      container attributes {
        description "Attributes for DataRadioBearer";
        uses moc-DataRadioBearer;
      } // end 'container attributes'
    } // end 'list DataRadioBearer'
  }
  augment /erienmnrmcomtop:ManagedElement/erienmnrmgnbdu:GNBDUFunction/erienmnrmgnbdu:NRSectorCarrier/erienmnrmgnbdu:CommonBeamforming {
    list Beam {
      key id;
      max-elements 64;
      description "SSB beam used by NRSectorCarrier.\n\nCreated by the system when NRCellDU::administrativeState is changed to UNLOCKED.\n\nThe RDN of this MO is Beam=[ssbPhysicalIndex].";
      yexte:is-system-created;
      erienmyext:enm-type MOC;
      uses moc-Beam-keys;
      container attributes {
        description "Attributes for Beam";
        uses moc-Beam;
      } // end 'container attributes'
    } // end 'list Beam'
  }
  augment /erienmnrmcomtop:ManagedElement/erienmnrmgnbdu:GNBDUFunction {
    list ResourcePartitions {
      key id;
      max-elements 1;
      description "Set of resource partitions.";
      erienmyext:enm-type MOC;
      uses moc-ResourcePartitions-keys;
    } // end 'list ResourcePartitions'
  }
  augment /erienmnrmcomtop:ManagedElement/erienmnrmgnbdu:GNBDUFunction/erienmnrmgnbdu:NRSectorCarrier {
    list CommonBeamforming {
      key id;
      max-elements 1;
      description "Contains configuration parameters related to common beamforming.\n\nCreated automatically when NRCellDU::administrativeState is changed to UNLOCKED.\nCan also be created manually.\n\nThe RDN of this MO is CommonBeamforming=1 when created automatically.";
      erienmyext:enm-type MOC;
      uses moc-CommonBeamforming-keys;
      container attributes {
        description "Attributes for CommonBeamforming";
        uses moc-CommonBeamforming;
      } // end 'container attributes'
    } // end 'list CommonBeamforming'
  }
  augment /erienmnrmcomtop:ManagedElement/erienmnrmgnbdu:GNBDUFunction/erienmnrmgnbdu:NRCellDU {
    list AdditionalPLMNInfo {
      key id;
      max-elements 11;
      description "PLMN-related information that can be additionally served by NR cell.";
      erienmyext:enm-type MOC;
      uses moc-AdditionalPLMNInfo-keys;
      container attributes {
        description "Attributes for AdditionalPLMNInfo";
        uses moc-AdditionalPLMNInfo;
      } // end 'container attributes'
    } // end 'list AdditionalPLMNInfo'
  }
  augment /erienmnrmcomtop:ManagedElement {
    list GNBDUFunction {
      key id;
      description "Represents gNodeB-DU function.\n\nCannot be deleted if there are NRSectorCarriers configured.";
      erienmyext:enm-type MOC;
      uses moc-GNBDUFunction-keys;
      container attributes {
        description "Attributes for GNBDUFunction";
        uses moc-GNBDUFunction;
      } // end 'container attributes'
    } // end 'list GNBDUFunction'
  }
  augment /erienmnrmcomtop:ManagedElement/erienmnrmgnbdu:GNBDUFunction/erienmnrmgnbdu:EndpointResource {
    list LocalSctpEndpoint {
      key id;
      description "Local transport network endpoint for control plane interface.";
      erienmyext:enm-type MOC;
      uses moc-LocalSctpEndpoint-keys;
      container attributes {
        description "Attributes for LocalSctpEndpoint";
        uses moc-LocalSctpEndpoint;
      } // end 'container attributes'
    } // end 'list LocalSctpEndpoint'
  }
  augment /erienmnrmcomtop:ManagedElement/erienmnrmgnbdu:GNBDUFunction/erienmnrmgnbdu:ResourcePartitions {
    list ResourcePartition {
      key id;
      max-elements 36;
      description "Combination of attributes specifying in which resource partition a UE is included.";
      erienmyext:enm-type MOC;
      uses moc-ResourcePartition-keys;
      container attributes {
        description "Attributes for ResourcePartition";
        uses moc-ResourcePartition;
      } // end 'container attributes'
    } // end 'list ResourcePartition'
  }
  augment /erienmnrmcomtop:ManagedElement/erienmnrmgnbdu:GNBDUFunction {
    list EndpointResource {
      key id;
      description "Transport network endpoints for RAN interfaces.\n\nConfiguration is valid for an entity that refers to an instance of this MO.";
      erienmyext:enm-type MOC;
      uses moc-EndpointResource-keys;
      container attributes {
        description "Attributes for EndpointResource";
        uses moc-EndpointResource;
      } // end 'container attributes'
    } // end 'list EndpointResource'
  }
  augment /erienmnrmcomtop:ManagedElement/erienmnrmgnbdu:GNBDUFunction {
    list NRSynchronization {
      key id;
      max-elements 1;
      description "Top class for synchronization within NR.\n\nThe RDN of this MO is NRSynchronization=1.";
      yexte:is-system-created;
      erienmyext:enm-type MOC;
      uses moc-NRSynchronization-keys;
    } // end 'list NRSynchronization'
  }
  augment /erienmnrmcomtop:ManagedElement/erienmnrmgnbdu:GNBDUFunction/erienmnrmgnbdu:DUResourcePartitions {
    list DUResourcePartition {
      key id;
      max-elements 1;
      description "Combination of attributes specifying in which resource partition a UE is included.";
      status obsolete {
        yexte:status-information "Since 20.Q2. Deprecated: Since 19.Q4. Planned to be removed.";
      }
      erienmyext:enm-type MOC;
      uses moc-DUResourcePartition-keys;
      container attributes {
        description "Attributes for DUResourcePartition";
        uses moc-DUResourcePartition;
      } // end 'container attributes'
    } // end 'list DUResourcePartition'
  }
  augment /erienmnrmcomtop:ManagedElement/erienmnrmgnbdu:GNBDUFunction/erienmnrmgnbdu:NRSectorCarrier {
    list PowerBackoff {
      key id;
      max-elements 1;
      description "Configuration parameters related to EMF Exposure Power Back-off.\n\nThe feature intends to reduce radio safety distance in massive MIMO products.";
      erienmyext:enm-type MOC;
      uses moc-PowerBackoff-keys;
      container attributes {
        description "Attributes for PowerBackoff";
        uses moc-PowerBackoff;
      } // end 'container attributes'
    } // end 'list PowerBackoff'
  }
  augment /erienmnrmcomtop:ManagedElement/erienmnrmgnbdu:GNBDUFunction {
    list DU5qiTable {
      key id;
      max-elements 36;
      description "Mapping from 5G QoS Identifier to parameters that have impact on QoS.";
      erienmyext:enm-type MOC;
      uses moc-DU5qiTable-keys;
      container attributes {
        description "Attributes for DU5qiTable";
        uses moc-DU5qiTable;
      } // end 'container attributes'
    } // end 'list DU5qiTable'
  }
  augment /erienmnrmcomtop:ManagedElement/erienmnrmgnbdu:GNBDUFunction {
    list TermPointToGNBCUCP {
      key id;
      max-elements 1;
      description "Models an F1-C link to a gNodeB-CU-CP.";
      erienmyext:enm-type MOC;
      uses moc-TermPointToGNBCUCP-keys;
      container attributes {
        description "Attributes for TermPointToGNBCUCP";
        uses moc-TermPointToGNBCUCP;
      } // end 'container attributes'
    } // end 'list TermPointToGNBCUCP'
  }
  augment /erienmnrmcomtop:ManagedElement/erienmnrmgnbdu:GNBDUFunction/erienmnrmgnbdu:RedundantGNodeB {
    list TermPointToGNBCUCP {
      key id;
      max-elements 1;
      description "Models an F1-C link to a gNodeB-CU-CP.";
      erienmyext:enm-type MOC;
      uses moc-TermPointToGNBCUCP-keys;
      container attributes {
        description "Attributes for TermPointToGNBCUCP";
        uses moc-TermPointToGNBCUCP;
      } // end 'container attributes'
    } // end 'list TermPointToGNBCUCP'
  }
  augment /erienmnrmcomtop:ManagedElement/erienmnrmgnbdu:GNBDUFunction {
    list QciProfileEndcConfig {
      key id;
      max-elements 1;
      description "Route from QCIs to parameters that impacts QoS for Data Radio Bearers.\n\nENDC stands for E-UTRAN NR Dual Connectivity.\n\nThe RDN of this MO is QciProfileEndcConfig=1.";
      status deprecated {
        yexte:status-information "Since 20.Q3. Replaced by DU5qi. Planned to be removed.";
      }
      yexte:is-system-created;
      erienmyext:enm-type MOC;
      uses moc-QciProfileEndcConfig-keys;
      container attributes {
        description "Attributes for QciProfileEndcConfig";
        uses moc-QciProfileEndcConfig;
      } // end 'container attributes'
    } // end 'list QciProfileEndcConfig'
  }
  augment /erienmnrmcomtop:ManagedElement/erienmnrmgnbdu:GNBDUFunction {
    list NRCellDU {
      key id;
      max-elements 48;
      description "NR Cell representation in gNodeB-DU.\n\nPrecondition: The MO must be locked before deletion.";
      erienmyext:enm-type MOC;
      uses moc-NRCellDU-keys;
      container attributes {
        description "Attributes for NRCellDU";
        uses moc-NRCellDU;
      } // end 'container attributes'
    } // end 'list NRCellDU'
  }
  augment /erienmnrmcomtop:ManagedElement/erienmnrmgnbdu:GNBDUFunction {
    list Paging {
      key id;
      max-elements 1;
      description "Configuration parameters for Paging in the RBS.\n\nThe RDN of this MO is Paging=1.";
      yexte:is-system-created;
      erienmyext:enm-type MOC;
      uses moc-Paging-keys;
      container attributes {
        description "Attributes for Paging";
        uses moc-Paging;
      } // end 'container attributes'
    } // end 'list Paging'
  }
  augment /erienmnrmcomtop:ManagedElement/erienmnrmgnbdu:GNBDUFunction {
    list QosPriorityMapping {
      key id;
      max-elements 1;
      description "Mapping from 5G QoS priorities to parameters that have impact on QoS.";
      erienmyext:enm-type MOC;
      uses moc-QosPriorityMapping-keys;
      container attributes {
        description "Attributes for QosPriorityMapping";
        uses moc-QosPriorityMapping;
      } // end 'container attributes'
    } // end 'list QosPriorityMapping'
  }
  augment /erienmnrmcomtop:ManagedElement/erienmnrmgnbdu:GNBDUFunction {
    list NRSectorCarrier {
      key id;
      max-elements 48;
      description "Power and frequency use of SectorEquipmentFunction that covers an area.\n\nCannot be deleted once txPowerPersistentLock has been set to true. See description of txPowerPersistentLock.";
      erienmyext:enm-type MOC;
      uses moc-NRSectorCarrier-keys;
      container attributes {
        description "Attributes for NRSectorCarrier";
        uses moc-NRSectorCarrier;
      } // end 'container attributes'
    } // end 'list NRSectorCarrier'
  }
  augment /erienmnrmcomtop:ManagedElement/erienmnrmgnbdu:GNBDUFunction {
    list RpUserPlaneTermination {
      key id;
      max-elements 1;
      description "Local termination point of the radio processing user plane interface.\n\nSystem created when the first radio processing user plane link is established.\nSystem deleted when the last radio processing user plane link is released.\n\nThe RDN of this MO is RpUserPlaneTermination=1.";
      yexte:is-system-created;
      erienmyext:enm-type MOC;
      uses moc-RpUserPlaneTermination-keys;
    } // end 'list RpUserPlaneTermination'
  }
  augment /erienmnrmcomtop:ManagedElement/erienmnrmgnbdu:GNBDUFunction {
    list ExtGNBDUPartnerFunction {
      key id;
      max-elements 18;
      description "Grouping point of ERAN links to a partner gNodeB distributed unit.";
      erienmyext:enm-type MOC;
      uses moc-ExtGNBDUPartnerFunction-keys;
      container attributes {
        description "Attributes for ExtGNBDUPartnerFunction";
        uses moc-ExtGNBDUPartnerFunction;
      } // end 'container attributes'
    } // end 'list ExtGNBDUPartnerFunction'
  }
  augment /erienmnrmcomtop:ManagedElement/erienmnrmgnbdu:GNBDUFunction/erienmnrmgnbdu:ExtGNBDUPartnerFunction {
    list InterMeLink {
      key id;
      max-elements 9;
      description "ERAN Link between a local ME and a neighboring ME.\n\nSystem created when an inter ME link is established.\nSystem deleted when an inter ME link is released.\n\nThe RDNs of these MOs are InterMeLink=1 to InterMeLink=9.";
      yexte:is-system-created;
      erienmyext:enm-type MOC;
      uses moc-InterMeLink-keys;
      container attributes {
        description "Attributes for InterMeLink";
        uses moc-InterMeLink;
      } // end 'container attributes'
    } // end 'list InterMeLink'
  }
  augment /erienmnrmcomtop:ManagedElement/erienmnrmgnbdu:GNBDUFunction/erienmnrmgnbdu:UeCC {
    list SchedulingProfile {
      key id;
      max-elements 100;
      description "Scheduling profile used for current connection.\n\nIf DU5qi::schedulingProfileRef is non-empty, attributes from referred MO instance are used.\nIf DU5qi::schedulingProfileRef is empty, attribute default values according to MO class definition are used.";
      status current {
        yexte:preliminary;
      }
      erienmyext:enm-type MOC;
      uses moc-SchedulingProfile-keys;
      container attributes {
        description "Attributes for SchedulingProfile";
        uses moc-SchedulingProfile;
      } // end 'container attributes'
    } // end 'list SchedulingProfile'
  }
  augment /erienmnrmcomtop:ManagedElement/erienmnrmgnbdu:GNBDUFunction/erienmnrmgnbdu:RadioBearerTable {
    list SignalingRadioBearer {
      key id;
      max-elements 1;
      description "Parameters related to Signaling Radio Bearer.\n\nThe RDN of this MO is SignalingRadioBearer=1.";
      yexte:is-system-created;
      erienmyext:enm-type MOC;
      uses moc-SignalingRadioBearer-keys;
      container attributes {
        description "Attributes for SignalingRadioBearer";
        uses moc-SignalingRadioBearer;
      } // end 'container attributes'
    } // end 'list SignalingRadioBearer'
  }
  augment /erienmnrmcomtop:ManagedElement/erienmnrmgnbdu:GNBDUFunction {
    list UeCC {
      key id;
      max-elements 1;
      description "Container class for UE Connection Control (UeCC) attributes and UeCC profile classes.\n\nThe RDN of this MO must always be UeCC=1.";
      status current {
        yexte:preliminary;
      }
      erienmyext:enm-type MOC;
      uses moc-UeCC-keys;
    } // end 'list UeCC'
  }
  augment /erienmnrmcomtop:ManagedElement/erienmnrmgnbdu:GNBDUFunction/erienmnrmgnbdu:DU5qiTable {
    list DU5qi {
      key id;
      max-elements 29;
      description "QoS configuration corresponding to 3GPP-defined and operator-defined 5QI profiles.\n\nMaximum number of operator-defined profiles is 9.\n\nEach profile can be present once in each table.";
      erienmyext:enm-type MOC;
      uses moc-DU5qi-keys;
      container attributes {
        description "Attributes for DU5qi";
        uses moc-DU5qi;
      } // end 'container attributes'
    } // end 'list DU5qi'
  }
  augment /erienmnrmcomtop:ManagedElement/erienmnrmgnbdu:GNBDUFunction/erienmnrmgnbdu:RpUserPlaneTermination {
    list RpUserPlaneLink {
      key id;
      description "User plane link for the radio processing interface.\n\nSystem created when a radio processing user plane link is established.\nSystem deleted when a radio processing user plane link is released.\n\nThe RDN of this MO is RpUserPlaneLink=[Remote Managed Element Identity].";
      yexte:is-system-created;
      erienmyext:enm-type MOC;
      uses moc-RpUserPlaneLink-keys;
      container attributes {
        description "Attributes for RpUserPlaneLink";
        uses moc-RpUserPlaneLink;
      } // end 'container attributes'
    } // end 'list RpUserPlaneLink'
  }
  augment /erienmnrmcomtop:ManagedElement/erienmnrmgnbdu:GNBDUFunction/erienmnrmgnbdu:QosPriorityMapping {
    list PriorityDomainMapping {
      key id;
      max-elements 64;
      description "Mapping from 5G QoS priority level to internal parameters that have absolute priority realization.";
      erienmyext:enm-type MOC;
      uses moc-PriorityDomainMapping-keys;
      container attributes {
        description "Attributes for PriorityDomainMapping";
        uses moc-PriorityDomainMapping;
      } // end 'container attributes'
    } // end 'list PriorityDomainMapping'
  }
  augment /erienmnrmcomtop:ManagedElement/erienmnrmgnbdu:GNBDUFunction/erienmnrmgnbdu:ResourcePartitions/erienmnrmgnbdu:ResourcePartition {
    list ResourcePartitionMember {
      key id;
      max-elements 36;
      description "Set of member information of resource partition.";
      erienmyext:enm-type MOC;
      uses moc-ResourcePartitionMember-keys;
      container attributes {
        description "Attributes for ResourcePartitionMember";
        uses moc-ResourcePartitionMember;
      } // end 'container attributes'
    } // end 'list ResourcePartitionMember'
  }
  augment /erienmnrmcomtop:ManagedElement/erienmnrmgnbdu:GNBDUFunction {
    list DUResourcePartitions {
      key id;
      max-elements 1;
      description "Set of resource partitions.";
      status obsolete {
        yexte:status-information "Since 20.Q2. Deprecated: Since 19.Q4. Planned to be removed.";
      }
      erienmyext:enm-type MOC;
      uses moc-DUResourcePartitions-keys;
    } // end 'list DUResourcePartitions'
  }
}
