module ericsson-enm-RtnDhcpRelayIPv6 {
  yang-version 1.1;
  namespace urn:rdns:com:ericsson:ericsson-enm-RtnDhcpRelayIPv6;
  prefix erienmnrmrtndhcprelayipv6;
  yexte:ecim-name RtnDhcpRelayIPv6;
  revision 2351-11-28 {
    yexte:version 1;
    yexte:release 3;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RtnL3Router {
    prefix erienmnrmrtnl3router;
  }
  grouping moc-DhcpRelayIPv6-keys {
    description "Key(s) for MOC DhcpRelayIPv6";
    leaf id {
      erienmyext:no-notification;
      description "The value component of the RDN.";
      mandatory true;
      yexte:ecim-name dhcpRelayIPv6Id;
      type string;
    }
  } // end 'grouping moc-DhcpRelayIPv6-keys'
  grouping moc-DhcpRelayIPv6 {
    description "Represents DHCP relay agent, that can relay IPv6 DHCP messages between DHCP clients and servers, which are not attached to same link.";
    leaf-list server {
      min-elements 1;
      max-elements 10;
      description "Reference to PeerIPv6 MO that DHCP packets will be relayed to.";
      yexte:disturbances "Changing this attribute causes traffic disturbances.";
      yexte:dependencies "Referred PeerIPv6 MO must belong to same Router MO.";
      erienmyext:enm-type MOREF;
      type string;
    }
    leaf-list linkAddress {
      min-elements 1;
      description "Reference to AddressIPv6 MO, used by DHCPv6 server to determine link from which client should be assigned address and other configuration information.";
      yexte:disturbances "Changing this attribute causes traffic disturbances.";
      yexte:dependencies "Referred AddressIPv6 MO must belong to same Router MO.\nReferred AddressIPv6 MO must have configurationMode MANUAL.\nMust not be link local address.\nMust not be duplicated.\nLoopback interfaces are not allowed.\nCannot refer to AddressIPv6 MO, used for IpsecTunnel MO.";
      erienmyext:enm-type MOREF;
      type string;
    }
  } // end 'grouping moc-DhcpRelayIPv6'
  augment /erienmnrmcomtop:ManagedElement/erienmnrmcomtop:Transport/erienmnrmrtnl3router:Router {
    list DhcpRelayIPv6 {
      key id;
      description "Represents DHCP relay agent, that can relay IPv6 DHCP messages between DHCP clients and servers, which are not attached to same link.";
      erienmyext:enm-type MOC;
      uses moc-DhcpRelayIPv6-keys;
      container attributes {
        description "Attributes for DhcpRelayIPv6";
        uses moc-DhcpRelayIPv6;
      } // end 'container attributes'
    } // end 'list DhcpRelayIPv6'
  }
}
