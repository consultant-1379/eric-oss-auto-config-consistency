module ericsson-enm-RcsPMEventSigM {
  yang-version 1.1;
  namespace urn:rdns:com:ericsson:ericsson-enm-RcsPMEventSigM;
  prefix erienmnrmrcspmeventsigm;
  yexte:ecim-name RcsPMEventSigM;
  revision 2351-11-28 {
    yexte:version 6;
    yexte:release 1;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef enum-EventStatus {
    description "Identifies the status of the Event Type";
    type enumeration {
      enum PRELIMINARY {
        description "The event is available and stepped in this version of the Managed Element, but is not yet approved. ";
        value 0;
      }
      enum USED {
        description "The event is approved, available and stepped in this version of the Managed Element. ";
        value 1;
      }
      enum DEPRECATED {
        description "The event is available in this version of the Managed Element, but as it is planned for removal it is not recommended for use.";
        value 2;
      }
      enum OBSOLETE {
        value 3;
      }
    }
  }
  grouping moc-PmEventSigM-keys {
    description "Key(s) for MOC PmEventSigM";
    leaf id {
      erienmyext:no-notification;
      description "Holds the name used when identifying the MO.";
      mandatory true;
      yexte:ecim-name pmEventSigMId;
      type string;
    }
  } // end 'grouping moc-PmEventSigM-keys'
  grouping moc-PmEventSigM {
    description "Performance management (PM) event fragment for signalling based event jobs.\nIt is used to provide event producer specific provisioning of event jobs controlled by signalling based activation from the core network.\n";
    leaf userLabel {
      description "Label for free use.";
      type string;
    }
  } // end 'grouping moc-PmEventSigM'
  grouping moc-EventProducerS-keys {
    description "Key(s) for MOC EventProducerS";
    leaf id {
      erienmyext:no-notification;
      description "Holds the name used when identifying the MO.";
      mandatory true;
      yexte:ecim-name eventProducerSId;
      type string;
    }
  } // end 'grouping moc-EventProducerS-keys'
  grouping moc-EventProducerS {
    description "Event producer.
\nAllows for multiple types of event producer within an application describing distinct event functions.\n\nThe RDN of this MO is EventProducerS=<ID>.\n";
    leaf generation {
      erienmyext:no-notification;
      config false;
      description "Determines if event producer concerns GSM, UMTS, EPS, combined GSM+UMTS+EPS, IMS or 5GS measurements.";
      type string;
    }
    leaf name {
      erienmyext:no-notification;
      config false;
      description "Name of event producer.";
      type string;
    }
    leaf streamDestinationPort {
      description "Port on target for UE trace streaming over TCP.";
      yexte:takes-effect "New UE trace";
      type uint16;
      default 51544;
    }
  } // end 'grouping moc-EventProducerS'
  grouping moc-EventTypeS-keys {
    description "Key(s) for MOC EventTypeS";
    leaf id {
      erienmyext:no-notification;
      description "Holds the name used when identifying the MO.";
      mandatory true;
      yexte:ecim-name eventTypeSId;
      type string;
    }
  } // end 'grouping moc-EventTypeS-keys'
  grouping moc-EventTypeS {
    description "Event type generated by ME.\n\nThe RDN of this MO is EventTypeS=<ID>.\n";
    leaf eventStatus {
      erienmyext:no-notification;
      config false;
      description "Status of event type.";
      type erienmnrmrcspmeventsigm:enum-EventStatus;
    }
  } // end 'grouping moc-EventTypeS'
  grouping moc-EventGroupS-keys {
    description "Key(s) for MOC EventGroupS";
    leaf id {
      erienmyext:no-notification;
      description "Holds the name used when identifying the MO.";
      mandatory true;
      yexte:ecim-name eventGroupSId;
      type string;
    }
  } // end 'grouping moc-EventGroupS-keys'
  grouping moc-EventGroupS {
    description "A group of related event types.\n\nThe RDN of this MO is EventGroupS=<ID>.\n";
    leaf-list ueTraceEventBlacklist {
      min-elements 0;
      description "Indicates the eventTypeSId of events to be filtered from UE trace jobs.";
      type string;
    }
    leaf description {
      erienmyext:no-notification;
      config false;
      description "Describes the content and purpose of the event group.";
      type string;
    }
    leaf eventGroupVersion {
      erienmyext:no-notification;
      config false;
      description "Event Group version identifier.
\nUnique version identifier associated with a change to the contents of the Event Group, where new Event Types have been added.";
      type string;
    }
  } // end 'grouping moc-EventGroupS'
  augment /erienmnrmcomtop:ManagedElement/erienmnrmcomtop:SystemFunctions {
    list PmEventSigM {
      key id;
      max-elements 1;
      description "Performance management (PM) event fragment for signalling based event jobs.\nIt is used to provide event producer specific provisioning of event jobs controlled by signalling based activation from the core network.\n";
      yexte:is-system-created;
      erienmyext:enm-type MOC;
      uses moc-PmEventSigM-keys;
      container attributes {
        description "Attributes for PmEventSigM";
        uses moc-PmEventSigM;
      } // end 'container attributes'
    } // end 'list PmEventSigM'
  }
  augment /erienmnrmcomtop:ManagedElement/erienmnrmcomtop:SystemFunctions/erienmnrmrcspmeventsigm:PmEventSigM {
    list EventProducerS {
      key id;
      description "Event producer.
\nAllows for multiple types of event producer within an application describing distinct event functions.\n\nThe RDN of this MO is EventProducerS=<ID>.\n";
      yexte:is-system-created;
      erienmyext:enm-type MOC;
      uses moc-EventProducerS-keys;
      container attributes {
        description "Attributes for EventProducerS";
        uses moc-EventProducerS;
      } // end 'container attributes'
    } // end 'list EventProducerS'
  }
  augment /erienmnrmcomtop:ManagedElement/erienmnrmcomtop:SystemFunctions/erienmnrmrcspmeventsigm:PmEventSigM/erienmnrmrcspmeventsigm:EventProducerS/erienmnrmrcspmeventsigm:EventGroupS {
    list EventTypeS {
      key id;
      description "Event type generated by ME.\n\nThe RDN of this MO is EventTypeS=<ID>.\n";
      yexte:is-system-created;
      erienmyext:enm-type MOC;
      uses moc-EventTypeS-keys;
      container attributes {
        description "Attributes for EventTypeS";
        uses moc-EventTypeS;
      } // end 'container attributes'
    } // end 'list EventTypeS'
  }
  augment /erienmnrmcomtop:ManagedElement/erienmnrmcomtop:SystemFunctions/erienmnrmrcspmeventsigm:PmEventSigM/erienmnrmrcspmeventsigm:EventProducerS {
    list EventGroupS {
      key id;
      description "A group of related event types.\n\nThe RDN of this MO is EventGroupS=<ID>.\n";
      yexte:is-system-created;
      erienmyext:enm-type MOC;
      uses moc-EventGroupS-keys;
      container attributes {
        description "Attributes for EventGroupS";
        uses moc-EventGroupS;
      } // end 'container attributes'
    } // end 'list EventGroupS'
  }
}
