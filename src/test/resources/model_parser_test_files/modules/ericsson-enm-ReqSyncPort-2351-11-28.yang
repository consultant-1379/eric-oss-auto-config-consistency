module ericsson-enm-ReqSyncPort {
  yang-version 1.1;
  namespace urn:rdns:com:ericsson:ericsson-enm-ReqSyncPort;
  prefix erienmnrmreqsyncport;
  yexte:ecim-name ReqSyncPort;
  revision 2351-11-28 {
    yexte:version 3;
    yexte:release 0;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqFieldReplaceableUnit {
    prefix erienmnrmreqfieldreplaceableunit;
  }
  import ericsson-enm-ReqEquipment {
    prefix erienmnrmreqequipment;
  }
  typedef enum-OperState {
    description "The operational states of a resource.";
    type enumeration {
      enum DISABLED {
        description " The resource is  totally inoperable.";
        value 0;
      }
      enum ENABLED {
        description " The resource is partially or fully operable.";
        value 1;
      }
    }
  }
  typedef enum-AvailStatus {
    description "The availability status is used to qualify the operational state.
\n It indicates why the operational state has changed its value. ";
    type enumeration {
      enum IN_TEST {
        description "The resource is undergoing a test procedure. 
\nIf the administrative state is locked or  shutting down then normal users are precluded from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "This indicates a log full condition.";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef ddt-ReqSyncPort_SyncPort_userLabel {
    type string {
      length 1..128;
    }
  }
  grouping moc-SyncPort-keys {
    description "Key(s) for MOC SyncPort";
    leaf id {
      erienmyext:no-notification;
      description "The value component of the RDN.\nShall match the corresponding connector label on the unit.\nFor details on which units support which sync ports, see the description of the relevant unit.";
      mandatory true;
      yexte:ecim-name syncPortId;
      yexte:dependencies "syncPortId can be SYNC, SYNC_A or SYNC_B.";
      type string;
    }
  } // end 'grouping moc-SyncPort-keys'
  grouping moc-SyncPort {
    description "This MO represents a physical connector for connecting a discrete synchronization signal.";
    leaf userLabel {
      description "Label for free use.";
      type erienmnrmreqsyncport:ddt-ReqSyncPort_SyncPort_userLabel;
    }
    leaf-list reservedBy {
      min-elements 0;
      config false;
      description "Contains a list of MO instances that reserve this MO instance.";
      notife:notifiable-state-data true;
      erienmyext:enm-type MOREF;
      type string;
    }
    leaf-list availabilityStatus {
      min-elements 0;
      erienmyext:no-notification;
      config false;
      description "The availability status.\nIt contains details about operationalState.";
      type erienmnrmreqsyncport:enum-AvailStatus;
    }
    leaf operationalState {
      erienmyext:no-notification;
      config false;
      description "The operational state.";
      type erienmnrmreqsyncport:enum-OperState;
    }
  } // end 'grouping moc-SyncPort'
  augment /erienmnrmcomtop:ManagedElement/erienmnrmreqequipment:Equipment/erienmnrmreqfieldreplaceableunit:FieldReplaceableUnit {
    list SyncPort {
      key id;
      description "This MO represents a physical connector for connecting a discrete synchronization signal.";
      erienmyext:enm-type MOC;
      uses moc-SyncPort-keys;
      container attributes {
        description "Attributes for SyncPort";
        uses moc-SyncPort;
      } // end 'container attributes'
    } // end 'list SyncPort'
  }
}
