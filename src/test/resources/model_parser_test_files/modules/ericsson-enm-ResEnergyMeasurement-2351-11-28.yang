module ericsson-enm-ResEnergyMeasurement {
  yang-version 1.1;
  namespace urn:rdns:com:ericsson:ericsson-enm-ResEnergyMeasurement;
  prefix erienmnrmresenergymeasurement;
  yexte:ecim-name ResEnergyMeasurement;
  revision 2351-11-28 {
    yexte:version 4;
    yexte:release 0;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ResEquipmentSupportFunction {
    prefix erienmnrmresequipmentsupportfunction;
  }
  typedef enum-OperState {
    description "Operational states of a resource.";
    type enumeration {
      enum DISABLED {
        description "The resource is  totally inoperable.";
        value 0;
      }
      enum ENABLED {
        description "The resource is partially or fully operable.";
        value 1;
      }
    }
  }
  typedef enum-AvailStatus {
    description "The availability status is used to qualify the operational state.
\n It indicates why the operational state has changed its value. ";
    type enumeration {
      enum IN_TEST {
        description "The resource is undergoing a test procedure. 
\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.
\nThe semantics are defined in CCITT Rec. X.735 | ISO/IEC 10164-6. ";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef ddt-ResEnergyMeasurement_EnergyMeasurement_powerConsumption {
    type int32;
  }
  typedef ddt-ResEnergyMeasurement_EnergyMeasurement_startTime {
    type string {
      length 14..14;
    }
  }
  typedef ddt-ResEnergyMeasurement_EnergyMeasurement_energyConsumption {
    type int32;
  }
  typedef ddt-ResEnergyMeasurement_EnergyMeasurement_stopTime {
    type string {
      length 14..14;
    }
  }
  typedef ddt-ResEnergyMeasurement_EnergyMeasurement_userLabel {
    type string {
      length 1..128;
    }
  }
  grouping moc-EnergyMeasurement-keys {
    description "Key(s) for MOC EnergyMeasurement";
    leaf id {
      erienmyext:no-notification;
      description "The value component of the RDN.";
      mandatory true;
      yexte:ecim-name energyMeasurementId;
      type string;
    }
  } // end 'grouping moc-EnergyMeasurement-keys'
  grouping moc-EnergyMeasurement {
    description "This MO displays the energy consumption for an RBS or part of an RBS.";
    leaf userLabel {
      description "Label for free use.
\n";
      type erienmnrmresenergymeasurement:ddt-ResEnergyMeasurement_EnergyMeasurement_userLabel;
    }
    leaf energyConsumption {
      erienmyext:no-notification;
      config false;
      description "The consumed energy for the specified units from startTime, in other words the sum of the consumption from all the included units in the energyMeterListRef attribute. ";
      type erienmnrmresenergymeasurement:ddt-ResEnergyMeasurement_EnergyMeasurement_energyConsumption;
    }
    leaf powerConsumption {
      erienmyext:no-notification;
      config false;
      description "The present power consumption of the units listed in the energyMeterListRef attribute.
\nAn undefined value indicates that it is not possible to calculate a measurement for the present power consumption.";
      type erienmnrmresenergymeasurement:ddt-ResEnergyMeasurement_EnergyMeasurement_powerConsumption;
    }
    leaf-list energyMeterListRef {
      min-elements 1;
      max-elements 32;
      erienmyext:no-notification;
      yexte:restricted;
      description "List with references to which energy meter can be included in the calculation. 
\nReference can be MO FieldReplaceableUnit representing a PSU, EMU or PDU of type ECM.";
      erienmyext:enm-type MOREF;
      type string;
    }
    leaf startTime {
      erienmyext:no-notification;
      yexte:restricted;
      description "From when the energy consumption is calculated. If the field is left empty/undefined the system will start the measurements immediately at the creation of the MO.
\nFormat: YYYYMMDD hh:mm";
      yexte:dependencies "startTime must be a date before stopTime.";
      type erienmnrmresenergymeasurement:ddt-ResEnergyMeasurement_EnergyMeasurement_startTime;
    }
    leaf stopTime {
      erienmyext:no-notification;
      yexte:restricted;
      description "When the measurement shall stop counting. An attribute to let the operator keep the measurement even when the calculating has stopped. If an empty/undefined value is set it means the measurement shall continue forever, i.e. until MO is deleted.
\nFormat: YYYYMMDD hh:mm";
      yexte:dependencies "stopTime must be a later date than startTime.";
      type erienmnrmresenergymeasurement:ddt-ResEnergyMeasurement_EnergyMeasurement_stopTime;
    }
    leaf-list availabilityStatus {
      min-elements 0;
      config false;
      description "The availability status. It contains details about operationalState.";
      notife:notifiable-state-data true;
      type erienmnrmresenergymeasurement:enum-AvailStatus;
    }
    leaf operationalState {
      erienmyext:no-notification;
      config false;
      description "Defines the operational state.";
      type erienmnrmresenergymeasurement:enum-OperState;
    }
  } // end 'grouping moc-EnergyMeasurement'
  augment /erienmnrmcomtop:ManagedElement/erienmnrmresequipmentsupportfunction:EquipmentSupportFunction {
    list EnergyMeasurement {
      key id;
      description "This MO displays the energy consumption for an RBS or part of an RBS.";
      erienmyext:enm-type MOC;
      uses moc-EnergyMeasurement-keys;
      container attributes {
        description "Attributes for EnergyMeasurement";
        uses moc-EnergyMeasurement;
      } // end 'container attributes'
    } // end 'list EnergyMeasurement'
  }
}
