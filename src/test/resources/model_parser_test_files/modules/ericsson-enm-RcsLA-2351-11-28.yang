module ericsson-enm-RcsLA {
  yang-version 1.1;
  namespace urn:rdns:com:ericsson:ericsson-enm-RcsLA;
  prefix erienmnrmrcsla;
  yexte:ecim-name RcsLA;
  revision 2351-11-28 {
    yexte:version 1;
    yexte:release 5;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-RcsSecM {
    prefix erienmnrmrcssecm;
  }
  typedef enum-AdmState {
    description "Administrative state of a resource.";
    type enumeration {
      enum LOCKED {
        description "The resource is administratively prohibited from performing services for its users.";
        value 0;
      }
      enum UNLOCKED {
        description "The resource is administratively permitted to perform services for its users.\nThis is independent of its inherent operability.";
        value 1;
      }
      enum SHUTTINGDOWN {
        description "Use of the resource is administratively permitted to existing instances of use only.\nWhile the system remains in the shutting down state the manager may at any time cause the managed object to revert to the locked state.";
        value 2;
      }
    }
  }
  typedef enum-OperState {
    description "Operational states of a resource.";
    type enumeration {
      enum DISABLED {
        description "The resource is  totally inoperable.";
        value 0;
      }
      enum ENABLED {
        description "The resource is partially or fully operable.";
        value 1;
      }
    }
  }
  typedef enum-EmergencyRestoreState {
    description "Options for emergency restore";
    type enumeration {
      enum PHYSICALONLY {
        description "Emergency restore can only be performed by pressing the physical 'Board restore' button.";
        value 0;
      }
      enum WEBENABLED {
        description "Emergency restore can be initated by pressing the physical 'Board restore' button or through the Emergency access web service.";
        value 1;
      }
    }
  }
  grouping moc-LocalAccess-keys {
    description "Key(s) for MOC LocalAccess";
    leaf id {
      erienmyext:no-notification;
      description "The value component of the RDN.\n\"LocalAccess=cmSsh\" object controls access to services like Ericsson CLI and NETCONF over SSH.\n\"LocalAccess=cmTls\" object controls access to service like Ericsson CLI and NETCONF over TLS.\n\"LocalAccess=web\" object controls access to Emergency access.\n";
      mandatory true;
      yexte:ecim-name localAccessId;
      type string;
    }
  } // end 'grouping moc-LocalAccess-keys'
  grouping moc-LocalAccess {
    description "Enables access to  local management services.\n\nControls access to SSH and TLS based services like Ericsson CLI and NETCONF, and the emergency access GUI.\n\nServices can be locked only if the Disable LMT license is present. If license is not present, services are unlocked regardless of configuration in this class.\n\nThe RDNs of these MOs are LocalAccess=cmSsh, LocalAccess=cmTls, and LocalAccess=web.";
    leaf userLabel {
      description "Label for free use.";
      type string;
    }
    leaf administrativeState {
      description "The administrative state.\nIt is not possible to set \"web\" MO to LOCKED until both \"cmSsh\" and \"cmTls\" are locked.\nIt is not possible to set \"cmSsh\" or \"cmTls\" to UNLOCKED unless \"web\" MO is UNLOCKED.\nSetting SHUTTINGDOWN will immediately shut down services and move to LOCKED.";
      yexte:dependencies "Services can be locked only if the \"Disable LMT\" license is present. If license is not present, services are unlocked regardless of configuration in this class.";
      type erienmnrmrcsla:enum-AdmState;
      default UNLOCKED;
    }
    leaf operationalState {
      config false;
      description "The operational state.";
      notife:notifiable-state-data true;
      type erienmnrmrcsla:enum-OperState;
    }
  } // end 'grouping moc-LocalAccess'
  grouping moc-LocalAccessM-keys {
    description "Key(s) for MOC LocalAccessM";
    leaf id {
      erienmyext:no-notification;
      description "The value component of the RDN.";
      mandatory true;
      yexte:ecim-name localAccessMId;
      type string;
    }
  } // end 'grouping moc-LocalAccessM-keys'
  grouping moc-LocalAccessM {
    description "Controls for the locally accessible terminal port.\n\nThe RDNs of this MO is \"LocalAccessM=1\".";
    leaf emergencyRestore {
      description "Access to emergency restore ability.\nEmergency restore can be activated by pressing the physical 'Board restore' button on boards which have this button.\nFor boards that do not have a physical 'Board restore' button, restore is initiated in the Emergency access web interface.\nFor boards that do have the phsycial 'Board restore' button it is possible to enable emergency restore in the web interfaces with this attribute.";
      yexte:dependencies "The 'Emergency Access' service must be turned on in 'LocalAccess=web' ";
      type erienmnrmrcsla:enum-EmergencyRestoreState;
      default PHYSICALONLY;
    }
    leaf userLabel {
      description "Label for free use.";
      type string;
    }
  } // end 'grouping moc-LocalAccessM'
  augment /erienmnrmcomtop:ManagedElement/erienmnrmcomtop:SystemFunctions/erienmnrmrcssecm:SecM/erienmnrmrcsla:LocalAccessM {
    list LocalAccess {
      key id;
      description "Enables access to  local management services.\n\nControls access to SSH and TLS based services like Ericsson CLI and NETCONF, and the emergency access GUI.\n\nServices can be locked only if the Disable LMT license is present. If license is not present, services are unlocked regardless of configuration in this class.\n\nThe RDNs of these MOs are LocalAccess=cmSsh, LocalAccess=cmTls, and LocalAccess=web.";
      yexte:is-system-created;
      erienmyext:enm-type MOC;
      uses moc-LocalAccess-keys;
      container attributes {
        description "Attributes for LocalAccess";
        uses moc-LocalAccess;
      } // end 'container attributes'
    } // end 'list LocalAccess'
  }
  augment /erienmnrmcomtop:ManagedElement/erienmnrmcomtop:SystemFunctions/erienmnrmrcssecm:SecM {
    list LocalAccessM {
      key id;
      max-elements 1;
      description "Controls for the locally accessible terminal port.\n\nThe RDNs of this MO is \"LocalAccessM=1\".";
      yexte:is-system-created;
      erienmyext:enm-type MOC;
      uses moc-LocalAccessM-keys;
      container attributes {
        description "Attributes for LocalAccessM";
        uses moc-LocalAccessM;
      } // end 'container attributes'
    } // end 'list LocalAccessM'
  }
}
