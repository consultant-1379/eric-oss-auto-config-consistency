module ericsson-enm-ResPowerDistribution {
  yang-version 1.1;
  namespace urn:rdns:com:ericsson:ericsson-enm-ResPowerDistribution;
  prefix erienmnrmrespowerdistribution;
  yexte:ecim-name ResPowerDistribution;
  revision 2351-11-28 {
    yexte:version 5;
    yexte:release 0;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ResEquipmentSupportFunction {
    prefix erienmnrmresequipmentsupportfunction;
  }
  typedef enum-OperState {
    description "Operational states of a resource.";
    type enumeration {
      enum DISABLED {
        description "The resource is  totally inoperable.";
        value 0;
      }
      enum ENABLED {
        description "The resource is partially or fully operable.";
        value 1;
      }
    }
  }
  typedef enum-AvailStatus {
    description "The availability status is used to qualify the operational state.\nIt indicates why the operational state has changed its value.";
    type enumeration {
      enum IN_TEST {
        description "The resource is undergoing a test procedure.\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.\nThis routine operation is to place the resource online and make it available for use. The operation may be manual or automatic, or both.\nThe operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.\nThe semantics are defined in CCITT Rec. X.735 | ISO/IEC 10164-6.";
        value 8;
      }
      enum DEPENDENCY_LOCKED {
        description "The administrative state of a resource that this resource depends on is locked.\nAlternatively, the availability status of the other resource is dependency locked.";
        value 9;
      }
      enum DEPENDENCY_FAILED {
        description "The availability status of a resource that this resource depends on is failed or dependency failed.";
        value 10;
      }
      enum DEPENDENCY_SHUTTINGDOWN {
        description "The administrative state of a resource that this resource depends on is shutting down.\nAlternatively, the availability status of the other resource is dependency shutting down.";
        value 11;
      }
      enum DEPENDENCY_RECOVERY {
        description "Resource that this resource depends on is undergoing a recovery procedure.";
        value 12;
      }
    }
  }
  typedef ddt-ResPowerDistribution_PowerDistribution_systemVoltage {
    type int32 {
      range "-600..-380 | -1..-1";
    }
  }
  typedef ddt-ResPowerDistribution_PowerDistribution_userLabel {
    type string {
      length 1..128;
    }
  }
  typedef ddt-ResPowerDistribution_PowerDistribution_priorityLoadUndervoltageDisconnect {
    type int32 {
      range -480..-400;
    }
  }
  typedef ddt-ResPowerDistribution_PowerDistribution_undervoltageDisconnectCeaseOffset {
    type int32 {
      range 10..100;
    }
  }
  typedef ddt-ResPowerDistribution_PowerDistribution_mainLoadUndervoltageDisconnect {
    type int32 {
      range -480..-400;
    }
  }
  typedef ddt-ResPowerDistribution_PowerDistribution_systemUndervoltageAlarmLevel {
    type int32 {
      range -480..-380;
    }
  }
  typedef ddt-ResPowerDistribution_PowerDistribution_systemOvervoltageAlarmLevel {
    type int32 {
      range -600..-530;
    }
  }
  grouping moc-PowerDistribution-keys {
    description "Key(s) for MOC PowerDistribution";
    leaf id {
      erienmyext:no-notification;
      description "The value component of the RDN.";
      mandatory true;
      yexte:ecim-name powerDistributionId;
      type string;
    }
  } // end 'grouping moc-PowerDistribution-keys'
  grouping moc-PowerDistribution {
    description "MO represents logical resource providing configuration and supervision support for cabinet power distribution capabilities. Examples include configuration of alarm levels and supervision of input voltage.
\n
\nDependencies: Can only exist in the node when the attribute supportSystemControl is set to true on a parent MO EquipmentSupportFunction.";
    leaf userLabel {
      description "Label for free use.
\n";
      type erienmnrmrespowerdistribution:ddt-ResPowerDistribution_PowerDistribution_userLabel;
    }
    leaf controlDomainRef {
      erienmyext:no-notification;
      description "The cabinet or hwGroup where functions represented by this MO are deployed.";
      erienmyext:enm-type MOREF;
      type string;
    }
    leaf mainLoadUndervoltageDisconnect {
      status deprecated {
        yexte:status-information "Since 18A. Replaced by mainLoadDisconnectLevel on MO BatteryBackup. Planned to be removed.";
      }
      description "The voltage at which the Battery Fuse Unit (BFU) must disconnect the main load. The main load is disconnected when systemVoltage is below mainLoadUndervoltageDisconnect
\nExample: The default value -460 = -46.0 V, gives that the main load is disconnected if systemVoltage is e.g. -45.9 V.\nDuring deprecation period, a setting of the mainLoadUndervoltageDisconnect is converted and mirrored to attribute mainLoadDisconnectLevel of MO BatteryBackup.";
      yexte:disturbances "When running on batteries, changing this attribute can cause loss of traffic.";
      yexte:dependencies "priorityLoadUndervoltageDisconnect - mainLoadUndervoltageDisconnect >= 0.2 V. 
\nmainLoadUnderVoltageDisconnect > systemUndervoltageAlarmLevel 
\nIf mainLoadUndervoltageDisconnect < -43.0 V a battery backup time test will be executed instead of a battery capacity test";
      type erienmnrmrespowerdistribution:ddt-ResPowerDistribution_PowerDistribution_mainLoadUndervoltageDisconnect;
      default -460;
    }
    leaf priorityLoadUndervoltageDisconnect {
      status deprecated {
        yexte:status-information "Since 18A. Replaced by batteryDisconnectLevel on MO BatteryBackup. Planned to be removed.";
      }
      description "The voltage at which the Battery Fuse Unit (BFU) must disconnect the Priority Load. The primary load is disconnected when systemVoltage is below priorityLoadUndervoltageDisconnect.
\nExample: The default value -450 = -45.0 V, gives that the priority load is disconnected if systemVoltage is e.g. -44.9 V.\nDuring deprecation period, a setting of the priorityLoadUndervoltageDisconnect is converted and mirrored to attribute batteryDisconnectLevel of MO BatteryBackup. ";
      yexte:disturbances "When running on batteries, changing this attribute can cause loss of traffic.";
      yexte:dependencies "priorityLoadUndervoltageDisconnect - mainLoadUndervoltageDisconnect >= 0.2 V";
      type erienmnrmrespowerdistribution:ddt-ResPowerDistribution_PowerDistribution_priorityLoadUndervoltageDisconnect;
      default -450;
    }
    leaf systemOvervoltageAlarmLevel {
      description "Alarm level for system over voltage. \nThe alarm active condition is true when systemVoltage is above SystemOvervoltageAlarmLevel.";
      type erienmnrmrespowerdistribution:ddt-ResPowerDistribution_PowerDistribution_systemOvervoltageAlarmLevel;
      default -575;
    }
    leaf systemUndervoltageAlarmLevel {
      description "Alarm level for system undervoltage. \nThe alarm is raised when systemVoltage is lower than SystemUndervoltageAlarmLevel.";
      type erienmnrmrespowerdistribution:ddt-ResPowerDistribution_PowerDistribution_systemUndervoltageAlarmLevel;
      default -475;
    }
    leaf-list availabilityStatus {
      min-elements 0;
      config false;
      description "The availability status. It contains details about operationalState.";
      notife:notifiable-state-data true;
      type erienmnrmrespowerdistribution:enum-AvailStatus;
    }
    leaf operationalState {
      erienmyext:no-notification;
      config false;
      description "Defines the operational state.";
      type erienmnrmrespowerdistribution:enum-OperState;
    }
    leaf undervoltageDisconnectCeaseOffset {
      status deprecated {
        yexte:status-information "Since 18A. Planned to be removed.";
      }
      description "The offset for the disconnected voltage above which the Battery Fuse Unit (BFU) reconnects the load. Applies to both main and priority load.
\nThe main load is reconnected when system voltage is above (mainLoadUndervoltageDisconect - undervoltageDisconnectCeaseOffset).
\nsystemVoltage = batteryVoltage when the system is running on battery supply.
\nExample: The default values gives a main load undervoltage reconnection at -460 – 70 = -530 (-53.0 V DC), the load is reconnected if systemVoltage is e.g. -53.1 V.
\n
\nNote: 
\nthe batteries are reconnected when systemVoltage is above (mainLoadUndervoltageDisconnected -underVoltageDisconnectCeaseOffset) and batteryVoltage is above -39.0V.
\nsystemVoltage is an attribute in MO PowerSupply.
\nbatteryVoltage is an attribute in MO BatteryBackup.
\n";
      type erienmnrmrespowerdistribution:ddt-ResPowerDistribution_PowerDistribution_undervoltageDisconnectCeaseOffset;
      default 70;
    }
    leaf systemVoltage {
      erienmyext:no-notification;
      config false;
      description "The measured system voltage.\nUndefined value -1 indicates that no value has been retrieved.";
      yexte:dependencies "Equal to batteryVoltage, MO BatteryBackup, if battery is connected and  discharging.";
      type erienmnrmrespowerdistribution:ddt-ResPowerDistribution_PowerDistribution_systemVoltage;
    }
  } // end 'grouping moc-PowerDistribution'
  augment /erienmnrmcomtop:ManagedElement/erienmnrmresequipmentsupportfunction:EquipmentSupportFunction {
    list PowerDistribution {
      key id;
      description "MO represents logical resource providing configuration and supervision support for cabinet power distribution capabilities. Examples include configuration of alarm levels and supervision of input voltage.
\n
\nDependencies: Can only exist in the node when the attribute supportSystemControl is set to true on a parent MO EquipmentSupportFunction.";
      erienmyext:enm-type MOC;
      uses moc-PowerDistribution-keys;
      container attributes {
        description "Attributes for PowerDistribution";
        uses moc-PowerDistribution;
      } // end 'container attributes'
    } // end 'list PowerDistribution'
  }
}
