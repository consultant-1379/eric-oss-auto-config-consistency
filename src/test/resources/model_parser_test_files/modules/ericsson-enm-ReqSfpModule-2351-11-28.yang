module ericsson-enm-ReqSfpModule {
  yang-version 1.1;
  namespace urn:rdns:com:ericsson:ericsson-enm-ReqSfpModule;
  prefix erienmnrmreqsfpmodule;
  yexte:ecim-name ReqSfpModule;
  revision 2351-11-28 {
    yexte:version 1;
    yexte:release 1;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqFieldReplaceableUnit {
    prefix erienmnrmreqfieldreplaceableunit;
  }
  import ericsson-enm-ReqEquipment {
    prefix erienmnrmreqequipment;
  }
  typedef enum-OperState {
    description "Operational states of a resource.";
    type enumeration {
      enum DISABLED {
        description "The resource is  totally inoperable.";
        value 0;
      }
      enum ENABLED {
        description "The resource is partially or fully operable.";
        value 1;
      }
    }
  }
  typedef enum-AdmState {
    description "Administrative state of a resource.";
    type enumeration {
      enum LOCKED {
        description "The resource is administratively prohibited from performing services for its users.";
        value 0;
      }
      enum UNLOCKED {
        description "The resource is administratively permitted to perform services for its users.
\nThis is independent of its inherent operability.";
        value 1;
      }
      enum SHUTTINGDOWN {
        description "Use of the resource is administratively permitted to existing instances of use only.
\nWhile the system remains in the shutting down state the manager may at any time cause the managed object to revert to the locked state.";
        value 2;
      }
    }
  }
  typedef enum-AvailStatus {
    description "The availability status is used to qualify the operational state.
\n It indicates why the operational state has changed its value. ";
    type enumeration {
      enum IN_TEST {
        description "The resource is undergoing a test procedure. 
\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.
\nThis routine operation is to place the resource online and make it available for use. The operation may be manual or automatic, or both. The operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.
\nThe semantics are defined in CCITT Rec. X.735 | ISO/IEC 10164-6. ";
        value 8;
      }
      enum DEPENDENCY_LOCKED {
        description "The administrative state of a resource that this resource depends on is locked.
\n or the availability status of the other resource is dependency locked.  ";
        value 9;
      }
      enum DEPENDENCY_FAILED {
        description "The availability status of a resource that this resource depends on is failed or dependency failed.";
        value 10;
      }
      enum DEPENDENCY_SHUTTINGDOWN {
        description "The administrative state of a resource that this resource depends on is shutting down.
\n or the availability status of the other resource is dependency shutting down. ";
        value 11;
      }
    }
  }
  typedef ddt-ReqSfpModule_SfpProductData_manufacturerDesignation {
    type string {
      length 0..16;
    }
  }
  typedef ddt-ReqSfpModule_SfpProductData_serialNumber {
    type string {
      length 0..16;
    }
  }
  typedef ddt-ReqSfpModule_SfpProductData_productNumber {
    type string {
      length 0..14;
    }
  }
  typedef ddt-ReqSfpModule_SfpProductData_productionDate {
    type string {
      length 0..8;
    }
  }
  typedef ddt-ReqSfpModule_SfpProductData_productRevision {
    type string {
      length 0..8;
    }
  }
  typedef ddt-ReqSfpModule_SfpProductData_manufacturerId {
    type string {
      length 0..16;
    }
  }
  typedef ddt-ReqSfpModule_SfpProductData_manufacturerRevision {
    type string {
      length 0..8;
    }
  }
  typedef ddt-ReqSfpModule_SfpProductData_negotiatedBitRate {
    type string {
      length 0..8;
    }
  }
  grouping struct-SfpProductData {
    description "Sfp product data.";
    leaf productionDate {
      description "The production date of the SFP module.\n";
      type erienmnrmreqsfpmodule:ddt-ReqSfpModule_SfpProductData_productionDate;
      mandatory true;
    }
    leaf serialNumber {
      description "The serial number of the SFP module.";
      type erienmnrmreqsfpmodule:ddt-ReqSfpModule_SfpProductData_serialNumber;
      mandatory true;
    }
    leaf manufacturerRevision {
      description "The manufacturer revision of the SFP module. ";
      type erienmnrmreqsfpmodule:ddt-ReqSfpModule_SfpProductData_manufacturerRevision;
      mandatory true;
    }
    leaf manufacturerId {
      description "The manufacturer ID of the SFP module. ";
      type erienmnrmreqsfpmodule:ddt-ReqSfpModule_SfpProductData_manufacturerId;
      mandatory true;
    }
    leaf manufacturerDesignation {
      description "The manufacturer designation of the SFP module. ";
      type erienmnrmreqsfpmodule:ddt-ReqSfpModule_SfpProductData_manufacturerDesignation;
      mandatory true;
    }
    leaf negotiatedBitRate {
      description "The maximum rate supported by the SFP module.\nUnit: 0.1 Gbps";
      type erienmnrmreqsfpmodule:ddt-ReqSfpModule_SfpProductData_negotiatedBitRate;
      mandatory true;
    }
    leaf productNumber {
      description "The product number of the SFP module. States \"Non-Ericsson\" when information not available.\n";
      type erienmnrmreqsfpmodule:ddt-ReqSfpModule_SfpProductData_productNumber;
      mandatory true;
    }
    leaf productRevision {
      description "The product version of the SFP module. States \"Non-Ericsson\" when information not available";
      type erienmnrmreqsfpmodule:ddt-ReqSfpModule_SfpProductData_productRevision;
      mandatory true;
    }
  } // end 'grouping struct-SfpProductData'
  grouping moc-SfpModule-keys {
    description "Key(s) for MOC SfpModule";
    leaf id {
      erienmyext:no-notification;
      description "The value component of the RDN.";
      mandatory true;
      yexte:ecim-name sfpModuleId;
      type string;
    }
  } // end 'grouping moc-SfpModule-keys'
  grouping moc-SfpModule {
    description "Created when an SFP-module is detected.\nXcede-module is treated as a special type of SFP-module.\nPM counters are not applicable for TN ports. \n \nThe RDN of this MO is the same as for the related port MO.";
    leaf administrativeState {
      description "The administrative state.
\nIf set to SHUTTINGDOWN, the state will immediately be brought to LOCKED.";
      type erienmnrmreqsfpmodule:enum-AdmState;
      default UNLOCKED;
    }
    leaf-list reservedBy {
      min-elements 0;
      erienmyext:no-notification;
      config false;
      description "Contains a list of MO instances that reserve this MO instance.";
      erienmyext:enm-type MOREF;
      type string;
    }
    container productData {
      description "Information on the installed small form-factor pluggable (SFP) module.
\n
\nA blank value indicates the data is currently unavailable. ";
      erienmyext:enm-type STRUCT;
      uses erienmnrmreqsfpmodule:struct-SfpProductData;
    } // end 'container productData'
    leaf-list availabilityStatus {
      min-elements 0;
      erienmyext:no-notification;
      config false;
      description "It contains details about operationalState.";
      type erienmnrmreqsfpmodule:enum-AvailStatus;
    }
    leaf operationalState {
      erienmyext:no-notification;
      config false;
      description "It contains details about operationalState.";
      type erienmnrmreqsfpmodule:enum-OperState;
    }
  } // end 'grouping moc-SfpModule'
  augment /erienmnrmcomtop:ManagedElement/erienmnrmreqequipment:Equipment/erienmnrmreqfieldreplaceableunit:FieldReplaceableUnit {
    list SfpModule {
      key id;
      description "Created when an SFP-module is detected.\nXcede-module is treated as a special type of SFP-module.\nPM counters are not applicable for TN ports. \n \nThe RDN of this MO is the same as for the related port MO.";
      yexte:is-system-created;
      erienmyext:enm-type MOC;
      uses moc-SfpModule-keys;
      container attributes {
        description "Attributes for SfpModule";
        uses moc-SfpModule;
      } // end 'container attributes'
    } // end 'list SfpModule'
  }
}
