module ericsson-enm-RtnLldp {
  yang-version 1.1;
  namespace urn:rdns:com:ericsson:ericsson-enm-RtnLldp;
  prefix erienmnrmrtnlldp;
  yexte:ecim-name RtnLldp;
  revision 2351-11-28 {
    yexte:version 1;
    yexte:release 3;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  typedef ddt-RtnLldp_Lldp_userLabel {
    type string {
      length 1..128;
    }
  }
  grouping moc-Lldp-keys {
    description "Key(s) for MOC Lldp";
    leaf id {
      erienmyext:no-notification;
      description "The value component of the RDN.";
      mandatory true;
      yexte:ecim-name lldpId;
      type string;
    }
  } // end 'grouping moc-Lldp-keys'
  grouping moc-Lldp {
    description "Represents Link Layer Discovery Protocol (LLDP) operation in Baseband.\n\nWhen MO is created, LLDP Rx functionality is enabled on all EthernetPorts. Lldp MO must be created before LLDP Tx functionality can be enabled. LLPD Tx is enabled separately per EthernetPort MO.";
    leaf userLabel {
      description "Label for free use.";
      type erienmnrmrtnlldp:ddt-RtnLldp_Lldp_userLabel;
    }
  } // end 'grouping moc-Lldp'
  augment /erienmnrmcomtop:ManagedElement/erienmnrmcomtop:Transport {
    list Lldp {
      key id;
      max-elements 1;
      description "Represents Link Layer Discovery Protocol (LLDP) operation in Baseband.\n\nWhen MO is created, LLDP Rx functionality is enabled on all EthernetPorts. Lldp MO must be created before LLDP Tx functionality can be enabled. LLPD Tx is enabled separately per EthernetPort MO.";
      erienmyext:enm-type MOC;
      uses moc-Lldp-keys;
      container attributes {
        description "Attributes for Lldp";
        uses moc-Lldp;
      } // end 'container attributes'
    } // end 'list Lldp'
  }
}
