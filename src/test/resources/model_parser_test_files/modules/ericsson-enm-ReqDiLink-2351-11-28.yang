module ericsson-enm-ReqDiLink {
  yang-version 1.1;
  namespace urn:rdns:com:ericsson:ericsson-enm-ReqDiLink;
  prefix erienmnrmreqdilink;
  yexte:ecim-name ReqDiLink;
  revision 2351-11-28 {
    yexte:version 1;
    yexte:release 1;
    yexte:correction 1;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  import ericsson-enm-ReqEquipment {
    prefix erienmnrmreqequipment;
  }
  typedef enum-OperState {
    description "Operational states of a resource.";
    type enumeration {
      enum DISABLED {
        description "The resource is  totally inoperable.";
        value 0;
      }
      enum ENABLED {
        description "The resource is partially or fully operable.";
        value 1;
      }
    }
  }
  typedef enum-AvailStatus {
    description "The availability status is used to qualify the operational state.\nIt indicates why the operational state has changed its value.";
    type enumeration {
      enum IN_TEST {
        description "The resource is undergoing a test procedure.\nIf the administrative state is locked or  shutting down, normal users are prevented from using the resource.";
        value 0;
      }
      enum FAILED {
        description "The resource has an internal fault that prevents it from operating.";
        value 1;
      }
      enum POWER_OFF {
        description "The resource requires power to be applied and is not powered on.";
        value 2;
      }
      enum OFF_LINE {
        description "The resource requires a routine operation to be performed.\nThis routine operation is to place the resource online and make it available for use. The operation may be manual or automatic, or both.\nThe operational state is disabled.";
        value 3;
      }
      enum OFF_DUTY {
        description "The resource has been made inactive by an internal control process.";
        value 4;
      }
      enum DEPENDENCY {
        description "The resource cannot operate because some other resource on which it depends is unavailable.";
        value 5;
      }
      enum DEGRADED {
        description "The service available from the resource is degraded in some respect.";
        value 6;
      }
      enum NOT_INSTALLED {
        description "The resource represented by the managed object is not present, or is incomplete.";
        value 7;
      }
      enum LOG_FULL {
        description "Indicates a log full condition.\nThe semantics are defined in CCITT Rec. X.735 | ISO/IEC 10164-6.";
        value 8;
      }
      enum DEPENDENCY_LOCKED {
        description "The administrative state of a resource that this resource depends on is locked.\nAlternatively, the availability status of the other resource is dependency locked.";
        value 9;
      }
      enum DEPENDENCY_FAILED {
        description "The availability status of a resource that this resource depends on is failed or dependency failed.";
        value 10;
      }
      enum DEPENDENCY_SHUTTINGDOWN {
        description "The administrative state of a resource that this resource depends on is shutting down.\nAlternatively, the availability status of the other resource is dependency shutting down.";
        value 11;
      }
      enum DEPENDENCY_RECOVERY {
        description "Resource that this resource depends on is undergoing a recovery procedure.";
        value 12;
      }
    }
  }
  grouping moc-DiLink-keys {
    description "Key(s) for MOC DiLink";
    leaf id {
      erienmyext:no-notification;
      description "Name used to identify the MO.";
      mandatory true;
      yexte:ecim-name diLinkId;
      type string;
    }
  } // end 'grouping moc-DiLink-keys'
  grouping moc-DiLink {
    description "This Managed Object is used to configure a DI link, or IDL. It has references to the two DiPort MOs that represent the endpoints of the link. The two DiPort references must be connected to the resources to make the configuration of the digital interconnect complete.\n";
    leaf diPortRef2 {
      description "Second DiPort connected to the link.";
      mandatory true;
      erienmyext:enm-type MOREF;
      type string;
    }
    leaf diPortRef1 {
      description "First DiPort connected to the link.";
      mandatory true;
      erienmyext:enm-type MOREF;
      type string;
    }
    leaf operationalState {
      erienmyext:no-notification;
      config false;
      description "The operational state.";
      type erienmnrmreqdilink:enum-OperState;
    }
    leaf-list availabilityStatus {
      min-elements 0;
      erienmyext:no-notification;
      config false;
      description "The availability status. It contains details about operationalState.";
      type erienmnrmreqdilink:enum-AvailStatus;
    }
  } // end 'grouping moc-DiLink'
  augment /erienmnrmcomtop:ManagedElement/erienmnrmreqequipment:Equipment {
    list DiLink {
      key id;
      description "This Managed Object is used to configure a DI link, or IDL. It has references to the two DiPort MOs that represent the endpoints of the link. The two DiPort references must be connected to the resources to make the configuration of the digital interconnect complete.\n";
      erienmyext:enm-type MOC;
      uses moc-DiLink-keys;
      container attributes {
        description "Attributes for DiLink";
        uses moc-DiLink;
      } // end 'container attributes'
    } // end 'list DiLink'
  }
}
