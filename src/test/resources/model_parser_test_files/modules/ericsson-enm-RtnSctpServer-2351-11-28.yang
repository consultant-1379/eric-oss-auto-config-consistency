module ericsson-enm-RtnSctpServer {
  yang-version 1.1;
  namespace urn:rdns:com:ericsson:ericsson-enm-RtnSctpServer;
  prefix erienmnrmrtnsctpserver;
  yexte:ecim-name RtnSctpServer;
  revision 2351-11-28 {
    yexte:version 1;
    yexte:release 6;
    yexte:correction 0;
  }
  import ericsson-yang-extensions {
    prefix yexte;
  }
  import ericsson-notifications {
    prefix notife;
  }
  import ericsson-enm-yang-extensions {
    prefix erienmyext;
  }
  organization "Ericsson AB";
  contact "Ericsson first line support via email";
  description "Copyright (c) 2021 Ericsson AB. All rights reserved.";
  import ericsson-enm-ComTop {
    prefix erienmnrmcomtop;
  }
  grouping moc-Sctp-keys {
    description "Key(s) for MOC Sctp";
    leaf id {
      erienmyext:no-notification;
      description "The value component of the RDN. ";
      mandatory true;
      yexte:ecim-name sctpId;
      type string;
    }
  } // end 'grouping moc-Sctp-keys'
  grouping moc-Sctp {
    description "The Sctp is an abstraction of the SCTP system.\nThe only purpose of this class is PM counters. Created automatically when the first SctpEndpoint is created.";
  } // end 'grouping moc-Sctp'
  augment /erienmnrmcomtop:ManagedElement/erienmnrmcomtop:Transport {
    list Sctp {
      key id;
      max-elements 1;
      description "The Sctp is an abstraction of the SCTP system.\nThe only purpose of this class is PM counters. Created automatically when the first SctpEndpoint is created.";
      yexte:is-system-created;
      erienmyext:enm-type MOC;
      uses moc-Sctp-keys;
    } // end 'list Sctp'
  }
}
